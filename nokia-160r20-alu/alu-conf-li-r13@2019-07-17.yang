module alu-conf-li-r13 {
  yang-version "1";

  namespace "urn:alcatel-lucent.com:sros:ns:yang:conf-li-r13";

  prefix "conf-li-r13";

  import alu-types {
    prefix "alu";
  }
  import ietf-inet-types {
    prefix "inet";
  }
  import ietf-yang-types {
    prefix "yang";
  }

  alu:alu-major-release "rel16";

  organization "Alcatel-Lucent";

  contact
      "Alcatel-Lucent SR OS Support 
       Web: <http://www.alcatel-lucent.com>";

  description
      "Alcatel-Lucent YANG Data model to configure Lawful Interception on SR OS based 
       routers. 
       
       Copyright 2014-2015 Alcatel-Lucent, 2016 Nokia. All rights reserved. 
       Reproduction of this document is authorized on the condition that the 
       foregoing copyright notice is included. 
       
       This alu-conf-li-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-07-17";

  grouping alu-conf-li-r13 {
    container li {
      description
          "Configure Lawful Interception";
      container li-filter-lock-state {
        description
            "Configure the lock state of the filters used by Lawful Intercept (LI)";
        leaf li-filter-lock-state-id {
          type enumeration {
            enum locked;
            enum unlocked-for-li-users;
            enum unlocked-for-all-users;
          }
        } //li-filter-lock-state-id

      } //container li-filter-lock-state

      container mirror-dest-reservation {
        description
            "Configure the service identifier range reserved for LI mirror destination 
             services";
        leaf service-id {
          type uint32 {
            range "1..2147483647";
          }
        } //service-id

        leaf to {
          type uint32 {
            range "1..2147483647";
          }
          description
              "service-id";
        } //to

      } //container mirror-dest-reservation

      leaf save {
        type boolean;
        description
            "Save Lawful Intercept configuration";
      }

      leaf use-outside-ip-address {
        type boolean;
        description
            "For Layer-2-Aware NAT subscribers, report their outside IP address";
      }

      container li-filter {
        description
            "Configuration of LI filters";
        list li-ip-filter {
          key "li-filter-name";
          description
              "Configure an LI IP filter";
          leaf li-filter-name {
            type string {
              length "1..32";
            }
          } //li-filter-name

          container description {
            description
                "Description for this filter";
            leaf description-string {
              type string {
                length "1..80";
              }
            } //description-string

          } //container description

          list entry {
            key "li-entry-id";
            description
                "Configure an li-ip-filter entry";
            leaf li-entry-id {
              type uint32 {
                range "1..65535";
              }
            } //li-entry-id

            container description {
              description
                  "Description for this entry";
              leaf description-string {
                type string {
                  length "1..80";
                }
              } //description-string

            } //container description

            container match {
              description
                  "Configure match criteria for this li-ip-filter entry";
              leaf protocol {
                type string;
                description
                    "Attribute protocol-id for match";
              } //protocol

              container dst-ip {
                description
                    "Configure destination IP address match condition";
                leaf ip-address-mask {
                  type inet:ip-prefix;
                  description
                      "<ip-address>/<mask>";
                } //ip-address-mask

                leaf ip-address {
                  type inet:ip-address;
                  description
                      "Attribute ip-address for dst-ip";
                } //ip-address

                leaf ipv4-address-mask {
                  type string;
                  description
                      "a.b.c.d any address mask expressed as dotted quad [0..255]";
                } //ipv4-address-mask

              } //container dst-ip

              container dst-port {
                description
                    "Configure destination port match condition";
                leaf dst-port-id {
                  type enumeration {
                    enum lt;
                    enum gt;
                    enum eq;
                  }
                } //dst-port-id

                leaf dst-port-number {
                  type string;
                  description
                      "Attribute dst-port-number for dst-port";
                } //dst-port-number

                leaf-list range {
                  type string;
                  max-elements 2;
                  description
                      "dst-port-number";
                } //range

              } //container dst-port

              container src-ip {
                description
                    "Configure source IP address match condition";
                leaf ip-address-mask {
                  type inet:ip-prefix;
                  description
                      "<ip-address>/<mask>";
                } //ip-address-mask

                leaf ip-address {
                  type inet:ip-address;
                  description
                      "Attribute ip-address for src-ip";
                } //ip-address

                leaf ipv4-address-mask {
                  type string;
                  description
                      "a.b.c.d any address mask expressed as dotted quad [0..255]";
                } //ipv4-address-mask

              } //container src-ip

              container src-port {
                description
                    "Configure source port match condition";
                leaf src-port-id {
                  type enumeration {
                    enum lt;
                    enum gt;
                    enum eq;
                  }
                } //src-port-id

                leaf src-port-number {
                  type string;
                  description
                      "Attribute src-port-number for src-port";
                } //src-port-number

                leaf-list range {
                  type string;
                  max-elements 2;
                  description
                      "src-port-number";
                } //range

              } //container src-port

            } //container match

          } //list entry

        } //list li-ip-filter

        list li-ipv6-filter {
          key "li-filter-name";
          description
              "Configure an LI IPv6 filter";
          leaf li-filter-name {
            type string {
              length "1..32";
            }
          } //li-filter-name

          container description {
            description
                "Description for this filter";
            leaf description-string {
              type string {
                length "1..80";
              }
            } //description-string

          } //container description

          list entry {
            key "li-entry-id";
            description
                "Configure an li-ipv6-filter entry";
            leaf li-entry-id {
              type uint32 {
                range "1..65535";
              }
            } //li-entry-id

            container description {
              description
                  "Description for this entry";
              leaf description-string {
                type string {
                  length "1..80";
                }
              } //description-string

            } //container description

            container match {
              description
                  "Configure match criteria for this li-ipv6-filter entry";
              leaf next-header {
                type string;
                description
                    "Attribute next-header for match";
              } //next-header

              container dst-ip {
                description
                    "Configure destination IPv6 address match condition";
                leaf ipv6-address-prefix-length {
                  type string;
                  description
                      "<ipv6-address>/<prefix-length>";
                } //ipv6-address-prefix-length

                leaf ipv6-address {
                  type inet:ipv6-address;
                  description
                      "Attribute ipv6-address for dst-ip";
                } //ipv6-address

                leaf ipv6-address-mask {
                  type inet:ipv6-address;
                  description
                      "Attribute ipv6-address-mask for dst-ip";
                } //ipv6-address-mask

              } //container dst-ip

              container dst-port {
                description
                    "Configure destination port match condition";
                leaf dst-port-id {
                  type enumeration {
                    enum lt;
                    enum gt;
                    enum eq;
                  }
                } //dst-port-id

                leaf dst-port-number {
                  type string;
                  description
                      "Attribute dst-port-number for dst-port";
                } //dst-port-number

                leaf-list range {
                  type string;
                  max-elements 2;
                  description
                      "dst-port-number";
                } //range

              } //container dst-port

              container src-ip {
                description
                    "Configure source IPv6 address match condition";
                leaf ipv6-address-prefix-length {
                  type string;
                  description
                      "<ipv6-address>/<prefix-length>";
                } //ipv6-address-prefix-length

                leaf ipv6-address {
                  type inet:ipv6-address;
                  description
                      "Attribute ipv6-address for src-ip";
                } //ipv6-address

                leaf ipv6-address-mask {
                  type inet:ipv6-address;
                  description
                      "Attribute ipv6-address-mask for src-ip";
                } //ipv6-address-mask

              } //container src-ip

              container src-port {
                description
                    "Configure source port match condition";
                leaf src-port-id {
                  type enumeration {
                    enum lt;
                    enum gt;
                    enum eq;
                  }
                } //src-port-id

                leaf src-port-number {
                  type string;
                  description
                      "Attribute src-port-number for src-port";
                } //src-port-number

                leaf-list range {
                  type string;
                  max-elements 2;
                  description
                      "src-port-number";
                } //range

              } //container src-port

            } //container match

          } //list entry

        } //list li-ipv6-filter

        list li-mac-filter {
          key "li-filter-name";
          description
              "Configure an LI MAC filter";
          leaf li-filter-name {
            type string {
              length "1..32";
            }
          } //li-filter-name

          container description {
            description
                "Description for this filter";
            leaf description-string {
              type string {
                length "1..80";
              }
            } //description-string

          } //container description

          list entry {
            key "li-entry-id";
            description
                "Configure an li-mac-filter entry";
            leaf li-entry-id {
              type string;
              description
                  "[1..65535]";
            } //li-entry-id

            container description {
              description
                  "Description for this entry";
              leaf description-string {
                type string {
                  length "1..80";
                }
              } //description-string

            } //container description

            container match {
              description
                  "Configure match criteria for this li-mac-filter entry";
              leaf frame-type {
                type enumeration {
                  enum 802dot3;
                  enum 802dot2-llc;
                  enum 802dot2-snap;
                  enum ethernet_II;
                }
              } //frame-type

              container dst-mac {
                description
                    "Configure dest. mac match condition";
                leaf ieee-address {
                  type alu:ieee-address;
                  description
                      "xx:xx:xx:xx:xx:xx or xx-xx-xx-xx-xx-xx";
                } //ieee-address

                leaf ieee-address-mask {
                  type string;
                  description
                      "xx:xx:xx:xx:xx:xx or xx-xx-xx-xx-xx-xx";
                } //ieee-address-mask

              } //container dst-mac

              container src-mac {
                description
                    "Configure source mac match condition";
                leaf ieee-address {
                  type alu:ieee-address;
                  description
                      "xx:xx:xx:xx:xx:xx or xx-xx-xx-xx-xx-xx";
                } //ieee-address

                leaf ieee-address-mask {
                  type string;
                  description
                      "xx:xx:xx:xx:xx:xx or xx-xx-xx-xx-xx-xx";
                } //ieee-address-mask

              } //container src-mac

            } //container match

          } //list entry

        } //list li-mac-filter

      } //container li-filter

      container li-filter-associations {
        description
            "Associate li-filters with regular filters";
        list li-ip-filter {
          key "li-filter-name";
          description
              "Configure an li-ip-filter association";
          leaf li-filter-name {
            type string {
              length "1..32";
            }
          } //li-filter-name

          list ip-filter {
            key "ip-filter-id";
            description
                "Associate an ip-filter with this li-ip-filter";
            leaf ip-filter-id {
              type string;
              description
                  "Attribute ip-filter-id for ip-filter";
            } //ip-filter-id

          } //list ip-filter

        } //list li-ip-filter

        list li-ipv6-filter {
          key "li-filter-name";
          description
              "Configure an li-ipv6-filter association";
          leaf li-filter-name {
            type string {
              length "1..32";
            }
          } //li-filter-name

          list ipv6-filter {
            key "ipv6-filter-id";
            description
                "Associate an ipv6-filter with this li-ipv6-filter";
            leaf ipv6-filter-id {
              type string;
              description
                  "Attribute ipv6-filter-id for ipv6-filter";
            } //ipv6-filter-id

          } //list ipv6-filter

        } //list li-ipv6-filter

        list li-mac-filter {
          key "li-filter-name";
          description
              "Configure an li-mac-filter association";
          leaf li-filter-name {
            type string {
              length "1..32";
            }
          } //li-filter-name

          list mac-filter {
            key "mac-filter-id";
            description
                "Associate a mac-filter with this li-mac-filter";
            leaf mac-filter-id {
              type string;
              description
                  "Attribute mac-filter-id for mac-filter";
            } //mac-filter-id

          } //list mac-filter

        } //list li-mac-filter

      } //container li-filter-associations

      container li-filter-block-reservation {
        description
            "Configure filter entry blocks reserved for Lawful Intercept (LI)";
        list li-reserved-block {
          key "block-name";
          description
              "Configure a filter entry block reserved for Lawful Intercept (LI)";
          leaf block-name {
            type string {
              length "1..32";
            }
          } //block-name

          container description {
            description
                "Description for this reserved block";
            leaf description-string {
              type string {
                length "1..80";
              }
            } //description-string

          } //container description

          list ip-filter {
            key "ip-filter-id";
            description
                "Configure an ip-filter in which the reservation is done";
            leaf ip-filter-id {
              type string;
              description
                  "Attribute ip-filter-id for ip-filter";
            } //ip-filter-id

          } //list ip-filter

          list ipv6-filter {
            key "ipv6-filter-id";
            description
                "Configure an ipv6-filter in which the reservation is done";
            leaf ipv6-filter-id {
              type string;
              description
                  "Attribute ipv6-filter-id for ipv6-filter";
            } //ipv6-filter-id

          } //list ipv6-filter

          list mac-filter {
            key "mac-filter-id";
            description
                "Configure a mac-filter in which the reservation is done";
            leaf mac-filter-id {
              type string;
              description
                  "Attribute mac-filter-id for mac-filter";
            } //mac-filter-id

          } //list mac-filter

          container start-entry {
            description
                "Configure a start point and a size of the reserved block";
            leaf entry-id {
              type uint32 {
                range "1..2097151";
              }
            } //entry-id

            leaf count {
              type uint32 {
                range "1..65535";
              }
              description
                  "Attribute count for start-entry";
            } //count

          } //container start-entry

        } //list li-reserved-block

      } //container li-filter-block-reservation

      list li-source {
        key "mirror-service-id";
        description
            "Configure a Lawful Intercept (LI) mirror source";
        leaf mirror-service-id {
          type string;
          description
              "Attribute mirror-service-id for li-source";
        } //mirror-service-id

        list ip-filter {
          key "ip-filter-id";
          description
              "Configure mirroring of packets matching entries for an IP filter to a mirror 
               destination";
          leaf ip-filter-id {
            type string;
            description
                "Attribute ip-filter-id for ip-filter";
          } //ip-filter-id

          leaf-list entry {
            type uint32 {
              range "1..2097151";
            }
            max-elements 8;
          } //entry

          leaf-list intercept-id {
            type uint32 {
              range "1..1073741823";
            }
            max-elements 8;
          } //intercept-id

          leaf-list session-id {
            type uint32 {
              range "1..4294967295";
            }
            max-elements 8;
          } //session-id

        } //list ip-filter

        list ipv6-filter {
          key "ipv6-filter-id";
          description
              "Configure mirroring of packets matching entries for an IPv6 filter to a mirror 
               destination";
          leaf ipv6-filter-id {
            type string;
            description
                "Attribute ipv6-filter-id for ipv6-filter";
          } //ipv6-filter-id

          leaf-list entry {
            type uint32 {
              range "1..2097151";
            }
            max-elements 8;
          } //entry

          leaf-list intercept-id {
            type uint32 {
              range "1..1073741823";
            }
            max-elements 8;
          } //intercept-id

          leaf-list session-id {
            type uint32 {
              range "1..4294967295";
            }
            max-elements 8;
          } //session-id

        } //list ipv6-filter

        list li-ip-filter {
          key "li-filter-name";
          description
              "Configure mirroring of packets matching entries of an li-ip-filter to a mirror 
               destination";
          leaf li-filter-name {
            type string {
              length "1..32";
            }
          } //li-filter-name

          leaf-list entry {
            type uint32 {
              range "1..65535";
            }
            max-elements 8;
          } //entry

          leaf-list intercept-id {
            type uint32 {
              range "1..1073741823";
            }
            max-elements 8;
          } //intercept-id

          leaf-list session-id {
            type uint32 {
              range "1..4294967295";
            }
            max-elements 8;
          } //session-id

        } //list li-ip-filter

        list li-ipv6-filter {
          key "li-filter-name";
          description
              "Configure mirroring of packets matching entries of an li-ipv6-filter to a 
               mirror destination";
          leaf li-filter-name {
            type string {
              length "1..32";
            }
          } //li-filter-name

          leaf-list entry {
            type uint32 {
              range "1..65535";
            }
            max-elements 8;
          } //entry

          leaf-list intercept-id {
            type uint32 {
              range "1..1073741823";
            }
            max-elements 8;
          } //intercept-id

          leaf-list session-id {
            type uint32 {
              range "1..4294967295";
            }
            max-elements 8;
          } //session-id

        } //list li-ipv6-filter

        list li-mac-filter {
          key "li-filter-name";
          description
              "Configure mirroring of packets matching entries of an li-mac-filter to a 
               mirror destination";
          leaf li-filter-name {
            type string {
              length "1..32";
            }
          } //li-filter-name

          leaf-list entry {
            type string;
            max-elements 8;
          } //entry

          leaf-list intercept-id {
            type uint32 {
              range "1..1073741823";
            }
            max-elements 8;
          } //intercept-id

          leaf-list session-id {
            type uint32 {
              range "1..4294967295";
            }
            max-elements 8;
          } //session-id

        } //list li-mac-filter

        list mac-filter {
          key "mac-filter-id";
          description
              "Configure mirroring of packets matching entries of a mac filter to a mirror 
               destination";
          leaf mac-filter-id {
            type string;
            description
                "Attribute mac-filter-id for mac-filter";
          } //mac-filter-id

          leaf-list entry {
            type uint32 {
              range "1..2097151";
            }
            max-elements 8;
          } //entry

          leaf-list intercept-id {
            type uint32 {
              range "1..1073741823";
            }
            max-elements 8;
          } //intercept-id

          leaf-list session-id {
            type uint32 {
              range "1..4294967295";
            }
            max-elements 8;
          } //session-id

        } //list mac-filter

        container sap {
          description
              "Associate a SAP with a mirror-source";
          leaf sap-id {
            type string;
            description
                "Attribute sap-id for sap";
          } //sap-id

          leaf ingress {
            type boolean;
          } //ingress

          leaf egress {
            type boolean;
          } //egress

          leaf intercept-id {
            type uint32 {
              range "1..1073741823";
            }
          } //intercept-id

          leaf session-id {
            type uint32 {
              range "1..4294967295";
            }
          } //session-id

        } //container sap

        leaf shutdown {
          type boolean;
          description
              "Administratively enable/disable the mirror source";
        }

        list subscriber {
          key "sub-ident-string";
          description
              "Add hosts of a subscriber to mirroring service";
          leaf sap {
            type string;
            description
                "Attribute sap-id for subscriber";
          } //sap

          leaf ip {
            type inet:ip-address;
          } //ip

          leaf mac {
            type alu:ieee-address;
            description
                "xx:xx:xx:xx:xx:xx or xx-xx-xx-xx-xx-xx";
          } //mac

          leaf sla-profile {
            type string {
              length "1..32";
            }
          } //sla-profile

          leaf-list fc {
            type enumeration {
              enum be;
              enum l2;
              enum af;
              enum l1;
              enum h2;
              enum ef;
              enum h1;
              enum nc;
            }
            max-elements 8;
          } //fc

          leaf ingress {
            type boolean;
          } //ingress

          leaf egress {
            type boolean;
          } //egress

          leaf sub-ident-string {
            type string {
              length "1..32";
            }
          } //sub-ident-string

          leaf intercept-id {
            type uint32 {
              range "1..1073741823";
            }
          } //intercept-id

          leaf session-id {
            type uint32 {
              range "1..4294967295";
            }
          } //session-id

          leaf host-type {
            type enumeration {
              enum any;
              enum ipoe;
              enum ppp;
            }
          } //host-type

          leaf family {
            type enumeration {
              enum any;
              enum ipv4;
              enum ipv6;
            }
          } //family

        } //list subscriber

        container nat {
          description
              "Configure NAT sources";
          container ethernet-header {
            description
                "Configure the ethernet header for the NAT sources";
            leaf da {
              type alu:ieee-address;
            } //da

            leaf sa {
              type alu:ieee-address;
            } //sa

            leaf etype {
              type uint16 {
                range "1536..65535";
              }
            } //etype

          } //container ethernet-header

          list classic-lsn-sub {
            key "router ip";
            description
                "Configure a Classic LSN subscriber source";
            leaf router {
              type string {
                length "1..32";
              }
              description
                  "<router-name>|<service-id>";
            } //router

            leaf ip {
              type inet:ip-address;
            } //ip

            container intercept-id {
              description
                  "Configure the intercept identifier";
              leaf intercept-id-id {
                type uint32 {
                  range "1..4294967295";
                }
              } //intercept-id-id

            } //container intercept-id

            container session-id {
              description
                  "Configure the session identifier";
              leaf session-id {
                type uint32 {
                  range "1..4294967295";
                }
              } //session-id

            } //container session-id

          } //list classic-lsn-sub

          list dslite-lsn-sub {
            key "router b4";
            description
                "Configure a Dual Stack Lite LSN subscriber source";
            leaf router {
              type string {
                length "1..32";
              }
              description
                  "<router-name>|<service-id>";
            } //router

            leaf b4 {
              type string;
              description
                  "Attribute ipv6-prefix for dslite-lsn-sub";
            } //b4

            container intercept-id {
              description
                  "Configure the intercept identifier";
              leaf intercept-id-id {
                type uint32 {
                  range "1..4294967295";
                }
              } //intercept-id-id

            } //container intercept-id

            container session-id {
              description
                  "Configure the session identifier";
              leaf session-id {
                type uint32 {
                  range "1..4294967295";
                }
              } //session-id

            } //container session-id

          } //list dslite-lsn-sub

          list l2-aware-sub {
            key "sub-ident-string";
            description
                "Configure a Layer-2-Aware subscriber source";
            leaf sub-ident-string {
              type string {
                length "1..32";
              }
            } //sub-ident-string

            container intercept-id {
              description
                  "Configure the intercept identifier";
              leaf intercept-id-id {
                type uint32 {
                  range "1..4294967295";
                }
              } //intercept-id-id

            } //container intercept-id

            container session-id {
              description
                  "Configure the session identifier";
              leaf session-id-id {
                type uint32 {
                  range "1..4294967295";
                }
              } //session-id-id

            } //container session-id

          } //list l2-aware-sub

          list nat64-lsn-sub {
            key "router ip";
            description
                "Configure a NAT64 LSN subscriber source";
            leaf router {
              type string {
                length "1..32";
              }
              description
                  "<router-name>|<service-id>";
            } //router

            leaf ip {
              type string;
              description
                  "Attribute ipv6-prefix for nat64-lsn-sub";
            } //ip

            container intercept-id {
              description
                  "Configure the intercept identifier";
              leaf intercept-id-id {
                type uint32 {
                  range "1..4294967295";
                }
              } //intercept-id-id

            } //container intercept-id

            container session-id {
              description
                  "Configure the session identifier";
              leaf session-id {
                type uint32 {
                  range "1..4294967295";
                }
              } //session-id

            } //container session-id

          } //list nat64-lsn-sub

        } //container nat

        container wlan-gw {
          description
              "Configure WLAN Gateway sources";
          list dsm-subscriber {
            key "mac";
            description
                "Configure a dsm subscriber source";
            leaf mac {
              type yang:mac-address;
            } //mac

            container intercept-id {
              description
                  "Configure the intercept identifier";
              leaf intercept-id-id {
                type uint32 {
                  range "1..4294967295";
                }
              } //intercept-id-id

            } //container intercept-id

            container session-id {
              description
                  "Configure the session identifier";
              leaf session-id-id {
                type uint32 {
                  range "1..4294967295";
                }
              } //session-id-id

            } //container session-id

          } //list dsm-subscriber

        } //container wlan-gw

      } //list li-source

      container log {
        description
            "Configure event log for Lawful Intercept";
        list log-id {
          key "log-id";
          description
              "Configure an LI event log destination";
          leaf log-id {
            type uint16 {
              range "1..100";
            }
          } //log-id

          container description {
            description
                "Description for this log-id";
            leaf description-string {
              type string {
                length "1..80";
              }
            } //description-string

          } //container description

          container filter {
            description
                "Specify filter to be used";
            leaf filter-id {
              type uint32 {
                range "1..1500";
              }
            } //filter-id

          } //container filter

          container from {
            description
                "Specify the source event stream directed to this destination";
            leaf li {
              type boolean;
              description
                  "keyword - specifies 'li' source stream";
            } //li

          } //container from

          leaf shutdown {
            type boolean;
            description
                "Administratively enable/disable the event log";
          }

          container time-format {
            description
                "Specify whether time should be displayed in local or UTC";
            leaf local-utc {
              type enumeration {
                enum local;
                enum utc;
              }
              default "utc";
              description
                  "keywords (Default - utc)";
            } //local-utc

          } //container time-format

          container to {
            description
                "Configure the destination type for this event log";
            leaf snmp {
              type boolean;
              description
                  "keyword - specifies SNMP as destination";
            } //snmp

            leaf memory {
              type boolean;
              description
                  "keyword - specifies memory as destination";
            } //memory

            leaf size {
              type uint16 {
                range "50..1024";
              }
              default 100;
            } //size

            leaf session {
              type boolean;
              description
                  "keyword - specifies telnet session as destination";
            } //session

          } //container to

        } //list log-id

      } //container log

      list mirror-dest-template {
        key "name";
        description
            "Configure a template for mirror destination service instances invoked by 
             Radius";
        leaf name {
          type string;
        } //name

        leaf type {
          type enumeration {
            enum ether;
            enum frame-relay;
            enum ppp;
            enum ip-only;
            enum atm-sdu;
            enum satop-e1;
            enum satop-t1;
            enum satop-e3;
            enum satop-t3;
            enum cesopsn;
            enum cesopsn-cas;
          }
          description
              "Attribute mirror-type for mirror-dest-template";
        } //type

        container layer-3-encap {
          description
              "Layer-3 header encapsulation";
          leaf layer-3-encap-id {
            type enumeration {
              enum ip-udp-shim;
              enum ip-gre;
            }
          } //layer-3-encap-id

          leaf direction-bit {
            type boolean;
            description
                "Enable/disable using the highest bit in the Interception ID field of the shim 
                 header to indicate the direction of the mirrored traffic flow";
          }

          container ip-src {
            description
                "Configure the source IP address to be used in the layer-3 encapsulation";
            leaf ip-address {
              type inet:ip-address;
              description
                  "a.b.c.d";
            } //ip-address

          } //container ip-src

          container router {
            description
                "Configure the router instance for the mirror destination layer-3 gateway";
            leaf router-instance {
              type string {
                length "1..32";
              }
              description
                  "Attribute router-instance for router";
            } //router-instance

          } //container router

          container udp-dst {
            description
                "Configure the default UDP destination port to be used in the Layer-3 
                 encapsulation if the layer-3 encapsulation type is ip-udp-shim";
            leaf udp-port {
              type int32 {
                range "1..65535";
              }
            } //udp-port

          } //container udp-dst

          container udp-src {
            description
                "Configure the UDP source port to be used in the Layer-3 encapsulation if the 
                 layer-3 encapsulation type is ip-udp-shim";
            leaf udp-port {
              type int32 {
                range "1..65535";
              }
            } //udp-port

          } //container udp-src

        } //container layer-3-encap

      } //list mirror-dest-template

      container persistence {
        description
            "Configure LI persistence applications";
        container x-interfaces {
          description
              "Configure persistence for x-interface applications";
          container targets-location {
            description
                "Configure the location for the targets persistence file";
            leaf cflash-id {
              type string;
              description
                  "Attribute cflash-id for targets-location";
            } //cflash-id

          } //container targets-location

        } //container x-interfaces

      } //container persistence

      container radius {
        description
            "Configure Radius for Lawful Intercept";
        container mirror-dest-template {
          description
              "Configure the mirror destination template for use with Radius";
          leaf template-name {
            type string;
          } //template-name

        } //container mirror-dest-template

      } //container radius

      container x-interfaces {
        description
            "Configure the Lawful Intercept X1, X2 and X3 interfaces";
        container ine-identifier {
          description
              "Configure the string that identifies this Intercepting Network Element";
          leaf identifier {
            type string;
          } //identifier

        } //container ine-identifier

        leaf shutdown {
          type boolean;
          description
              "Administratively disable the X1, X2 and X3 interfaces";
        }

        container user-db {
          description
              "Configure the local user database for hosts that are static for the LIC";
          leaf name {
            type string;
          } //name

        } //container user-db

        container correlation-id {
          description
              "Configure the origin of the correlation identifiers";
          container ipoe {
            description
                "Configure the correlation identfier origin for IPoE";
            leaf origin {
              type enumeration {
                enum host;
                enum queue;
                enum session;
              }
            } //origin

          } //container ipoe

          container pppoe {
            description
                "Configure the correlation identifiers origin for PPPoE";
            leaf origin {
              type enumeration {
                enum host;
                enum queue;
                enum session;
              }
            } //origin

          } //container pppoe

        } //container correlation-id

        container lics {
          description
              "Configure this Network Element to communicate with LI Centers";
          list lic {
            key "lic-name";
            description
                "Configure parameters to communicate with a specific LI Center";
            leaf lic-name {
              type string;
            } //lic-name

            container address {
              description
                  "Configure the IP address of this LIC";
              leaf ipv4-address {
                type inet:ip-address;
                description
                    "a.b.c.d";
              } //ipv4-address

            } //container address

            container description {
              description
                  "Configure a descriptive text for this LIC";
              leaf description-string {
                type string {
                  length "1..80";
                }
              } //description-string

            } //container description

            container lic-identifier {
              description
                  "Configure the string that identifies this LIC";
              leaf identifier {
                type string;
              } //identifier

            } //container lic-identifier

            container port {
              description
                  "Configure the TCP port associated with this LIC";
              leaf tcp-port {
                type uint16 {
                  range "1..65535";
                }
              } //tcp-port

            } //container port

            container router {
              description
                  "Configure the router instance";
              leaf router-name {
                type string;
                description
                    "Attribute router-name for router";
              } //router-name

            } //container router

            container authentication {
              presence
                  "Configure parameters for authentication of INE and LIC on the X1 and X2 
                   interfaces";
              container password {
                description
                    "Configure the password";
                leaf hex-string {
                  type string {
                    length "1..34";
                  }
                  description
                      "[0x0102030405060708090a0b0c0d0e0f01(exactly 32 hex nibbles)]";
                } //hex-string

              } //container password

              container private-ki {
                description
                    "Configure the private Ki";
                leaf hex-string {
                  type string {
                    length "1..34";
                  }
                  description
                      "[0x0102030405060708090a0b0c0d0e0f01 (exactly 32 hex nibbles)]";
                } //hex-string

              } //container private-ki

              container sequence-group {
                description
                    "Configure the sequence group";
                leaf group {
                  type uint32 {
                    range "2..4294967295";
                  }
                } //group

              } //container sequence-group

            } //container authentication

          } //list lic

        } //container lics

        container x1 {
          description
              "Configure the Lawful Intercept X1 interface";
          container address {
            description
                "Configure the address of this system on the X1 interface";
            leaf ipv4-address {
              type inet:ip-address;
              description
                  "a.b.c.d";
            } //ipv4-address

          } //container address

          container peer {
            description
                "Configure the X1 peer LIC";
            leaf lic-name {
              type string;
            } //lic-name

          } //container peer

          container port {
            description
                "Configure the TCP port for the X1 interface. The system listens to this port, 
                 and uses it as source TCP port.";
            leaf tcp-port {
              type uint16 {
                range "1..65535";
              }
            } //tcp-port

          } //container port

          container timeouts {
            description
                "Configure the X1 timers";
            container message-timeout {
              description
                  "Configure the X1 message timeout";
              leaf seconds {
                type uint32 {
                  range "180..300";
                }
              } //seconds

            } //container message-timeout

          } //container timeouts

        } //container x1

        container x2 {
          description
              "Configure the Lawful Intercept X2 interface";
          container address {
            description
                "Configure the address of this system on the X2 interface";
            leaf ipv4-address {
              type inet:ip-address;
              description
                  "a.b.c.d";
            } //ipv4-address

          } //container address

          container peer {
            description
                "Configure the X2 peer LIC";
            leaf lic-name {
              type string;
            } //lic-name

          } //container peer

          container timeouts {
            description
                "Configure the X2 timers";
            container keep-alive {
              description
                  "Configure the X2 keep-alive timeout";
              leaf seconds {
                type uint32 {
                  range "300..600";
                }
              } //seconds

            } //container keep-alive

            container request {
              description
                  "Configure the X2 request timeout";
              leaf seconds {
                type uint32 {
                  range "5..30";
                }
              } //seconds

            } //container request

          } //container timeouts

        } //container x2

        container x3 {
          description
              "Configure the Lawful Intercept X3 interface";
          container address-range {
            description
                "Configure the range of IP addresses of this system for the X3 interface";
            leaf start {
              type inet:ip-address;
              description
                  "a.b.c.d";
            } //start

            leaf end {
              type inet:ip-address;
              description
                  "ipv4-address";
            } //end

          } //container address-range

          container li-group {
            description
                "Configure the ISA-BB group for X3 processing";
            leaf isa-group-id {
              type uint32 {
                range "1..4";
              }
            } //isa-group-id

          } //container li-group

          container session-limit {
            description
                "Configure the maximum number of X3 sessions this system sets up";
            leaf limit {
              type uint32 {
                range "1..32";
              }
            } //limit

          } //container session-limit

          container alarms {
            description
                "Configure X3 alarms";
            container cpu-alarm {
              description
                  "Configure the ISA MDA CPU usage alarm";
              leaf high-threshold {
                type uint32 {
                  range "1..100";
                }
              } //high-threshold

              leaf low-threshold {
                type uint32 {
                  range "0..99";
                }
              } //low-threshold

            } //container cpu-alarm

            container memory-alarm {
              description
                  "Configure the ISA MDA packet buffer memory alarm";
              leaf high-threshold {
                type uint32 {
                  range "1..100";
                }
              } //high-threshold

              leaf low-threshold {
                type uint32 {
                  range "0..99";
                }
              } //low-threshold

            } //container memory-alarm

            container throughput-alarm {
              description
                  "Configure the ISA MDA throughput alarm";
              leaf high-threshold {
                type uint32 {
                  range "1..4294967295";
                }
              } //high-threshold

              leaf low-threshold {
                type uint32;
                description
                    "Mbps";
              } //low-threshold

            } //container throughput-alarm

          } //container alarms

          container peers {
            description
                "Configure the X3 peer LIC's";
            list peer {
              key "lic-name";
              description
                  "Add a peer LIC for the X3 interface";
              leaf lic-name {
                type string;
              } //lic-name

            } //list peer

          } //container peers

          container timeouts {
            description
                "Configure the X3 timers";
            container keep-alive {
              description
                  "Configure the X3 keep-alive timeout";
              leaf seconds {
                type uint32 {
                  range "300..600";
                }
              } //seconds

            } //container keep-alive

            container request {
              description
                  "Configure the X3 request timeout";
              leaf seconds {
                type uint32 {
                  range "5..30";
                }
              } //seconds

            } //container request

            container target-retry-wait {
              description
                  "Configure the retry interval for target tunnel set-up";
              leaf seconds {
                type uint32 {
                  range "300..1200";
                }
              } //seconds

            } //container target-retry-wait

          } //container timeouts

        } //container x3

      } //container x-interfaces

    } //container li

  } //grouping alu-conf-li-r13

} //module  alu-conf-li-r13
