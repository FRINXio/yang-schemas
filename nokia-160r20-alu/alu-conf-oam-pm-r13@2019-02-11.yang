module alu-conf-oam-pm-r13 {
  yang-version "1";

  namespace "urn:alcatel-lucent.com:sros:ns:yang:conf-oam-pm-r13";

  prefix "conf-oam-pm-r13";

  import alu-types {
    prefix "alu";
  }
  import ietf-inet-types {
    prefix "inet";
  }
  import ietf-yang-types {
    prefix "yang";
  }

  alu:alu-major-release "rel16";

  organization "Alcatel-Lucent";

  contact
      "Alcatel-Lucent SR OS Support 
       Web: <http://www.alcatel-lucent.com>";

  description
      "Alcatel-Lucent YANG Data model to configure Operations, Administration, and 
       Maintenance Performance Monitoring on SR OS based routers. 
       
       Copyright 2014-2015 Alcatel-Lucent, 2016 Nokia. All rights reserved. 
       Reproduction of this document is authorized on the condition that the 
       foregoing copyright notice is included. 
       
       This alu-conf-oam-pm-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-02-11";

  grouping alu-conf-oam-pm-r13 {
    container oam-pm {
      description
          "Configure Operations, Administration, and Maintenance Performance Monitoring";
      list bin-group {
        key "bin-group-number";
        description
            "Configure an OAM Performance Monitoring bin group";
        leaf bin-group-number {
          type uint64 {
            range "1..255";
          }
        } //bin-group-number

        leaf fd-bin-count {
          type uint64 {
            range "2..10";
          }
          description
              "[2..10] - Frame Delay bin count";
        } //fd-bin-count

        leaf fdr-bin-count {
          type uint64 {
            range "2..10";
          }
          description
              "[2..10] - Frame Delay Range bin count";
        } //fdr-bin-count

        leaf ifdv-bin-count {
          type uint64 {
            range "2..10";
          }
          description
              "[2..10] - Inter-Frame Delay Variation bin count";
        } //ifdv-bin-count

        container description {
          description
              "Configure (or remove) a text description of the bin group";
          leaf description-string {
            type string {
              length "1..80";
            }
          } //description-string

        } //container description

        leaf shutdown {
          type boolean;
          description
              "Administratively enable or disable the bin group";
        }

        container bin-type {
          description
              "Select the type of bin to be configured within the bin group";
          leaf fd-fdr-ifdv {
            type enumeration {
              enum fd;
              enum fdr;
              enum ifdv;
            }
            description
                "keywords - Frame Delay, Frame Delay Range, Inter-Frame Delay Variation";
          } //fd-fdr-ifdv

          list delay-event {
            key "forward-backward-round-trip";
            description
                "Configure delay thresholds for the bin type";
            leaf forward-backward-round-trip {
              type enumeration {
                enum forward;
                enum backward;
                enum round-trip;
              }
            } //forward-backward-round-trip

            leaf lowest-bin {
              type uint32 {
                range "0..9";
              }
            } //lowest-bin

            leaf threshold {
              type uint32 {
                range "1..864000";
              }
            } //threshold

            leaf clear {
              type uint32 {
                range "0..863999";
              }
              default 0;
              description
                  "[0..863999] - Default: clear threshold disabled";
            } //clear

          } //list delay-event

          list delay-event-exclusion {
            key "forward-backward-round-trip";
            description
                "Configure the lowest bin number of the set of bins to be excluded from 
                 Threshold Crossing Alert (TCA) calculations";
            leaf forward-backward-round-trip {
              type enumeration {
                enum forward;
                enum backward;
                enum round-trip;
              }
            } //forward-backward-round-trip

            leaf lowest-bin {
              type uint32 {
                range "1..9";
              }
            } //lowest-bin

          } //list delay-event-exclusion

          list exclude-from-avg {
            key "forward-backward-round-trip";
            description
                "Configure a set of bin numbers to be excluded from average delay calculations";
            leaf forward-backward-round-trip {
              type enumeration {
                enum forward;
                enum backward;
                enum round-trip;
              }
            } //forward-backward-round-trip

            leaf bins {
              type string {
              }
              description
                  "A set of bin numbers, each in the range 0..9 
                   Three example values: 0 0,8,9 0,7-9";
            } //bins

          } //list exclude-from-avg

          container bin {
            description
                "Configure a bin within the bin type";
            leaf bin-number {
              type uint64 {
                range "1..9";
              }
            } //bin-number

            container lower-bound {
              description
                  "Configure the lower bound for the bin";
              leaf microseconds {
                type uint64 {
                  range "1..4294967295";
                }
                description
                    "[1..4294967295] - Default: <bin-number> * 5000 microseconds";
              } //microseconds

            } //container lower-bound

          } //container bin

        } //container bin-type

      } //list bin-group

      list session {
        key "session-name";
        description
            "Configure an OAM Performance Monitoring session";
        leaf session-name {
          type string {
            length "1..32";
          }
        } //session-name

        leaf test-family {
          type enumeration {
            enum ethernet;
            enum ip;
            enum mpls;
          }
          description
              "keywords";
        } //test-family

        leaf session-type {
          type enumeration {
            enum proactive;
            enum on-demand;
          }
          default "proactive";
          description
              "keywords - Default: proactive";
        } //session-type

        container bin-group {
          description
              "Configure a bin group for the session";
          leaf bin-group-number {
            type uint64 {
              range "1..255";
            }
            default 1;
            description
                "[1..255] - Default: 1";
          } //bin-group-number

        } //container bin-group

        container description {
          description
              "Configure (or remove) a text description of the session";
          leaf description-string {
            type string {
              length "1..80";
            }
          } //description-string

        } //container description

        container ethernet {
          description
              "Configure the Ethernet parameters for the session";
          container dest-mac {
            description
                "Configure the destination MAC address for the session (mutually exclusive with 
                 remote-mepid)";
            leaf ieee-address {
              type yang:mac-address;
            } //ieee-address

          } //container dest-mac

          container priority {
            description
                "Configure the priority and forwarding class for the session";
            leaf priority {
              type uint64 {
                range "0..7";
              }
              default 0;
              description
                  "[0..7] - Default: 0";
            } //priority

          } //container priority

          container remote-mepid {
            description
                "Configure the remote Maintenance association End Point (MEP) for the session 
                 (mutually exclusive with dest-mac)";
            leaf mep-id {
              type uint32 {
                range "1..8191";
              }
            } //mep-id

          } //container remote-mepid

          container source {
            description
                "Configure the source Ethernet parameters for the session";
            leaf mep {
              type uint32 {
                range "1..8191";
              }
            } //mep

            leaf domain {
              type uint32 {
                range "1..4294967295";
              }
              description
                  "[1..4294967295] 
                   domain-name is the preferred parameter for specifying the domain information";
            } //domain

            leaf association {
              type uint32 {
                range "1..4294967295";
              }
              description
                  "[1..4294967295] 
                   association-name is the preferred parameter for specifying the association 
                   information";
            } //association

            leaf domain-name {
              type string {
                length "1..64";
              }
            } //domain-name

            leaf association-name {
              type string {
                length "1..64";
              }
              description
                  "admin-name";
            } //association-name

          } //container source

          container dmm {
            description
                "Create or configure the Delay Measurement Message test for the session";
            leaf test-id {
              type uint64 {
                range "0..2147483647";
              }
            } //test-id

            container data-tlv-size {
              description
                  "Configure the size of the pad TLV in the frames sent for the DMM test";
              leaf octets {
                type uint64 {
                  range "0..2000";
                }
                default 0;
                description
                    "[0 | 3..2000] - Default: 0 octets";
              } //octets

            } //container data-tlv-size

            container interval {
              description
                  "Configure the transmission interval of the DMM test";
              leaf milliseconds {
                type uint64 {
                  range "100..10000";
                }
                default 1000;
                description
                    "[100 | 1000 | 10000] - Default: 1000 milliseconds";
              } //milliseconds

            } //container interval

            leaf shutdown {
              type boolean;
              description
                  "Administratively enable or disable the DMM test";
            }

            container test-duration {
              description
                  "Configure the duration of an on-demand DMM test";
              leaf seconds {
                type uint64 {
                  range "1..86400";
                }
              } //seconds

            } //container test-duration

          } //container dmm

          container lmm {
            description
                "Create or configure the Loss Measurement Message test for the session";
            leaf test-id {
              type uint64 {
                range "0..2147483647";
              }
            } //test-id

            leaf enable-fc-collection {
              type boolean;
              description
                  "Enable or disable the collection of per forwarding class statistics for the 
                   LMM test";
            }

            container interval {
              description
                  "Configure the transmission interval of the LMM test";
              leaf milliseconds {
                type uint32 {
                  range "100..10000";
                }
                default 1000;
                description
                    "[100 | 1000 | 10000] - Default: 1000 milliseconds";
              } //milliseconds

            } //container interval

            leaf shutdown {
              type boolean;
              description
                  "Administratively enable or disable the LMM test";
            }

            container test-duration {
              description
                  "Configure the duration of an on-demand LMM test";
              leaf seconds {
                type uint64 {
                  range "1..86400";
                }
              } //seconds

            } //container test-duration

            container availability {
              description
                  "Configure the availability parameters of the LMM test";
              container flr-threshold {
                description
                    "Configure the Frame Loss Ratio threshold for the LMM test";
                leaf percentage {
                  type uint32 {
                    range "0..100";
                  }
                  default 50;
                  description
                      "[0..100] - Default: 50 percent";
                } //percentage

              } //container flr-threshold

              leaf hli-force-count {
                type boolean;
                description
                    "Force High Loss Intervals (HLIs) and Consecutive High Loss Intervals (CHLIs) 
                     to be counted, regardless of the Availability state";
              }

              leaf shutdown {
                type boolean;
                description
                    "Administratively enable or disable availability calculations for the LMM test";
              }

              container timing {
                description
                    "Configure the timing and windowing availability parameters for the LMM test";
                leaf frames-per-delta-t {
                  type uint32 {
                    range "1..50";
                  }
                  default 10;
                  description
                      "[1..50] - Default: 10 frames";
                } //frames-per-delta-t

                leaf consec-delta-t {
                  type uint32 {
                    range "2..10";
                  }
                  default 10;
                  description
                      "[2..10] - Default: 10";
                } //consec-delta-t

                leaf chli-threshold {
                  type uint32 {
                    range "1..9";
                  }
                  default 5;
                  description
                      "[1..9] - Default: 5";
                } //chli-threshold

              } //container timing

            } //container availability

            container loss-events {
              description
                  "Configure the thresholds for loss Threshold Crossing Alerts (TCAs)";
              list avg-flr-event {
                key "forward-backward";
                description
                    "Configure the thresholds for Average Frame Loss Ratio (FLR) TCAs";
                leaf forward-backward {
                  type enumeration {
                    enum forward;
                    enum backward;
                  }
                  description
                      "keywords - traffic flow direction";
                } //forward-backward

                leaf threshold {
                  type string;
                  description
                      "[0.001..100.000] - percentage";
                } //threshold

                leaf clear {
                  type string;
                  description
                      "[0.000..99.999] - percentage. Default: clear threshold disabled";
                } //clear

              } //list avg-flr-event

              list chli-event {
                key "forward-backward-aggregate";
                description
                    "Configure the thresholds for Consecutive High Loss Interval (CHLI) TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list chli-event

              list hli-event {
                key "forward-backward-aggregate";
                description
                    "Configure the thresholds for High Loss Interval (HLI) TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list hli-event

              list unavailability-event {
                key "forward-backward-aggregate";
                description
                    "Configure the thresholds for Unavailability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list unavailability-event

              list undet-availability-event {
                key "forward-backward-aggregate";
                description
                    "Configure the thresholds for Undetermined Availability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list undet-availability-event

              list undet-unavailability-event {
                key "forward-backward-aggregate";
                description
                    "Configure the thresholds for Undetermined Unavailability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list undet-unavailability-event

            } //container loss-events

          } //container lmm

          container slm {
            description
                "Create or configure the Synthetic Loss Measurement test for the session";
            leaf test-id {
              type uint64 {
                range "0..2147483647";
              }
            } //test-id

            container data-tlv-size {
              description
                  "Configure the size of the pad TLV in the frames sent for the SLM test";
              leaf octets {
                type uint64 {
                  range "0..2000";
                }
                default 0;
                description
                    "[0 | 3..2000] - Default: 0 octets";
              } //octets

            } //container data-tlv-size

            container flr-threshold {
              description
                  "Configure the Frame Loss Ratio threshold for the SLM test";
              leaf percentage {
                type uint64 {
                  range "0..100";
                }
                default 50;
                description
                    "[0..100] - Default: 50 percent";
              } //percentage

            } //container flr-threshold

            leaf hli-force-count {
              type boolean;
              description
                  "Force High Loss Intervals (HLIs) and Consecutive High Loss Intervals (CHLIs) 
                   to be counted, regardless of the Availability state";
            }

            leaf shutdown {
              type boolean;
              description
                  "Administratively enable or disable the SLM test";
            }

            container test-duration {
              description
                  "Configure the duration of an on-demand SLM test";
              leaf seconds {
                type uint64 {
                  range "1..86400";
                }
              } //seconds

            } //container test-duration

            container timing {
              description
                  "Configure the timing and windowing parameters for the SLM test";
              leaf frames-per-delta-t {
                type uint32 {
                  range "1..50";
                }
                default 10;
                description
                    "[1..50] - Default: 10 frames";
              } //frames-per-delta-t

              leaf consec-delta-t {
                type uint64 {
                  range "2..10";
                }
                default 10;
                description
                    "[2..10] - Default: 10";
              } //consec-delta-t

              leaf interval {
                type uint64 {
                  range "100..1000";
                }
                default 100;
                description
                    "[100 | 1000] - Default: 100 milliseconds";
              } //interval

              leaf chli-threshold {
                type uint64 {
                  range "1..9";
                }
                default 5;
                description
                    "[1..9] - Default: 5";
              } //chli-threshold

            } //container timing

            container loss-events {
              description
                  "Configure the thresholds for loss Threshold Crossing Alerts (TCAs)";
              list avg-flr-event {
                key "forward-backward";
                description
                    "Configure the thresholds for Average Frame Loss Ratio (FLR) TCAs";
                leaf forward-backward {
                  type enumeration {
                    enum forward;
                    enum backward;
                  }
                  description
                      "keywords - traffic flow direction";
                } //forward-backward

                leaf threshold {
                  type string;
                  description
                      "[0.001..100.000] - percentage";
                } //threshold

                leaf clear {
                  type string;
                  description
                      "[0.000..99.999] - percentage. Default: clear threshold disabled";
                } //clear

              } //list avg-flr-event

              list chli-event {
                key "forward-backward-aggregate";
                description
                    "Configure the thresholds for Consecutive High Loss Interval (CHLI) TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list chli-event

              list hli-event {
                key "forward-backward-aggregate";
                description
                    "Configure the thresholds for High Loss Interval (HLI) TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list hli-event

              list unavailability-event {
                key "forward-backward-aggregate";
                description
                    "Configure the thresholds for Unavailability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list unavailability-event

              list undet-availability-event {
                key "forward-backward-aggregate";
                description
                    "Configure the thresholds for Undetermined Availability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list undet-availability-event

              list undet-unavailability-event {
                key "forward-backward-aggregate";
                description
                    "Configure the thresholds for Undetermined Unavailability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list undet-unavailability-event

            } //container loss-events

          } //container slm

        } //container ethernet

        container ip {
          description
              "Configure the IP parameters for the session";
          leaf allow-egress-remark-dscp {
            type boolean;
            description
                "Configure whether or not to allow the session's configured DSCP value to be 
                 overwritten by the applicable egress Quality of Service (QoS) policy";
          }

          container dest-udp-port {
            description
                "Configure the destination UDP port for the session";
            leaf udp-port-number {
              type uint64 {
                range "1..65535";
              }
            } //udp-port-number

          } //container dest-udp-port

          container destination {
            description
                "Configure the destination IP address for the session";
            leaf ip-address {
              type string;
              description
                  "Attribute ip-address for destination";
            } //ip-address

          } //container destination

          leaf do-not-fragment {
            type boolean;
            description
                "Configure the IPv4 packet header Don't Fragment (DF) field for the session";
          }

          container dscp {
            description
                "Configure the Differentiated Services Code Point (DSCP) for the session";
            leaf dscp-name {
              type string {
                length "1..4";
              }
              description
                  "Attribute dscp-name for dscp";
            } //dscp-name

            leaf resolve {
              type boolean;
              description
                  "keyword - use the fc and profile configuration values to derive the DSCP value";
            } //resolve

          } //container dscp

          container fc {
            description
                "Configure the forwarding class for the session";
            leaf fc-name {
              type enumeration {
                enum be;
                enum l2;
                enum af;
                enum l1;
                enum h2;
                enum ef;
                enum h1;
                enum nc;
              }
              default "be";
              description
                  "be|l2|af|l1|h2|ef|h1|nc - Default: be";
            } //fc-name

          } //container fc

          container forwarding {
            description
                "Configure the packet forwarding options for the session";
            leaf next-hop {
              type string;
              description
                  "Attribute ip-address for forwarding";
            } //next-hop

            leaf interface {
              type string {
                length "1..32";
              }
            } //interface

            leaf bypass-routing {
              type boolean;
              description
                  "keyword - bypass the routing table when sending test packets";
            } //bypass-routing

          } //container forwarding

          container pattern {
            description
                "Configure the pattern used to fill the packet padding field for the session";
            leaf pad-value {
              type uint64 {
                range "0..65535";
              }
              default 0;
              description
                  "[0..65535] - Default: 0";
            } //pad-value

          } //container pattern

          container profile {
            description
                "Configure the Quality of Service profile for the session";
            leaf in-out {
              type enumeration {
                enum in;
                enum out;
              }
              default "out";
              description
                  "keywords - Default: out";
            } //in-out

          } //container profile

          container router {
            description
                "Configure the router for the session";
            leaf router-or-service {
              type string {
                length "1..64";
              }
              default "Base";
              description
                  "Attribute router-or-service for router";
            } //router-or-service

            leaf service-name {
              type string;
              description
                  "[64 chars max] 
                   router-instance is the preferred parameter for specifying the router or 
                   service.";
            } //service-name

          } //container router

          container router-instance {
            description
                "Configure the router instance for the session";
            leaf router-instance {
              type string {
                length "1..64";
              }
            } //router-instance

          } //container router-instance

          container source {
            description
                "Configure the source IP address for the session";
            leaf ip-address {
              type string;
              description
                  "Attribute ip-address for source";
            } //ip-address

          } //container source

          container source-udp-port {
            description
                "Configure the source UDP port for the session";
            leaf udp-port-number {
              type uint32 {
                range "64374..64383";
              }
            } //udp-port-number

          } //container source-udp-port

          container ttl {
            description
                "Configure the Time-To-Live value for the session";
            leaf time-to-live {
              type uint64 {
                range "1..255";
              }
              default 255;
              description
                  "[1..255] - Default: 255";
            } //time-to-live

          } //container ttl

          container twamp-light {
            description
                "Create or configure the TWAMP-Light (Two Way Active Measurement Protocol, 
                 Light) test for the session";
            leaf test-id {
              type uint64 {
                range "0..2147483647";
              }
            } //test-id

            container interval {
              description
                  "Configure the transmission interval of the TWAMP-Light test";
              leaf milliseconds {
                type uint64 {
                  range "100..10000";
                }
                default 1000;
                description
                    "[100 | 1000 | 10000] - Default: 1000 milliseconds";
              } //milliseconds

            } //container interval

            container pad-size {
              description
                  "Configure the amount of padding in each packet sent for the TWAMP-Light test";
              leaf octets {
                type uint64 {
                  range "0..2000";
                }
                default 0;
                description
                    "[0..2000] - Default: 0 octets";
              } //octets

            } //container pad-size

            container record-stats {
              description
                  "Configure the type of statistics recorded for the TWAMP-Light test";
              leaf delay-loss-delay-and-loss {
                type enumeration {
                  enum delay;
                  enum loss;
                  enum delay-and-loss;
                }
                default "delay";
                description
                    "keywords - record delay statistics, loss statistics, or both. Default: delay";
              } //delay-loss-delay-and-loss

            } //container record-stats

            leaf shutdown {
              type boolean;
              description
                  "Administratively enable or disable the TWAMP-Light test";
            }

            container test-duration {
              description
                  "Configure the duration of an on-demand TWAMP-Light test";
              leaf seconds {
                type uint64 {
                  range "1..86400";
                }
              } //seconds

            } //container test-duration

            container loss {
              description
                  "Configure loss parameters for the TWAMP-Light test";
              container flr-threshold {
                description
                    "Configure the Frame Loss Ratio threshold for the TWAMP-Light test";
                leaf percentage {
                  type uint32 {
                    range "0..100";
                  }
                  default 50;
                  description
                      "[0..100] - Default: 50 percent";
                } //percentage

              } //container flr-threshold

              leaf hli-force-count {
                type boolean;
                description
                    "Force High Loss Intervals (HLIs) and Consecutive High Loss Intervals (CHLIs) 
                     to be counted, regardless of the Availability state";
              }

              container timing {
                description
                    "Configure the timing and windowing loss parameters for the TWAMP-Light test";
                leaf frames-per-delta-t {
                  type uint32 {
                    range "1..50";
                  }
                  default 1;
                  description
                      "[1..50] - Default: 1 frame";
                } //frames-per-delta-t

                leaf consec-delta-t {
                  type uint32 {
                    range "2..10";
                  }
                  default 10;
                  description
                      "[2..10] - Default: 10";
                } //consec-delta-t

                leaf chli-threshold {
                  type uint32 {
                    range "1..9";
                  }
                  default 5;
                  description
                      "[1..9] - Default: 5";
                } //chli-threshold

              } //container timing

            } //container loss

            container loss-events {
              description
                  "Configure the thresholds for loss Threshold Crossing Alerts (TCAs)";
              list avg-flr-event {
                key "forward-backward";
                description
                    "Configure the thresholds for Average Frame Loss Ratio (FLR) TCAs";
                leaf forward-backward {
                  type enumeration {
                    enum forward;
                    enum backward;
                  }
                  description
                      "keywords - traffic flow direction";
                } //forward-backward

                leaf threshold {
                  type string;
                  description
                      "[0.001..100.000] - percentage";
                } //threshold

                leaf clear {
                  type string;
                  description
                      "[0.000..99.999] - percentage. Default: clear threshold disabled";
                } //clear

              } //list avg-flr-event

              list chli-event {
                key "forward-backward-aggregate";
                description
                    "Configure the thresholds for Consecutive High Loss Interval (CHLI) TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list chli-event

              list hli-event {
                key "forward-backward-aggregate";
                description
                    "Configure the thresholds for High Loss Interval (HLI) TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list hli-event

              list unavailability-event {
                key "forward-backward-aggregate";
                description
                    "Configure the thresholds for Unavailability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list unavailability-event

              list undet-availability-event {
                key "forward-backward-aggregate";
                description
                    "Configure the thresholds for Undetermined Availability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list undet-availability-event

              list undet-unavailability-event {
                key "forward-backward-aggregate";
                description
                    "Configure the thresholds for Undetermined Unavailability TCAs";
                leaf forward-backward-aggregate {
                  type enumeration {
                    enum forward;
                    enum backward;
                    enum aggregate;
                  }
                  description
                      "keywords - traffic flow direction";
                } //forward-backward-aggregate

                leaf threshold {
                  type uint32 {
                    range "1..864000";
                  }
                } //threshold

                leaf clear {
                  type uint32 {
                    range "0..863999";
                  }
                  default 0;
                  description
                      "[0..863999] - Default: clear threshold disabled";
                } //clear

              } //list undet-unavailability-event

            } //container loss-events

          } //container twamp-light

        } //container ip

        list meas-interval {
          key "t15-mins-1-hour-1-day";
          description
              "Configure the measurement interval parameters for the session";
          leaf t15-mins-1-hour-1-day {
            type enumeration {
              enum 5-mins;
              enum 15-mins;
              enum 1-hour;
              enum 1-day;
            }
            description
                "keywords - the duration of the measurement interval";
          } //t15-mins-1-hour-1-day

          container accounting-policy {
            description
                "Configure the accounting policy for the measurement interval";
            leaf acct-policy-id {
              type uint64 {
                range "1..99";
              }
            } //acct-policy-id

          } //container accounting-policy

          container boundary-type {
            description
                "Configure the start condition for the measurement interval (start when the 
                 test starts, or wall clock aligned)";
            leaf clock-aligned-test-relative {
              type enumeration {
                enum clock-aligned;
                enum test-relative;
              }
              default "clock-aligned";
              description
                  "keywords - Default: clock-aligned";
            } //clock-aligned-test-relative

          } //container boundary-type

          container clock-offset {
            description
                "Configure the wall clock offset (in seconds) for a clock-aligned measurement 
                 interval";
            leaf seconds {
              type string;
              description
                  "Attribute seconds for clock-offset";
            } //seconds

          } //container clock-offset

          container intervals-stored {
            description
                "Configure the maximum number of intervals stored for the measurement interval";
            leaf intervals {
              type string;
              description
                  "Attribute intervals for intervals-stored";
            } //intervals

          } //container intervals-stored

          container event-mon {
            description
                "Configure Threshold Cross Alerts (TCAs) for the measurement interval";
            leaf delay-events {
              type boolean;
              description
                  "Enable or disable delay TCAs for the measurement interval";
            }

            leaf loss-events {
              type boolean;
              description
                  "Enable or disable loss TCAs for the measurement interval";
            }

            leaf shutdown {
              type boolean;
              description
                  "Administratively enable or disable TCAs for the measurement interval";
            }

          } //container event-mon

        } //list meas-interval

        container mpls {
          description
              "Configure the MPLS parameters for the session";
          container dscp {
            description
                "Configure the Differentiated Services Code Point (DSCP) for the session";
            leaf dscp-name {
              type string {
                length "1..4";
              }
              description
                  "Attribute dscp-name for dscp";
            } //dscp-name

          } //container dscp

          container fc {
            description
                "Configure the forwarding class for the session";
            leaf fc-name {
              type enumeration {
                enum be;
                enum l2;
                enum af;
                enum l1;
                enum h2;
                enum ef;
                enum h1;
                enum nc;
              }
              default "be";
              description
                  "be|l2|af|l1|h2|ef|h1|nc - Default: be";
            } //fc-name

          } //container fc

          container pattern {
            description
                "Configure the pattern used to fill the packet padding field for the session";
            leaf pad-value {
              type uint64 {
                range "0..65535";
              }
              default 0;
              description
                  "[0..65535] - Default: 0";
            } //pad-value

          } //container pattern

          container profile {
            description
                "Configure the Quality of Service profile for the session";
            leaf in-out {
              type enumeration {
                enum in;
                enum out;
              }
              default "out";
              description
                  "keywords - Default: out";
            } //in-out

          } //container profile

          container ttl {
            description
                "Configure the MPLS Time-To-Live value for the session";
            leaf time-to-live {
              type uint64 {
                range "1..255";
              }
              default 255;
              description
                  "[1..255] - Default: 255";
            } //time-to-live

          } //container ttl

          container dm {
            description
                "Create or configure the MPLS Delay Measurement (MPLS-DM) test for the session";
            leaf test-id {
              type uint64 {
                range "0..67108863";
              }
            } //test-id

            container interval {
              description
                  "Configure the transmission interval of the MPLS-DM test";
              leaf milliseconds {
                type uint64 {
                  range "1000..10000";
                }
                default 1000;
                description
                    "[1000 | 2000 | 3000 | 4000 | 5000 | 6000 | 7000 | 8000 | 9000 | 10000] - 
                     Default: 1000 milliseconds";
              } //milliseconds

            } //container interval

            container pad-tlv-size {
              description
                  "Configure the total number of padding octets (including overhead) in each 
                   query packet sent for the MPLS-DM test";
              leaf octets {
                type uint32 {
                  range "0..257";
                }
                default 0;
                description
                    "[0 | 2..257] - Default: 0 octets";
              } //octets

            } //container pad-tlv-size

            leaf reflect-pad {
              type boolean;
              description
                  "Configure whether or not to copy the padding in each MPLS-DM query to the 
                   response";
            }

            leaf shutdown {
              type boolean;
              description
                  "Administratively enable or disable the MPLS-DM test";
            }

            container test-duration {
              description
                  "Configure the duration of an on-demand MPLS-DM test";
              leaf seconds {
                type uint64 {
                  range "1..86400";
                }
              } //seconds

            } //container test-duration

          } //container dm

          container lsp {
            presence
                "Specify the LSP to be tested";
            container mpls-tp-static {
              description
                  "Specify the MPLS Transport Profile (MPLS-TP) static LSP to be tested";
              container lsp {
                description
                    "Specify the name of the MPLS-TP static LSP to be tested";
                leaf lsp-name {
                  type string {
                    length "1..64";
                  }
                } //lsp-name

              } //container lsp

            } //container mpls-tp-static

            container rsvp {
              description
                  "Specify the manually-created RSVP LSP to be tested";
              container lsp {
                description
                    "Specify the name of the RSVP LSP to be tested";
                leaf lsp-name {
                  type string {
                    length "1..64";
                  }
                } //lsp-name

              } //container lsp

              container udp-return-object {
                description
                    "Configure the destination IP address used by the far end of the test to send a 
                     test response";
                leaf ip-address {
                  type string;
                  description
                      "Attribute ip-address for udp-return-object";
                } //ip-address

              } //container udp-return-object

            } //container rsvp

            container rsvp-auto {
              description
                  "Specify the automatically-created RSVP LSP to be tested";
              container from {
                description
                    "Specify an IPv4 address used (with the LSP template) to identify the LSP to be 
                     tested";
                leaf ipv4-address {
                  type inet:ip-address;
                } //ipv4-address

              } //container from

              container lsp-template {
                description
                    "Specify the LSP template used to identify the LSP to be tested";
                leaf template-name {
                  type string {
                    length "1..32";
                  }
                } //template-name

              } //container lsp-template

              container to {
                description
                    "Specify an IPv4 address used (with the LSP template) to identify the LSP to be 
                     tested";
                leaf ipv4-address {
                  type inet:ip-address;
                } //ipv4-address

              } //container to

              container udp-return-object {
                description
                    "Configure the destination IP address used by the far end of the test to send a 
                     test response";
                leaf ip-address {
                  type string;
                  description
                      "Attribute ip-address for udp-return-object";
                } //ip-address

              } //container udp-return-object

            } //container rsvp-auto

          } //container lsp

        } //container mpls

      } //list session

    } //container oam-pm

  } //grouping alu-conf-oam-pm-r13

} //module  alu-conf-oam-pm-r13
