module alu-conf-svc-ies-ipt-r13 {
  yang-version "1";

  namespace "urn:alcatel-lucent.com:sros:ns:yang:conf-svc-ies-ipt-r13";

  prefix "conf-svc-ies-ipt-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to create/delete or configure an IP transport 
       on SR OS based routers. 
       
       Copyright 2014-2015 Alcatel-Lucent, 2016 Nokia. All rights reserved. 
       Reproduction of this document is authorized on the condition that the 
       foregoing copyright notice is included. 
       
       This alu-conf-svc-ies-ipt-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-07-31";

  grouping alu-conf-svc-ies-ipt-r13 {
    list ip-transport {
      key "ipt-id";
      description
          "Create/delete or configure an IP transport";
      leaf ipt-id {
        type string {
          length "1..17";
        }
        description
            "Attribute ipt-id for ip-transport";
      } //ipt-id

      container description {
        description
            "Add/remove a description for the IP transport";
        leaf description-string {
          type string {
            length "1..80";
          }
        } //description-string

      } //container description

      container dscp {
        description
            "Configure DSCP name";
        leaf dscp-name {
          type string {
            length "1..32";
          }
          description
              "Attribute dscp-name for dscp";
        } //dscp-name

      } //container dscp

      leaf filter-unknown-host {
        type boolean;
        description
            "Enable/disable communication with unknown remote hosts";
      }

      container local-host {
        description
            "Set/unset IP transport local host";
        leaf ip-addr {
          type inet:ip-address;
          description
              "ipv4-address - a.b.c.d";
        } //ip-addr

        leaf port-num {
          type string {
          }
          description
              "Attribute port-number for local-host";
        } //port-num

        leaf protocol {
          type enumeration {
            enum tcp;
            enum udp;
          }
        } //protocol

      } //container local-host

      leaf shutdown {
        type boolean;
        description
            "Administratively enable/disable the IP transport";
      }

      list remote-host {
        key "host-id";
        description
            "Create/delete or configure an IP transport remote host";
        leaf host-id {
          type string;
          description
              "Attribute host-id for remote-host";
        } //host-id

        leaf ip-addr {
          type inet:ip-address;
          description
              "ipv4-address - a.b.c.d";
        } //ip-addr

        leaf port-num {
          type string {
          }
          description
              "Attribute port-number for remote-host";
        } //port-num

        container description {
          description
              "Add/remove a description for the IPT remote host";
          leaf description-string {
            type string {
              length "1..80";
            }
          } //description-string

        } //container description

        container name {
          description
              "Add/remove a name for the IPT remote host";
          leaf name {
            type string;
          } //name

        } //container name

      } //list remote-host

      container tcp {
        description
            "Configure TCP parameters of the IP transport";
        container inactivity-timeout {
          description
              "Configure TCP connect inactivity timeout";
          leaf seconds {
            type uint32;
            default 3600;
            description
                "Attribute seconds for inactivity-timeout";
          } //seconds

        } //container inactivity-timeout

        container max-retries {
          description
              "Configure TCP connect maximum retries";
          leaf number {
            type uint16 {
              range "0..127";
            }
            description
                "Attribute number for max-retries";
          } //number

        } //container max-retries

        container retry-interval {
          description
              "Configure TCP connect retry interval";
          leaf seconds {
            type uint32;
            default 3600;
            description
                "Attribute seconds for retry-interval";
          } //seconds

        } //container retry-interval

      } //container tcp

    } //list ip-transport

  } //grouping alu-conf-svc-ies-ipt-r13

} //module  alu-conf-svc-ies-ipt-r13
