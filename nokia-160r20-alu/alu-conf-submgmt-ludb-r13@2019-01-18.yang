module alu-conf-submgmt-ludb-r13 {
  yang-version "1";

  namespace "urn:alcatel-lucent.com:sros:ns:yang:conf-submgmt-ludb-r13";

  prefix "conf-submgmt-ludb-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure a local user database on SR OS 
       based routers. 
       
       Copyright 2014-2015 Alcatel-Lucent, 2016 Nokia. All rights reserved. 
       Reproduction of this document is authorized on the condition that the 
       foregoing copyright notice is included. 
       
       This alu-conf-submgmt-ludb-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-01-18";

  grouping alu-conf-submgmt-ludb-r13 {
    list local-user-db {
      key "local-user-db-name";
      description
          "Configure a local user database";
      leaf local-user-db-name {
        type string {
          length "1..32";
        }
      } //local-user-db-name

      container description {
        description
            "Description for this local user database";
        leaf description-string {
          type string {
            length "1..80";
          }
        } //description-string

      } //container description

      leaf shutdown {
        type boolean;
        description
            "Administratively enable/disable this local user database";
      }

      container ipoe {
        description
            "Configure IPOE hosts";
        list mask {
          key "type";
          description
              "Configure the mask";
          leaf type {
            type enumeration {
              enum none;
              enum circuit-id;
              enum mac;
              enum option60;
              enum remote-id;
              enum sap-id;
              enum service-id;
              enum string;
              enum system-id;
            }
            description
                "Attribute ipoe-match-type for mask";
          } //type

          leaf prefix-string {
            type string {
              length "1..127";
            }
            description
                "[127 chars max] ('*' is wildcard)";
          } //prefix-string

          leaf prefix-length {
            type uint32 {
              range "1..127";
            }
          } //prefix-length

          leaf suffix-string {
            type string {
              length "1..127";
            }
            description
                "[127 chars max] ('*' is wildcard)";
          } //suffix-string

          leaf suffix-length {
            type uint32 {
              range "1..127";
            }
          } //suffix-length

        } //list mask

        container match-list {
          description
              "Configure the IPOE host match criteria";
          leaf-list ipoe-match-type {
            type enumeration {
              enum none;
              enum circuit-id;
              enum derived-id;
              enum dual-stack-remote-id;
              enum encap-tag-range;
              enum ip;
              enum mac;
              enum option60;
              enum remote-id;
              enum sap-id;
              enum service-id;
              enum string;
              enum system-id;
            }
            max-elements 4;
          } //ipoe-match-type

        } //container match-list

        list host {
          key "host-name";
          description
              "Configure a IPOE host";
          leaf host-name {
            type string {
              length "1..32";
            }
          } //host-name

          container acct-policy {
            description
                "Configure an accounting policy for acct-stop on failures";
            leaf acct-policy-name {
              type string {
                length "1..32";
              }
            } //acct-policy-name

            leaf duplicate {
              type string {
              }
            } //duplicate

          } //container acct-policy

          container address {
            description
                "Configure the IP address of this host";
            leaf ip-address {
              type inet:ip-address;
            } //ip-address

            leaf pool {
              type string {
                length "1..32";
              }
            } //pool

            leaf gi-address {
              type boolean;
            } //gi-address

            leaf use-pool-from-client {
              type boolean;
            } //use-pool-from-client

            leaf scope {
              type enumeration {
                enum subnet;
                enum pool;
              }
            } //scope

            leaf secondary-pool {
              type string {
                length "1..32";
              }
            } //secondary-pool

            leaf delimiter {
              type string {
                length "1";
              }
            } //delimiter

          } //container address

          container auth-domain-name {
            description
                "Configure the authentication domain name for this host";
            leaf domain-name {
              type string {
                length "1..32";
              }
            } //domain-name

          } //container auth-domain-name

          container auth-policy {
            description
                "Configure the authentication policy of this host";
            leaf policy-name {
              type string {
                length "1..32";
              }
            } //policy-name

          } //container auth-policy

          container diameter-application-policy {
            description
                "Configure the Diameter application policy";
            leaf name {
              type string;
            } //name

          } //container diameter-application-policy

          container diameter-auth-policy {
            description
                "Configure the Diameter NASREQ application policy to use for authentication";
            leaf name {
              type string;
            } //name

          } //container diameter-auth-policy

          container gi-address {
            description
                "Configure the DHCP gi-address of this host";
            leaf ip-address {
              type inet:ip-address;
            } //ip-address

          } //container gi-address

          container interface {
            description
                "Configure the interface where IPoE sessions are terminated";
            leaf ip-int-name {
              type string {
                length "1..32";
              }
              description
                  "[32 chars max] (must start with a letter)";
            } //ip-int-name

            leaf service-id {
              type string;
              description
                  "Attribute service-id for interface";
            } //service-id

          } //container interface

          container ipv6-address {
            description
                "Configure the IPv6 address of this host";
            leaf ipv6-address {
              type inet:ipv6-address;
              description
                  "ipv6-prefix x:x:x:x:x:x:x:x (eight 16-bit pieces) 
                   x:x:x:x:x:x:d.d.d.d 
                   x [0..FFFF]H 
                   d [0..255]D";
            } //ipv6-address

          } //container ipv6-address

          container ipv6-delegated-prefix {
            description
                "Configure the IPv6 delegated prefix of this host";
            leaf ipv6-prefix-prefix-length {
              type string;
              description
                  "ipv6-prefix x:x:x:x:x:x:x:x (eight 16-bit pieces) 
                   x:x:x:x:x:x:d.d.d.d 
                   x [0..FFFF]H 
                   d [0..255]D 
                   prefix-length [48..64]";
            } //ipv6-prefix-prefix-length

          } //container ipv6-delegated-prefix

          container ipv6-delegated-prefix-length {
            description
                "Configure the delegated prefix length";
            leaf bits {
              type uint32 {
                range "48..64";
              }
            } //bits

          } //container ipv6-delegated-prefix-length

          container ipv6-delegated-prefix-pool {
            description
                "Configure the delegated prefix pool";
            leaf pool-name {
              type string {
                length "1..32";
              }
            } //pool-name

          } //container ipv6-delegated-prefix-pool

          container ipv6-slaac-prefix {
            description
                "Configure the IPv6 slaac prefix of this host";
            leaf ipv6-prefix-prefix-length {
              type string;
              description
                  "ipv6-prefix x:x:x:x:x:x:x:x (eight 16-bit pieces) 
                   x:x:x:x:x:x:d.d.d.d 
                   x [0..FFFF]H 
                   d [0..255]D 
                   prefix-length 64";
            } //ipv6-prefix-prefix-length

          } //container ipv6-slaac-prefix

          container ipv6-slaac-prefix-pool {
            description
                "Configure the IPv6 slaac prefix pool of this host";
            leaf pool {
              type string {
                length "1..32";
              }
            } //pool

          } //container ipv6-slaac-prefix-pool

          container ipv6-wan-address-pool {
            description
                "Configure the WAN address pool";
            leaf pool-name {
              type string {
                length "1..32";
              }
            } //pool-name

          } //container ipv6-wan-address-pool

          container link-address {
            description
                "Configure the DHCP Relay link-address";
            leaf ipv6-address {
              type inet:ipv6-address;
              description
                  "Attribute ipv6-address for link-address";
            } //ipv6-address

          } //container link-address

          container retail-service-id {
            description
                "Configure the retailer service Id";
            leaf service-id {
              type string;
              description
                  "Attribute service-id for retail-service-id";
            } //service-id

          } //container retail-service-id

          container rip-policy {
            description
                "Configure a RIP policy";
            leaf policy-name {
              type string {
                length "1..32";
              }
            } //policy-name

          } //container rip-policy

          container router-advertisement-policy {
            description
                "Configure a IPv6 router advertisement policy";
            leaf policy {
              type string;
            } //policy

          } //container router-advertisement-policy

          container server {
            description
                "Configure the IP address of the DHCP server to relay to";
            leaf ip-address {
              type inet:ip-address;
            } //ip-address

          } //container server

          container server6 {
            description
                "Configure the IPv6 address of the DHCP server";
            leaf ipv6-address {
              type inet:ipv6-address;
              description
                  "Attribute ipv6-address for server6";
            } //ipv6-address

          } //container server6

          leaf shutdown {
            type boolean;
            description
                "Administratively enable/disable this IPOE host";
          }

          container host-identification {
            description
                "Configure host identification parameters";
            container circuit-id {
              description
                  "Configure the circuit id of this host";
              leaf string {
                type string {
                  length "1..127";
                }
              } //string

              leaf hex {
                type string {
                }
                description
                    "[0x0..0xFFFFFFFF...(max 254 hex nibbles)]";
              } //hex

            } //container circuit-id

            container derived-id {
              description
                  "Configure the host ID to be derived by a python script from DHCP packets 
                   during a DHCP transaction";
              leaf derived-id-string {
                type string {
                  length "1..255";
                }
              } //derived-id-string

            } //container derived-id

            container encap-tag-range {
              description
                  "Configure the SAP encap range tags for this host";
              leaf type {
                type enumeration {
                  enum atm;
                  enum vlan;
                }
              } //type

              leaf start-tag {
                type string {
                  length "1..9";
                }
                description
                    "Attribute start-tag for encap-tag-range";
              } //start-tag

              leaf end-tag {
                type string {
                  length "1..9";
                }
                description
                    "Attribute end-tag for encap-tag-range";
              } //end-tag

            } //container encap-tag-range

            container ip-prefix {
              description
                  "Configure the IP prefix";
              leaf ip-prefix-ip-prefix-length {
                type string {
                  length "1..64";
                }
                description
                    "Attribute ip-prefix/ip-prefix-length for ip-prefix";
              } //ip-prefix-ip-prefix-length

            } //container ip-prefix

            container mac {
              description
                  "Configure the MAC address of this host";
              leaf ieee-address {
                type string;
                description
                    "xx:xx:xx:xx:xx:xx or xx-xx-xx-xx-xx-xx (cannot be all zeros)";
              } //ieee-address

            } //container mac

            container option60 {
              description
                  "Configure the option 60 of this host";
              leaf hex {
                type string {
                  length "1..66";
                }
                description
                    "[0x0..0xFFFFFFFF...(max 64 hex nibbles)]";
              } //hex

              leaf string {
                type string {
                  length "1..32";
                }
              } //string

            } //container option60

            container remote-id {
              description
                  "Configure the remote id of this host";
              leaf string {
                type string {
                  length "1..255";
                }
              } //string

              leaf hex {
                type string {
                  length "1..512";
                }
                description
                    "[0x0..0xFFFFFFFF...(max 510 hex nibbles)]";
              } //hex

            } //container remote-id

            container sap-id {
              description
                  "Configure the SAP id of this host";
              leaf sap-id {
                type string {
                  length "1..255";
                }
              } //sap-id

            } //container sap-id

            container service-id {
              description
                  "Configure the service id of this host";
              leaf service-id {
                type string;
                description
                    "Attribute service-id for service-id";
              } //service-id

            } //container service-id

            container string {
              description
                  "Configure the VSO string of this host";
              leaf string {
                type string {
                  length "1..255";
                }
              } //string

            } //container string

            container system-id {
              description
                  "Configure the system id of this host";
              leaf system-id {
                type string {
                  length "1..255";
                }
              } //system-id

            } //container system-id

          } //container host-identification

          container identification-strings {
            description
                "Configure identification strings";
            leaf option-number {
              type uint32 {
                range "1..254";
              }
              description
                  "[1..254] - default 254";
            } //option-number

            container ancp-string {
              description
                  "Configure the ANCP string";
              leaf ancp-string {
                type string {
                  length "1..63";
                }
              } //ancp-string

            } //container ancp-string

            container app-profile-string {
              description
                  "Configure the application profile string";
              leaf app-profile-string {
                type string {
                  length "1..16";
                }
              } //app-profile-string

            } //container app-profile-string

            container category-map-name {
              description
                  "Configure the category map name";
              leaf category-map-name {
                type string {
                  length "1..32";
                }
              } //category-map-name

            } //container category-map-name

            container inter-dest-id {
              description
                  "Configure the intermediate destination id";
              leaf intermediate-destination-id {
                type string {
                  length "1..32";
                }
              } //intermediate-destination-id

            } //container inter-dest-id

            container sla-profile-string {
              description
                  "Configure the SLA profile string";
              leaf sla-profile-string {
                type string {
                  length "1..16";
                }
              } //sla-profile-string

            } //container sla-profile-string

            container spi-sharing-group-id {
              description
                  "The group identifier for SLA Profile Instance sharing per group";
              leaf group-id {
                type uint32 {
                  range "0..65535";
                }
              } //group-id

            } //container spi-sharing-group-id

            container sub-profile-string {
              description
                  "Configure the sub-profile string";
              leaf sub-profile-string {
                type string {
                  length "1..16";
                }
              } //sub-profile-string

            } //container sub-profile-string

            container subscriber-id {
              description
                  "Configure the subscriber-id";
              leaf sub-ident-string {
                type string {
                  length "1..32";
                }
              } //sub-ident-string

            } //container subscriber-id

          } //container identification-strings

          container ipv6-lease-times {
            presence
                "Configure the lease times for DHCPv6";
            container preferred-lifetime {
              description
                  "Configure the time a lease remains preferred";
              leaf days {
                type uint32 {
                  range "0..3650";
                }
              } //days

              leaf hrs {
                type uint32 {
                  range "0..23";
                }
              } //hrs

              leaf min {
                type uint32 {
                  range "0..59";
                }
              } //min

              leaf sec {
                type uint32 {
                  range "0..59";
                }
              } //sec

              leaf infinite {
                type boolean;
              } //infinite

            } //container preferred-lifetime

            container rebind-timer {
              description
                  "Configure the rebind timer (T2)";
              leaf days {
                type uint32 {
                  range "0..14";
                }
              } //days

              leaf hrs {
                type uint32 {
                  range "0..23";
                }
              } //hrs

              leaf min {
                type uint32 {
                  range "0..59";
                }
              } //min

              leaf sec {
                type uint32 {
                  range "0..59";
                }
              } //sec

            } //container rebind-timer

            container renew-timer {
              description
                  "Configure the renew timer (T1)";
              leaf days {
                type uint32 {
                  range "0..7";
                }
              } //days

              leaf hrs {
                type uint32 {
                  range "0..23";
                }
              } //hrs

              leaf min {
                type uint32 {
                  range "0..59";
                }
              } //min

              leaf sec {
                type uint32 {
                  range "0..59";
                }
              } //sec

            } //container renew-timer

            container valid-lifetime {
              description
                  "Configure the time a lease remains valid";
              leaf days {
                type uint32 {
                  range "0..3650";
                }
              } //days

              leaf hrs {
                type uint32 {
                  range "0..23";
                }
              } //hrs

              leaf min {
                type uint32 {
                  range "0..59";
                }
              } //min

              leaf sec {
                type uint32 {
                  range "0..59";
                }
              } //sec

              leaf infinite {
                type boolean;
              } //infinite

            } //container valid-lifetime

          } //container ipv6-lease-times

          container match-radius-proxy-cache {
            description
                "Configure RADIUS Proxy cache match parameters";
            container fail-action {
              description
                  "Configure what to do when no match is found";
              leaf fail-action-id {
                type enumeration {
                  enum continue;
                  enum drop;
                }
              } //fail-action-id

            } //container fail-action

            container mac-format {
              description
                  "Configure the expected MAC address format";
              leaf mac-format {
                type string {
                  length "1..7";
                }
                description
                    "(only when match is equal to mac) 
                     like ab: for 00:0c:f1:99:85:b8 
                     or XY- for 00-0C-F1-99-85-B8 
                     or mmmm. for 0002.03aa.abff 
                     or xx for 000cf19985b8";
              } //mac-format

            } //container mac-format

            container match {
              description
                  "Configure how to find a matching entry in the cache";
              leaf match-id {
                type enumeration {
                  enum circuit-id;
                  enum mac;
                  enum remote-id;
                }
              } //match-id

              leaf option {
                type uint8 {
                  range "1..254";
                }
              } //option

              leaf option6 {
                type uint32 {
                  range "1..65535";
                }
              } //option6

            } //container match

            container server {
              description
                  "Specify the RADIUS Proxy server";
              leaf service {
                type string;
                description
                    "Attribute service-id for server";
              } //service

              leaf name {
                type string {
                  length "1..32";
                }
              } //name

            } //container server

          } //container match-radius-proxy-cache

          container mld-parameters {
            description
                "Configure Multicast Listener Discovery (MLD)";
            list import {
              key "policy-name";
              description
                  "Configure an MLD import policy for this host";
              leaf policy-name {
                type string {
                  length "1..32";
                }
              } //policy-name

            } //list import

          } //container mld-parameters

          container msap-defaults {
            description
                "Configure MSAP authentication defaults";
            container group-interface {
              description
                  "Configure the group interface";
              leaf ip-int-name {
                type string {
                  length "1..32";
                }
              } //ip-int-name

              leaf prefix {
                type enumeration {
                  enum port-id;
                }
              } //prefix

              leaf suffix {
                type enumeration {
                  enum port-id;
                }
              } //suffix

            } //container group-interface

            container policy {
              description
                  "Configure the MSAP policy";
              leaf msap-policy-name {
                type string {
                  length "1..32";
                }
                description
                    "Managed SAP policy name";
              } //msap-policy-name

            } //container policy

            container service {
              description
                  "Configure the service";
              leaf service-id {
                type string;
                description
                    "Attribute service-id for service";
              } //service-id

            } //container service

          } //container msap-defaults

          container options {
            description
                "Configure DHCP options";
            list custom-option {
              key "option-number";
              description
                  "Configure a IPOE option";
              leaf option-number {
                type int32 {
                  range "1..254";
                }
              } //option-number

              leaf-list address {
                type inet:ip-address;
                max-elements 4;
              } //address

              leaf string {
                type string {
                  length "1..127";
                }
              } //string

              leaf hex {
                type string {
                }
                description
                    "[0x0..0xFFFFFFFF...(max 254 hex nibbles)]";
              } //hex

            } //list custom-option

            container default-router {
              description
                  "Configure the default router";
              leaf-list ip-address {
                type inet:ip-address;
                max-elements 4;
              } //ip-address

            } //container default-router

            container dns-server {
              description
                  "Configure the DNS server";
              leaf-list ip-address {
                type inet:ip-address;
                max-elements 4;
              } //ip-address

            } //container dns-server

            container domain-name {
              description
                  "Configure the domain name";
              leaf domain-name {
                type string {
                  length "1..127";
                }
              } //domain-name

            } //container domain-name

            container lease-rebind-time {
              description
                  "Configure the lease rebind time";
              leaf days {
                type int32 {
                  range "0..3650";
                }
              } //days

              leaf hrs {
                type int32 {
                  range "0..23";
                }
              } //hrs

              leaf min {
                type int32 {
                  range "0..59";
                }
              } //min

              leaf sec {
                type int32 {
                  range "0..59";
                }
              } //sec

            } //container lease-rebind-time

            container lease-renew-time {
              description
                  "Configure the lease renew time";
              leaf days {
                type int32 {
                  range "0..3650";
                }
              } //days

              leaf hrs {
                type int32 {
                  range "0..23";
                }
              } //hrs

              leaf min {
                type int32 {
                  range "0..59";
                }
              } //min

              leaf sec {
                type int32 {
                  range "0..59";
                }
              } //sec

            } //container lease-renew-time

            container lease-time {
              description
                  "Configure the lease time";
              leaf days {
                type int32 {
                  range "0..3650";
                }
              } //days

              leaf hrs {
                type int32 {
                  range "0..23";
                }
              } //hrs

              leaf min {
                type int32 {
                  range "0..59";
                }
              } //min

              leaf sec {
                type int32 {
                  range "0..59";
                }
              } //sec

            } //container lease-time

            container netbios-name-server {
              description
                  "Configure the netbios name server";
              leaf-list ip-address {
                type inet:ip-address;
                max-elements 4;
              } //ip-address

            } //container netbios-name-server

            container netbios-node-type {
              description
                  "Configure the netbios node type";
              leaf netbios-node-type {
                type string {
                  length "1";
                }
                description
                    "B|P|M|H";
              } //netbios-node-type

            } //container netbios-node-type

            container subnet-mask {
              description
                  "Configure the subnet mask";
              leaf ip-address {
                type inet:ip-address;
              } //ip-address

            } //container subnet-mask

          } //container options

          container options6 {
            description
                "Configure DHCP options";
            container dns-server {
              description
                  "Configure the DNS server";
              leaf-list ipv6-address {
                type inet:ipv6-address;
                max-elements 4;
                description
                    "Attribute ipv6-address for dns-server";
              } //ipv6-address

            } //container dns-server

          } //container options6

          container to-client-options {
            description
                "Configure DHCP options to send to the client";
            container ipv4 {
              description
                  "Configure DHCP options to send to the client";
              list option {
                key "option-number";
                description
                    "Configure a DHCP option to send to the client";
                leaf option-number {
                  type int32 {
                    range "1..254";
                  }
                } //option-number

                leaf-list address {
                  type inet:ip-address;
                  max-elements 4;
                } //address

                leaf string {
                  type string {
                    length "1..127";
                  }
                } //string

                leaf hex {
                  type string {
                  }
                  description
                      "[0x0..0xFFFFFFFF...(max 254 hex nibbles)]";
                } //hex

              } //list option

            } //container ipv4

            container ipv6 {
              description
                  "Configure a DHCP6 option to send to the client";
              list option {
                key "option-number";
                description
                    "Configure a DHCP6 option to send to the client";
                leaf option-number {
                  type int32 {
                    range "1..65535";
                  }
                } //option-number

                leaf-list address {
                  type inet:ipv6-address;
                  max-elements 4;
                  description
                      "Attribute ipv6-address for option";
                } //address

                leaf string {
                  type string {
                    length "1..127";
                  }
                } //string

                leaf hex {
                  type string {
                  }
                  description
                      "[0x0..0xFFFFFFFF...(max 254 hex nibbles)]";
                } //hex

                leaf domain {
                  type string {
                    length "1..127";
                  }
                  description
                      "domain name as in RFC 1035 section 3.1";
                } //domain

              } //list option

            } //container ipv6

          } //container to-client-options

          container to-server-options {
            description
                "Configure DHCP options to send to the server";
            container ipv6 {
              description
                  "Configure a DHCP6 option to send to the server";
              list option {
                key "option-number";
                description
                    "Configure a DHCP6 option to send to the server";
                leaf option-number {
                  type int32 {
                    range "1..65535";
                  }
                } //option-number

                leaf-list address {
                  type inet:ipv6-address;
                  max-elements 4;
                  description
                      "Attribute ipv6-address for option";
                } //address

                leaf string {
                  type string {
                    length "1..127";
                  }
                } //string

                leaf hex {
                  type string {
                  }
                  description
                      "[0x0..0xFFFFFFFF...(max 254 hex nibbles)]";
                } //hex

                leaf domain {
                  type string {
                    length "1..127";
                  }
                  description
                      "domain name as in RFC 1035 section 3.1";
                } //domain

              } //list option

            } //container ipv6

          } //container to-server-options

          container wpp {
            description
                "Configure Web Portal Protocol parameters";
            container initial-app-profile {
              description
                  "Configure the initial application profile";
              leaf app-profile-name {
                type string {
                  length "1..32";
                }
              } //app-profile-name

            } //container initial-app-profile

            container initial-sla-profile {
              description
                  "Configure the initial SLA profile";
              leaf sla-profile-name {
                type string {
                  length "1..32";
                }
              } //sla-profile-name

            } //container initial-sla-profile

            container initial-sub-profile {
              description
                  "Configure the initial subscriber profile";
              leaf sub-profile-name {
                type string {
                  length "1..32";
                }
              } //sub-profile-name

            } //container initial-sub-profile

            container portal {
              description
                  "Configure the WPP portal for this host";
              leaf router {
                type string {
                  length "1..32";
                }
                default "Base";
                description
                    "Attribute router-instance for portal";
              } //router

              leaf name {
                type string;
              } //name

            } //container portal

            container portal-group {
              description
                  "Configure the WPP portal group for this host";
              leaf portal-group-name {
                type string;
              } //portal-group-name

            } //container portal-group

            container restore-disconnected {
              description
                  "Restore initial profiles after the host has disconnected";
              leaf restore-disconnected-id {
                type enumeration {
                  enum restore;
                  enum no-restore;
                }
              } //restore-disconnected-id

            } //container restore-disconnected

          } //container wpp

        } //list host

      } //container ipoe

      container ppp {
        description
            "Configure PPP hosts";
        list mask {
          key "type";
          description
              "Configure the mask";
          leaf type {
            type enumeration {
              enum none;
              enum circuit-id;
              enum mac;
              enum remote-id;
              enum sap-id;
              enum service-name;
              enum username;
            }
            description
                "Attribute ppp-match-type for mask";
          } //type

          leaf prefix-string {
            type string {
              length "1..127";
            }
            description
                "[127 chars max] ('*' is wildcard)";
          } //prefix-string

          leaf prefix-length {
            type uint32 {
              range "1..127";
            }
          } //prefix-length

          leaf suffix-string {
            type string {
              length "1..127";
            }
            description
                "[127 chars max] ('*' is wildcard)";
          } //suffix-string

          leaf suffix-length {
            type uint32 {
              range "1..127";
            }
          } //suffix-length

        } //list mask

        container match-list {
          description
              "Configure the PPP host match criteria";
          leaf-list ppp-match-type {
            type enumeration {
              enum none;
              enum circuit-id;
              enum derived-id;
              enum encap-tag-range;
              enum mac;
              enum remote-id;
              enum sap-id;
              enum service-name;
              enum username;
            }
            max-elements 3;
            description
                "Attribute ppp-match-type for match-list";
          } //ppp-match-type

        } //container match-list

        list host {
          key "host-name";
          description
              "Configure a PPP host";
          leaf host-name {
            type string {
              length "1..32";
            }
          } //host-name

          container acct-policy {
            description
                "Configure an accounting policy for acct-stop on failures";
            leaf acct-policy-name {
              type string {
                length "1..32";
              }
            } //acct-policy-name

            leaf duplicate {
              type string {
                length "1..32";
              }
            } //duplicate

          } //container acct-policy

          container address {
            description
                "Configure the IP address of this host";
            leaf ip-address-prefix-length {
              type string;
              description
                  "a.b.c.d 
                   prefix-length [1..32]";
            } //ip-address-prefix-length

            leaf pool {
              type string {
                length "1..32";
              }
            } //pool

            leaf gi-address {
              type boolean;
            } //gi-address

            leaf use-pool-from-client {
              type boolean;
            } //use-pool-from-client

            leaf scope {
              type enumeration {
                enum subnet;
                enum pool;
              }
            } //scope

            leaf secondary-pool {
              type string {
                length "1..32";
              }
            } //secondary-pool

            leaf delimiter {
              type string {
                length "1";
              }
            } //delimiter

          } //container address

          container auth-policy {
            description
                "Configure the authentication policy of this host";
            leaf policy-name {
              type string {
                length "1..32";
              }
            } //policy-name

          } //container auth-policy

          container diameter-application-policy {
            description
                "Configure the Diameter application policy";
            leaf policy-name {
              type string;
            } //policy-name

          } //container diameter-application-policy

          container diameter-auth-policy {
            description
                "Configure the Diameter NASREQ application policy to use for authentication";
            leaf name {
              type string;
            } //name

          } //container diameter-auth-policy

          leaf force-ipv6cp {
            type boolean;
            description
                "forces ipv6 control protocol";
          }

          leaf ignore-df-bit {
            type boolean;
            description
                "Fragment frames if necessary, even if they have the Don't Fragment (DF) bit 
                 set in the IPv4 header";
          }

          container interface {
            description
                "Configure the interface where PPP sessions are terminated";
            leaf ip-int-name {
              type string {
                length "1..32";
              }
              description
                  "[32 chars max] (must start with a letter)";
            } //ip-int-name

            leaf service-id {
              type string;
              description
                  "Attribute service-id for interface";
            } //service-id

          } //container interface

          container ipv6-address {
            description
                "Configure the IPv6 address of this host";
            leaf ipv6-address {
              type inet:ipv6-address;
              description
                  "ipv6-prefix x:x:x:x:x:x:x:x (eight 16-bit pieces) 
                   x:x:x:x:x:x:d.d.d.d 
                   x [0..FFFF]H 
                   d [0..255]D";
            } //ipv6-address

          } //container ipv6-address

          container ipv6-delegated-prefix {
            description
                "Configure the IPv6 delegated prefix of this host";
            leaf ipv6-prefix-prefix-length {
              type string;
              description
                  "ipv6-prefix x:x:x:x:x:x:x:x (eight 16-bit pieces) 
                   x:x:x:x:x:x:d.d.d.d 
                   x [0..FFFF]H 
                   d [0..255]D 
                   prefix-length [48..64]";
            } //ipv6-prefix-prefix-length

          } //container ipv6-delegated-prefix

          container ipv6-delegated-prefix-length {
            description
                "Configure the delegated prefix length";
            leaf bits {
              type uint32 {
                range "48..64";
              }
            } //bits

          } //container ipv6-delegated-prefix-length

          container ipv6-delegated-prefix-pool {
            description
                "Configure the delegated prefix pool";
            leaf pool-name {
              type string {
                length "1..32";
              }
            } //pool-name

          } //container ipv6-delegated-prefix-pool

          container ipv6-slaac-prefix {
            description
                "Configure the IPv6 slaac prefix of this host";
            leaf ipv6-prefix-prefix-length {
              type string;
              description
                  "ipv6-prefix x:x:x:x:x:x:x:x (eight 16-bit pieces) 
                   x:x:x:x:x:x:d.d.d.d 
                   x [0..FFFF]H 
                   d [0..255]D 
                   prefix-length 64";
            } //ipv6-prefix-prefix-length

          } //container ipv6-slaac-prefix

          container ipv6-slaac-prefix-pool {
            description
                "Configure the IPv6 slaac prefix pool of this host";
            leaf pool {
              type string {
                length "1..32";
              }
            } //pool

          } //container ipv6-slaac-prefix-pool

          container ipv6-wan-address-pool {
            description
                "Configure the WAN address pool";
            leaf pool-name {
              type string {
                length "1..32";
              }
            } //pool-name

          } //container ipv6-wan-address-pool

          container padi-auth-policy {
            description
                "Configure the policy to use for PADI authentication";
            leaf policy {
              type string;
            } //policy

          } //container padi-auth-policy

          container pado-delay {
            description
                "Configure the delay timeout before sending a PADO";
            leaf deci-seconds {
              type uint32 {
                range "1..30";
              }
            } //deci-seconds

          } //container pado-delay

          container password {
            description
                "Configure the password";
            leaf ignore {
              type boolean;
            } //ignore

            leaf pap {
              type string {
                length "1..500";
              }
              description
                  "password - [64 chars max] 
                   hash-key 
                   hash2-key 
                   custom-key";
            } //pap

            leaf chap {
              type string {
                length "1..500";
              }
            } //chap

            leaf hash-hash2-custom {
              type enumeration {
                enum hash;
                enum hash2;
                enum custom;
              }
              description
                  "keywords - specify hashing scheme";
            } //hash-hash2-custom

          } //container password

          container pre-auth-policy {
            description
                "Configure the pre-authentication policy of this host";
            leaf policy-name {
              type string;
            } //policy-name

          } //container pre-auth-policy

          container retail-service-id {
            description
                "Configure the retailer service Id";
            leaf service-id {
              type string;
              description
                  "Attribute service-id for retail-service-id";
            } //service-id

          } //container retail-service-id

          container rip-policy {
            description
                "Configure a RIP policy";
            leaf policy-name {
              type string {
                length "1..32";
              }
            } //policy-name

          } //container rip-policy

          container router-advertisement-policy {
            description
                "Configure a IPv6 router advertisement policy";
            leaf policy {
              type string;
            } //policy

          } //container router-advertisement-policy

          leaf shutdown {
            type boolean;
            description
                "Administratively enable/disable this PPPoE host";
          }

          container steering-profile {
            description
                "Configure a steering profile";
            leaf steering-profile {
              type string {
                length "1..32";
              }
            } //steering-profile

          } //container steering-profile

          container user-db {
            description
                "Configure the local user DB to use for PPP PAP/CHAP authentication";
            leaf name {
              type string;
            } //name

          } //container user-db

          container access-loop-encapsulation {
            presence
                "Configure access loop encapsulation parameters for this host";
            container encap-offset {
              description
                  "Configure the egress encapsulation offset";
              leaf type {
                type enumeration {
                  enum pppoa-llc;
                  enum pppoa-null;
                  enum pppoeoa-llc;
                  enum pppoeoa-llc-fcs;
                  enum pppoeoa-llc-tagged;
                  enum pppoeoa-llc-tagged-fcs;
                  enum pppoeoa-null;
                  enum pppoeoa-null-fcs;
                  enum pppoeoa-null-tagged;
                  enum pppoeoa-null-tagged-fcs;
                  enum ipoa-llc;
                  enum ipoa-null;
                  enum ipoeoa-llc;
                  enum ipoeoa-llc-fcs;
                  enum ipoeoa-llc-tagged;
                  enum ipoeoa-llc-tagged-fcs;
                  enum ipoeoa-null;
                  enum ipoeoa-null-fcs;
                  enum ipoeoa-null-tagged;
                  enum ipoeoa-null-tagged-fcs;
                  enum pppoe;
                  enum pppoe-tagged;
                  enum ipoe;
                  enum ipoe-tagged;
                }
              } //type

            } //container encap-offset

            container rate-down {
              description
                  "Configure the last mile link downstream rate in the access loop";
              leaf rate {
                type uint32 {
                  range "1..100000";
                }
                description
                    "[1..100000] kbps";
              } //rate

            } //container rate-down

          } //container access-loop-encapsulation

          container access-loop-information {
            description
                "Configure access loop information";
            container circuit-id {
              description
                  "Configure the Circuit ID to substitute for the PPPoE Intermediate Agent 
                   Circuit ID TAG in case it is not available";
              leaf string {
                type string {
                  length "1..63";
                }
              } //string

              leaf sap-id {
                type boolean;
              } //sap-id

            } //container circuit-id

            container remote-id {
              description
                  "Configure the Remote ID to substitute for the PPPoE Intermediate Agent Remote 
                   ID TAG in case it is not available";
              leaf string {
                type string {
                  length "1..63";
                }
              } //string

              leaf mac {
                type boolean;
              } //mac

            } //container remote-id

          } //container access-loop-information

          container host-identification {
            description
                "Configure host identification parameters";
            container circuit-id {
              description
                  "Configure the circuit id of this host";
              leaf string {
                type string {
                  length "1..127";
                }
              } //string

              leaf hex {
                type string {
                }
                description
                    "[0x0..0xFFFFFFFF...(max 254 hex nibbles)]";
              } //hex

            } //container circuit-id

            container derived-id {
              description
                  "Configure the host ID to be derived by a python script from DHCP packets 
                   during a DHCP transaction";
              leaf derived-id-string {
                type string {
                  length "1..255";
                }
              } //derived-id-string

            } //container derived-id

            container encap-tag-range {
              description
                  "Configure the SAP encap range tags for this host";
              leaf type {
                type enumeration {
                  enum atm;
                  enum vlan;
                }
              } //type

              leaf start-tag {
                type string {
                  length "1..9";
                }
                description
                    "Attribute start-tag for encap-tag-range";
              } //start-tag

              leaf end-tag {
                type string {
                  length "1..9";
                }
                description
                    "Attribute end-tag for encap-tag-range";
              } //end-tag

            } //container encap-tag-range

            container mac {
              description
                  "Configure the MAC address of this host";
              leaf ieee-address {
                type string;
                description
                    "xx:xx:xx:xx:xx:xx or xx-xx-xx-xx-xx-xx (cannot be all zeros)";
              } //ieee-address

            } //container mac

            container remote-id {
              description
                  "Configure the remote id of this host";
              leaf string {
                type string {
                  length "1..255";
                }
              } //string

              leaf hex {
                type string {
                  length "1..512";
                }
                description
                    "[0x0..0xFFFFFFFF...(max 510 hex nibbles)]";
              } //hex

            } //container remote-id

            container sap-id {
              description
                  "Configure the SAP identifier of this host";
              leaf sap-id {
                type string {
                  length "1..255";
                }
              } //sap-id

            } //container sap-id

            container service-name {
              description
                  "Configure the service name of this host";
              leaf service-name {
                type string {
                  length "1..255";
                }
              } //service-name

            } //container service-name

            container username {
              description
                  "Configure the user name of this host";
              leaf user-name {
                type string {
                  length "1..253";
                }
              } //user-name

              leaf domain-only {
                type boolean;
              } //domain-only

              leaf no-domain {
                type boolean;
              } //no-domain

            } //container username

          } //container host-identification

          container identification-strings {
            description
                "Configure identification strings";
            leaf option-number {
              type uint32 {
                range "1..254";
              }
              description
                  "[1..254] - default 254";
            } //option-number

            container ancp-string {
              description
                  "Configure the ANCP string";
              leaf ancp-string {
                type string {
                  length "1..63";
                }
              } //ancp-string

            } //container ancp-string

            container app-profile-string {
              description
                  "Configure the application profile string";
              leaf app-profile-string {
                type string {
                  length "1..16";
                }
              } //app-profile-string

            } //container app-profile-string

            container category-map-name {
              description
                  "Configure the category map name";
              leaf category-map-name {
                type string {
                  length "1..32";
                }
              } //category-map-name

            } //container category-map-name

            container inter-dest-id {
              description
                  "Configure the intermediate destination id";
              leaf intermediate-destination-id {
                type string {
                  length "1..32";
                }
              } //intermediate-destination-id

            } //container inter-dest-id

            container sla-profile-string {
              description
                  "Configure the SLA profile string";
              leaf sla-profile-string {
                type string {
                  length "1..16";
                }
              } //sla-profile-string

            } //container sla-profile-string

            container spi-sharing-group-id {
              description
                  "The group identifier for SLA Profile Instance sharing per group";
              leaf group-id {
                type uint32 {
                  range "0..65535";
                }
              } //group-id

            } //container spi-sharing-group-id

            container sub-profile-string {
              description
                  "Configure the sub-profile string";
              leaf sub-profile-string {
                type string {
                  length "1..16";
                }
              } //sub-profile-string

            } //container sub-profile-string

            container subscriber-id {
              description
                  "Configure the subscriber-id";
              leaf sub-ident-string {
                type string {
                  length "1..32";
                }
              } //sub-ident-string

            } //container subscriber-id

          } //container identification-strings

          container ipv6-lease-times {
            presence
                "Configure the lease times for DHCPv6";
            container preferred-lifetime {
              description
                  "Configure the time a lease remains preferred";
              leaf days {
                type uint32 {
                  range "0..3650";
                }
              } //days

              leaf hrs {
                type uint32 {
                  range "0..23";
                }
              } //hrs

              leaf min {
                type uint32 {
                  range "0..59";
                }
              } //min

              leaf sec {
                type uint32 {
                  range "0..59";
                }
              } //sec

              leaf infinite {
                type boolean;
              } //infinite

            } //container preferred-lifetime

            container rebind-timer {
              description
                  "Configure the rebind timer (T2)";
              leaf days {
                type uint32 {
                  range "0..14";
                }
              } //days

              leaf hrs {
                type uint32 {
                  range "0..23";
                }
              } //hrs

              leaf min {
                type uint32 {
                  range "0..59";
                }
              } //min

              leaf sec {
                type uint32 {
                  range "0..59";
                }
              } //sec

            } //container rebind-timer

            container renew-timer {
              description
                  "Configure the renew timer (T1)";
              leaf days {
                type uint32 {
                  range "0..7";
                }
              } //days

              leaf hrs {
                type uint32 {
                  range "0..23";
                }
              } //hrs

              leaf min {
                type uint32 {
                  range "0..59";
                }
              } //min

              leaf sec {
                type uint32 {
                  range "0..59";
                }
              } //sec

            } //container renew-timer

            container valid-lifetime {
              description
                  "Configure the time a lease remains valid";
              leaf days {
                type uint32 {
                  range "0..3650";
                }
              } //days

              leaf hrs {
                type uint32 {
                  range "0..23";
                }
              } //hrs

              leaf min {
                type uint32 {
                  range "0..59";
                }
              } //min

              leaf sec {
                type uint32 {
                  range "0..59";
                }
              } //sec

              leaf infinite {
                type boolean;
              } //infinite

            } //container valid-lifetime

          } //container ipv6-lease-times

          container l2tp {
            description
                "Configure L2TP for this host";
            container group {
              description
                  "Configure the L2TP LAC tunnel group";
              leaf tunnel-group-name {
                type string {
                  length "1..63";
                }
              } //tunnel-group-name

              leaf service-id {
                type string;
                description
                    "Attribute service-id for group";
              } //service-id

            } //container group

          } //container l2tp

          container mld-parameters {
            description
                "Configure Multicast Listener Discovery (MLD)";
            list import {
              key "policy-name";
              description
                  "Configure an MLD import policy for this host";
              leaf policy-name {
                type string {
                  length "1..32";
                }
              } //policy-name

            } //list import

          } //container mld-parameters

          container msap-defaults {
            description
                "Configure MSAP authentication defaults";
            container group-interface {
              description
                  "Configure the group interface";
              leaf ip-int-name {
                type string {
                  length "1..32";
                }
                description
                    "[32 chars max] (must start with a letter)";
              } //ip-int-name

              leaf prefix {
                type enumeration {
                  enum port-id;
                }
              } //prefix

              leaf suffix {
                type enumeration {
                  enum port-id;
                }
              } //suffix

            } //container group-interface

            container policy {
              description
                  "Configure the MSAP policy";
              leaf msap-policy-name {
                type string {
                  length "1..32";
                }
                description
                    "Managed SAP policy name";
              } //msap-policy-name

            } //container policy

            container service {
              description
                  "Configure the service";
              leaf service-id {
                type string;
                description
                    "Attribute service-id for service";
              } //service-id

            } //container service

          } //container msap-defaults

          container options {
            description
                "Configure DHCP options";
            list custom-option {
              key "option-number";
              description
                  "Configure a IPOE option";
              leaf option-number {
                type uint32 {
                  range "1..254";
                }
              } //option-number

              leaf-list address {
                type inet:ip-address;
                max-elements 4;
              } //address

              leaf string {
                type string {
                  length "1..127";
                }
              } //string

              leaf hex {
                type string {
                }
                description
                    "[0x0..0xFFFFFF...(max 254 hex nibbles)]";
              } //hex

            } //list custom-option

            container dns-server {
              description
                  "Configure the DNS server";
              leaf-list ip-address {
                type inet:ip-address;
                max-elements 4;
              } //ip-address

            } //container dns-server

            container netbios-name-server {
              description
                  "Configure the netbios name server";
              leaf-list ip-address {
                type inet:ip-address;
                max-elements 4;
              } //ip-address

            } //container netbios-name-server

          } //container options

          container options6 {
            description
                "Configure DHCP options";
            container dns-server {
              description
                  "Configure the DNS server";
              leaf-list ipv6-address {
                type inet:ipv6-address;
                max-elements 4;
                description
                    "Attribute ipv6-address for dns-server";
              } //ipv6-address

            } //container dns-server

          } //container options6

          container to-client-options {
            description
                "Configure DHCP options to send to the client";
            container ipv6 {
              description
                  "Configure a DHCP6 option to send to the client";
              list option {
                key "option-number";
                description
                    "Configure a DHCP6 option to send to the client";
                leaf option-number {
                  type int32 {
                    range "1..65535";
                  }
                } //option-number

                leaf-list address {
                  type inet:ipv6-address;
                  max-elements 4;
                  description
                      "Attribute ipv6-address for option";
                } //address

                leaf string {
                  type string {
                    length "1..127";
                  }
                } //string

                leaf hex {
                  type string {
                  }
                  description
                      "[0x0..0xFFFFFFFF...(max 254 hex nibbles)]";
                } //hex

                leaf domain {
                  type string {
                  }
                  description
                      "domain name as in RFC 1035 section 3.1";
                } //domain

              } //list option

            } //container ipv6

          } //container to-client-options

        } //list host

      } //container ppp

    } //list local-user-db

  } //grouping alu-conf-submgmt-ludb-r13

} //module  alu-conf-submgmt-ludb-r13
