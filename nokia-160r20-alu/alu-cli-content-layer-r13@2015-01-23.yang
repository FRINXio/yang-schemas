module alu-cli-content-layer-r13 {
    yang-version 1;

    namespace "urn:alcatel-lucent.com:sros:ns:yang:cli-content-layer-r13";

    prefix cli-content-layer-r13;

    organization
        "Alcatel-Lucent";

    contact
        "Alcatel-Lucent SR OS Support 
        Web: <http://www.alcatel-lucent.com>";

    description
        "Alcatel-Lucent YANG Data model to configure, manage and gather
        operational information on SR OS based routers using a CLI content
        layer format.

        Copyright 2014-2015 Alcatel-Lucent. All rights reserved.
        Reproduction of this document is authorized on the condition
        that the foregoing copyright notice is included.

        This alu-cli-content-layer-r13 YANG module embodies Alcatel-Lucent's
        proprietary intellectual property. Alcatel-Lucent retains
        all title and ownership in the Specification, including any
        revisions.

        Alcatel-Lucent grants all interested parties a non-exclusive
        license to use and distribute an unmodified copy of this
        Specification in connection with management of Alcatel-Lucent
        products, and without fee, provided this copyright notice and
        license appear on all copies.

        This Specification is supplied `as is', and Alcatel-Lucent
        makes no warranty, either express or implied, as to the use,
        operation, condition, or performance of the Specification.";

    revision 2015-01-23;

    // Custom Protocol Operations

    rpc get-config {
      description
        "Retrieve all or part of a specified configuration.";

      input {
        container source {
          description
            "Particular configuration to retrieve.";

          leaf running {
            type empty;
            mandatory true;
            description
              "The running configuration is the config source.";
          }
        } // container source

        container filter {
          description
            "Contains the requested list of CLI configuration branches.";

          container config-format-cli-block {
              description
                  "Indicates that the requested format of the configuration
                  information is a block of CLI text.";
              leaf-list cli-info {
                  type string;
                  description
                    "A whitespace-delimited CLI path (relative to the CLI root
                    configuration branch) to the configuration node at which
                    the output of the info command is requested in order to
                    retrieve configuration information. For example:
                    <cli-info>system login-control</cli-info>";
              }
              leaf-list cli-info-detail {
                  type string;
                  description
                    "A whitespace-delimited CLI path (relative to the CLI root
                    configuration branch) to the configuration node at which
                    the output of the info detail command is requested in order
                    to retrieve detailed configuration information. For example:
                    <cli-info-detail>system login-control</cli-info-detail>";
              }
          }
        } // container filter 
      } // input

      output {
        container data {
          description
            "Copy of the source datastore subset that matched
             the filter criteria (if any).";

          container config-format-cli-block {
            list item {
              choice detail-level {
                case no-detail {
                  leaf cli-info {
                    type string;
                    description
                      "Indicates the CLI path of the configuration node at
                      which the output of the info command was requested.";
                  }
                }
                case detail {
                  leaf cli-info-detail {
                    type string;
                    description
                      "Indicates the CLI path of the configuration node at
                      which the output of the info detail command was
                      requested.";
                  }
                }
              } // choice detail-level
              leaf response {
                type string;
                description
                  "Command response in block CLI text format.";
              }
            }
          }
        } //container data
      } // output
    } // rpc get-config

    rpc edit-config {
      description

        "The <edit-config> operation loads all or part of a specified
         configuration to the specified target configuration.";

      input {
        container target {
          description
            "Particular configuration to edit.";

          leaf running {
            type empty;
            mandatory true;
            description
              "The running configuration is the config target.";
          }
        } // container target

        container config {
          description
            "Inline Config content.";

          leaf config-format-cli-block {
              type string;
              mandatory true;
              description
                  "CLI configuration commands in whitespace-delimited CLI
                  format. The starting branch/context of the request begins
                  with the CLI root context. For example:
                    <config-format-cli-block>
                      configure system time zone EST
                    </config-format-cli-block>";
          }
        } // container config
      } // input
    } //rpc edit-config

    rpc get {
      description
        "Retrieve running configuration and device state information.";

      input {
        container filter {
          description
            "Contains the requested list of CLI show commands.";

          container oper-data-format-cli-block {
            description
              "Indicates that the requested format of the operational data is a
              block of CLI text.";

            leaf-list cli-show {
              type string;
              description
                 "A whitespace-delimited CLI show command (relative to the
                 CLI show branch). For example:
                 <cli-show>
                   router interface &quot;int-1b&quot; detail
                 </cli-show>";
            }
          }
        }
      } // input

      output {
        container data {
          description
            "Copy of the state data that matched the filter criteria (if any).";

          container oper-data-format-cli-block {
            list item {
              leaf cli-show {
                type string;
                description
                  "Indicates the CLI show command for which output was
                  requested.";
              }
              leaf response {
                type string;
                description
                  "Command response in block CLI text format.";
              }
            }
          }
        } // container data
      } // output
    } //rpc get

    rpc cli-action {
      description
        "Request the execution of a CLI admin command.";

      input {
        leaf-list admin {
          type string;
          description
            "A whitespace-delimited CLI admin command (relative to the CLI
            admin branch). For example: <admin>rollback save</admin>.
            The following admin commands are supported:
                rollback save
                rollback revert
                rollback compare
                rollback delete
                rollabck view";
        }
      } // input

      output {
        container data {
          description
            "Result of executing the specified operation.";

        container cli-action {
          list item {
             leaf admin {
                type string;
                description
                  "admin command.";
              }
              leaf response {
                type string;
                description
                  "Command response in block CLI text format.";
              }
            }
          }
        } // data
      } // output
    } //rpc cli-action
}
