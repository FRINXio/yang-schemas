module alu-conf-svc-sdp-r13 {
  yang-version "1";

  namespace "urn:alcatel-lucent.com:sros:ns:yang:conf-svc-sdp-r13";

  prefix "conf-svc-sdp-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure SDPs on SR OS based routers. 
       
       Copyright 2014-2015 Alcatel-Lucent, 2016 Nokia. All rights reserved. 
       Reproduction of this document is authorized on the condition that the 
       foregoing copyright notice is included. 
       
       This alu-conf-svc-sdp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-11-02";

  grouping alu-conf-svc-sdp-r13 {
    list sdp {
      key "sdp-id";
      description
          "Configure SDPs";
      leaf sdp-id {
        type uint32 {
          range "1..32767";
        }
      } //sdp-id

      leaf delivery-type {
        type enumeration {
          enum gre;
          enum mpls;
          enum l2tpv3;
          enum gre-eth-bridged;
        }
        description
            "Attribute delivery-type for sdp";
      } //delivery-type

      container accounting-policy {
        description
            "Configure accounting-policy to be used";
        leaf acct-policy-id {
          type uint64 {
            range "1..99";
          }
        } //acct-policy-id

      } //container accounting-policy

      leaf adv-mtu-override {
        type boolean;
        description
            "Override the advertised VC MTU";
      }

      leaf allow-fragmentation {
        type boolean;
        description
            "Allow GRE encapsulated packets to be sent without setting the DF bit";
      }

      leaf bgp-tunnel {
        type boolean;
        description
            "Enable/disable BGP tunnels";
      }

      container booking-factor {
        description
            "Configure the SDP booking-factor";
        leaf percentage {
          type uint32 {
            range "0..1000";
          }
          description
              "[0..1000] default 100";
        } //percentage

      } //container booking-factor

      leaf collect-stats {
        type boolean;
        description
            "Enable/disable statistics collection";
      }

      list description {
        key "description-string";
        description
            "Description for SDP";
        leaf description-string {
          type string {
            length "1..80";
          }
        } //description-string

      } //list description

      list encryption-keygroup {
        key "direction";
        description
            "Configure the encryption keygroup for the sdp";
        leaf keygroup-id {
          type string;
          description
              "Attribute keygroup-id for encryption-keygroup";
        } //keygroup-id

        leaf direction {
          type enumeration {
            enum inbound;
            enum outbound;
          }
        } //direction

      } //list encryption-keygroup

      container far-end {
        description
            "Configure far-end address";
        leaf ip-address-ipv6-address {
          type string;
        } //ip-address-ipv6-address

        leaf node-id {
          type string {
            length "1..15";
          }
          description
              "a.b.c.d|<1..4294967295>";
        } //node-id

        leaf global-id {
          type uint64 {
            range "1..4294967295";
          }
        } //global-id

      } //container far-end

      leaf ldp {
        type boolean;
        description
            "Enable/disable LDP-signaled LSP's";
      }

      container local-end {
        description
            "Configure local-end address";
        leaf ip-address-ipv6-address {
          type string;
        } //ip-address-ipv6-address

      } //container local-end

      list lsp {
        key "lsp-name";
        description
            "Configure LSP to be used by SDP";
        leaf lsp-name {
          type string;
          description
              "Attribute lsp-name for lsp";
        } //lsp-name

      } //list lsp

      container metric {
        description
            "Configure SDP Metric";
        leaf metric {
          type uint32 {
            range "1..65535";
          }
        } //metric

      } //container metric

      container network-domain {
        description
            "Associate a network-domain";
        leaf network-domain-name {
          type inet:domain-name;
        } //network-domain-name

      } //container network-domain

      list path-mtu {
        key "bytes";
        description
            "Configure path MTU";
        leaf bytes {
          type uint32 {
            range "576..9194";
          }
        } //bytes

      } //list path-mtu

      list pbb-etype {
        key "t0x0600..0xffff";
        description
            "Configure PBB ethertype";
        leaf t0x0600..0xffff {
          type string;
          description
              "[1536..65535] - accepts in decimal or hex";
        } //t0x0600..0xffff

      } //list pbb-etype

      list sdp-group {
        key "group-name";
        description
            "Configure SDP group";
        leaf group-name {
          type string {
            length "1..32";
          }
        } //group-name

      } //list sdp-group

      leaf shutdown {
        type boolean;
        description
            "Administratively enable/disable the SDP";
      }

      container signaling {
        description
            "Configure type of VC label signaling";
        leaf off-tldp-bgp {
          type enumeration {
            enum off;
            enum tldp;
            enum bgp;
          }
          description
              "keywords - specify type of label-signaling";
        } //off-tldp-bgp

      } //container signaling

      container source-bmac-lsb {
        description
            "Configure lsb for Backbone MAC";
        leaf MAC-Lsb {
          type string;
          description
              "[1..65535] or xx-xx or xx:xx";
        } //MAC-Lsb

        leaf control-pw-vc-id {
          type uint32 {
            range "1..4294967295";
          }
        } //control-pw-vc-id

      } //container source-bmac-lsb

      leaf sr-isis {
        type boolean;
        description
            "Configure segment-routing ISIS";
      }

      leaf sr-ospf {
        type boolean;
        description
            "Configure segment routing for OSPF";
      }

      list sr-te-lsp {
        key "lsp-name";
        description
            "Configure segment-routing (traffic-engineered) LSP to be used by SDP";
        leaf lsp-name {
          type string;
          description
              "Attribute lsp-name for sr-te-lsp";
        } //lsp-name

      } //list sr-te-lsp

      list tunnel-far-end {
        key "ip-address-ipv6-address";
        description
            "Configure tunnel-far-end address";
        leaf ip-address-ipv6-address {
          type string;
        } //ip-address-ipv6-address

      } //list tunnel-far-end

      list vlan-vc-etype {
        key "ethernet-type";
        description
            "Configure VLAN VC ethertype";
        leaf ethernet-type {
          type string;
          description
              "[0x0600..0xffff]";
        } //ethernet-type

      } //list vlan-vc-etype

      leaf weighted-ecmp {
        type boolean;
        description
            "Enable/disable weighted ecmp capability when RSVP LSPs are configured";
      }

      container binding {
        description
            "Configure binding information";
        container port {
          description
              "Configure port binding";
          leaf port-id---lag-id {
            type string {
              length "1..17";
            }
            description
                "slot/mda/port or lag-<lag-id>";
          } //port-id---lag-id

        } //container port

        list pw-port {
          key "pw-port-id";
          description
              "Configure pseudo-wire port information";
          leaf pw-port-id {
            type uint64 {
              range "1..32767";
            }
          } //pw-port-id

          leaf vc-id {
            type uint64 {
              range "1..4294967295";
            }
          } //vc-id

          container monitor-oper-group {
            description
                "Configure an Operational-Group to monitor";
            leaf group-name {
              type string;
            } //group-name

          } //container monitor-oper-group

          leaf shutdown {
            type boolean;
            description
                "Enable/Disable pseudo-wire port";
          }

          container vc-type {
            description
                "Configure VC type";
            leaf ether-vlan {
              type enumeration {
                enum ether;
                enum vlan;
              }
            } //ether-vlan

          } //container vc-type

          container vlan-vc-tag {
            description
                "Configure VLAN VC tag";
            leaf vlan-id {
              type uint32 {
                range "0..4094";
              }
            } //vlan-id

          } //container vlan-vc-tag

          container egress {
            description
                "Configure pseudo-wire port egress side parameters";
            container vc-label {
              description
                  "Configure egress VC label";
              leaf egress-vc-label {
                type int32 {
                  range "16..1048575";
                }
              } //egress-vc-label

            } //container vc-label

            container shaper {
              presence
                  "Configure shaper parameters";
              container int-dest-id {
                description
                    "Configure an intermediate destination identifier applicable to esm pw-saps";
                leaf int-dest-id {
                  type string;
                } //int-dest-id

              } //container int-dest-id

              container pw-sap-secondary-shaper {
                description
                    "Configure a default secondary shaper applicable to pw-saps under normal 
                     interfaces";
                leaf pw-sap-sec-shaper-name {
                  type string;
                } //pw-sap-sec-shaper-name

              } //container pw-sap-secondary-shaper

              container vport {
                description
                    "Configure a virtual port applicable to all pw-saps";
                leaf vport-name {
                  type string;
                } //vport-name

              } //container vport

            } //container shaper

          } //container egress

          container ingress {
            description
                "Configure ingress parameters";
            container vc-label {
              description
                  "Configure ingress VC label";
              leaf ingress-vc-label {
                type string;
                description
                    "Attribute ingress-vc-label for vc-label";
              } //ingress-vc-label

            } //container vc-label

          } //container ingress

        } //list pw-port

      } //container binding

      container class-forwarding {
        description
            "Configure class-based forwarding";
        leaf default-lsp {
          type string;
          description
              "Attribute lsp-name for class-forwarding";
        } //default-lsp

        leaf enforce-diffserv-lsp-fc {
          type boolean;
          description
              "Configure validation of support of fc by lsp with RSVP";
        }

        list fc {
          key "fc-id";
          description
              "Configure a forwarding class to LSP mapping";
          leaf fc-id {
            type enumeration {
              enum be;
              enum l2;
              enum af;
              enum l1;
              enum h2;
              enum ef;
              enum h1;
              enum nc;
            }
          } //fc-id

          leaf lsp {
            type string;
            description
                "Attribute lsp-name for fc";
          } //lsp

        } //list fc

        container multicast-lsp {
          description
              "Configure an LSP for all MC traffic";
          leaf lsp-name {
            type string;
            description
                "Attribute lsp-name for multicast-lsp";
          } //lsp-name

        } //container multicast-lsp

        leaf shutdown {
          type boolean;
          description
              "Administratively enable/disable class-based forwarding";
        }

      } //container class-forwarding

      container keep-alive {
        description
            "Configure keep alive parameters";
        list hello-time {
          key "seconds";
          description
              "Configure keep-alive hello time";
          leaf seconds {
            type uint32 {
              range "1..3600";
            }
          } //seconds

        } //list hello-time

        list hold-down-time {
          key "seconds";
          description
              "Configure keep-alive hold down time";
          leaf seconds {
            type uint32 {
              range "0..3600";
            }
          } //seconds

        } //list hold-down-time

        list max-drop-count {
          key "count";
          description
              "Configure keep-alive max-drop-count";
          leaf count {
            type uint32 {
              range "1..5";
            }
          } //count

        } //list max-drop-count

        list message-length {
          key "message-length";
          description
              "Configure keep-alive message-length";
          leaf message-length {
            type uint32 {
              range "40..9198";
            }
          } //message-length

        } //list message-length

        leaf shutdown {
          type boolean;
          description
              "Enable/disable keep-alive";
        }

        container timeout {
          description
              "Configure keep-alive hello timeout";
          leaf timeout {
            type uint32 {
              range "1..10";
            }
          } //timeout

        } //container timeout

      } //container keep-alive

      container mixed-lsp-mode {
        presence
            "Enable/disable Mixed LSP mode";
        container revert-time {
          description
              "Configure the time to wait before reverting to a preferred LSP type";
          leaf revert-time {
            type uint32 {
              range "0..600";
            }
            description
                "[0..600] seconds";
          } //revert-time

          leaf infinite {
            type boolean;
            description
                "keyword - makes sdp non-revertive";
          } //infinite

        } //container revert-time

      } //container mixed-lsp-mode

    } //list sdp

  } //grouping alu-conf-svc-sdp-r13

} //module  alu-conf-svc-sdp-r13
