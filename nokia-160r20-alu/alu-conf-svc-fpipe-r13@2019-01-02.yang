module alu-conf-svc-fpipe-r13 {
  yang-version "1";

  namespace "urn:alcatel-lucent.com:sros:ns:yang:conf-svc-fpipe-r13";

  prefix "conf-svc-fpipe-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure Frame Relay Pipe services on SR OS 
       based routers. 
       
       Copyright 2014-2015 Alcatel-Lucent, 2016 Nokia. All rights reserved. 
       Reproduction of this document is authorized on the condition that the 
       foregoing copyright notice is included. 
       
       This alu-conf-svc-fpipe-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-01-02";

  grouping alu-conf-svc-fpipe-r13 {
    list fpipe {
      key "service-id";
      description
          "Configure Frame Relay Pipe services";
      leaf service-id {
        type string;
        description
            "Attribute service-id for fpipe";
      } //service-id

      leaf customer {
        type uint32 {
          range "1..2147483647";
        }
      } //customer

      leaf vpn {
        type uint32 {
          range "1..2147483647";
        }
      } //vpn

      leaf vc-type {
        type enumeration {
          enum fr-dlci;
        }
        description
            "keyword";
      } //vc-type

      leaf vc-switching {
        type boolean;
        description
            "keyword - create a vc-switching Fpipe";
      } //vc-switching

      leaf name {
        type string;
        description
            "64-char max";
      } //name

      list description {
        key "description-string";
        description
            "Description for the service";
        leaf description-string {
          type string {
            length "1..80";
          }
        } //description-string

      } //list description

      container service-mtu {
        description
            "Configure service MTU";
        leaf octets {
          type uint32 {
            range "1..9194";
          }
        } //octets

      } //container service-mtu

      container service-name {
        status "obsolete";
        description
            "Configure a service name";
        leaf service-name {
          type string;
          description
              "64-char max";
        } //service-name

      } //container service-name

      leaf shutdown {
        type boolean;
        description
            "Administratively enable/disable the service";
      }

      list endpoint {
        key "endpoint-name";
        description
            "Configure a service end-point";
        leaf endpoint-name {
          type string {
            length "1..32";
          }
        } //endpoint-name

        container active-hold-delay {
          description
              "Configure the time to hold the active status";
          leaf active-hold-delay {
            type uint32 {
              range "1..60";
            }
            description
                "[1..60] deci-seconds";
          } //active-hold-delay

        } //container active-hold-delay

        container description {
          description
              "Description for the service end-point";
          leaf description-string {
            type string {
              length "1..80";
            }
          } //description-string

        } //container description

        container revert-time {
          description
              "Configure the time to wait before reverting to primary spoke-sdp";
          leaf revert-time {
            type uint32 {
              range "0..600";
            }
            description
                "[0..600] seconds";
          } //revert-time

          leaf infinite {
            type boolean;
            description
                "keyword - makes endpoint non-revertive";
          } //infinite

        } //container revert-time

      } //list endpoint

      list sap {
        key "sap-id";
        description
            "Provision a SAP";
        leaf sap-id {
          type string;
          description
              "Attribute sap-id for sap";
        } //sap-id

        leaf endpoint {
          type string {
            length "1..32";
          }
        } //endpoint

        leaf no-endpoint {
          type boolean;
          description
              "keyword - used to remove an endpoint association";
        } //no-endpoint

        list accounting-policy {
          key "acct-policy-id";
          description
              "Configure accounting-policy to be used";
          leaf acct-policy-id {
            type uint64 {
              range "1..99";
            }
          } //acct-policy-id

        } //list accounting-policy

        container bandwidth {
          description
              "Configure SAP Bandwidth";
          leaf bandwidth {
            type uint32 {
              range "1..3200000000";
            }
            description
                "[1..3200000000] Kbps";
          } //bandwidth

        } //container bandwidth

        leaf collect-stats {
          type boolean;
          description
              "Enable/disable statistics collection";
        }

        list description {
          key "long-description-string";
          description
              "Description for the SAP";
          leaf long-description-string {
            type string {
              length "1..160";
            }
          } //long-description-string

        } //list description

        container dist-cpu-protection {
          description
              "Assign Distributed CPU protection policy for the SAP";
          leaf policy-name {
            type string;
          } //policy-name

        } //container dist-cpu-protection

        container multi-service-site {
          description
              "Specify the multi-service-site to which this SAP belongs";
          leaf customer-site-name {
            type string {
              length "1..32";
            }
          } //customer-site-name

        } //container multi-service-site

        leaf shutdown {
          type boolean;
          description
              "Administratively enable/disable the SAP";
        }

        container tod-suite {
          status "obsolete";
          description
              "Configure a time-of-day suite for this SAP";
          leaf tod-suite-name {
            type string {
              length "1..32";
            }
          } //tod-suite-name

        } //container tod-suite

        container egress {
          description
              "Configure egress policies";
          container filter {
            description
                "Apply egress filter";
            leaf ip {
              type string;
              description
                  "[1..65535]|<name:64 char max>";
            } //ip

            leaf ipv6 {
              type string;
              description
                  "[1..65535]|<name:64 char max>";
            } //ipv6

          } //container filter

          container policer-control-policy {
            description
                "Specify policer control policy";
            leaf policy-name {
              type string {
                length "1..32";
              }
            } //policy-name

          } //container policer-control-policy

          leaf qinq-mark-top-only {
            type boolean;
            description
                "Mark p-bits on top q-tag only";
          }

          list qos {
            key "policy-id";
            description
                "Apply egress QoS policy";
            leaf policy-id {
              type string;
              description
                  "[1..65535]|<name:64 char max>";
            } //policy-id

          } //list qos

          container scheduler-policy {
            description
                "Specify a scheduler-policy";
            leaf scheduler-policy-name {
              type string {
                length "1..32";
              }
            } //scheduler-policy-name

          } //container scheduler-policy

          container agg-rate {
            presence
                "Configure aggregate rate limit";
            leaf limit-unused-bandwidth {
              type boolean;
              description
                  "Specify whether to enable limit unused bandwidth";
            }

            container rate {
              description
                  "Specify rate limit for agg-rate";
              leaf kilobits-per-second {
                type string;
                description
                    "[1..3200000000|max] Kbps";
              } //kilobits-per-second

            } //container rate

          } //container agg-rate

          container policer-control-override {
            description
                "Configure policer control overrides";
            container max-rate {
              description
                  "Configure Max Rate override in kilobits-per-second";
              leaf max-rate-string {
                type string;
                description
                    "[1..2000000000|max] Kbps";
              } //max-rate-string

            } //container max-rate

            container priority-mbs-thresholds {
              description
                  "Configure priority mbs thresholds overrides";
              container min-thresh-separation {
                description
                    "configure min threshold separation override";
                leaf size {
                  type string;
                  description
                      "[0..16777216 default]";
                } //size

                leaf min-thresh-separation-id {
                  type enumeration {
                    enum bytes;
                    enum kilobytes;
                  }
                } //min-thresh-separation-id

              } //container min-thresh-separation

              list priority {
                key "level";
                description
                    "Configure Priority Levels overrides";
                leaf level {
                  type uint32 {
                    range "1..8";
                  }
                } //level

                container mbs-contribution {
                  description
                      "Configure mbs size override";
                  leaf size {
                    type string;
                    description
                        "[0..16777216 default]";
                  } //size

                  leaf mbs-contribution-id {
                    type enumeration {
                      enum bytes;
                      enum kilobytes;
                    }
                  } //mbs-contribution-id

                } //container mbs-contribution

              } //list priority

            } //container priority-mbs-thresholds

          } //container policer-control-override

          container policer-override {
            presence
                "Configure policer overrides";
            list policer {
              key "policer-id";
              description
                  "Configure overrides for the policer";
              leaf policer-id {
                type uint32 {
                  range "1..63";
                }
              } //policer-id

              container cbs {
                description
                    "Specify Cbs override";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs override";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "Specify packet byte offset";
                leaf add {
                  type uint32 {
                    range "0..31";
                  }
                } //add

                leaf subtract {
                  type string;
                  description
                      "Attribute sub-bytes for packet-byte-offset";
                } //subtract

              } //container packet-byte-offset

              container percent-rate {
                description
                    "Specify percent rates (CIR and PIR) override";
                leaf pir-percent {
                  type string;
                  description
                      "[0.01..100.00]";
                } //pir-percent

                leaf cir {
                  type string;
                  description
                      "[0.00..100.00]";
                } //cir

              } //container percent-rate

              container rate {
                description
                    "Specify rates (CIR and PIR) override";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-profile-cir;
                    enum offered-total-cir;
                    enum offered-total-cir-exceed;
                    enum offered-four-profile-no-cir;
                    enum offered-total-cir-four-profile;
                  }
                } //stat-mode

              } //container stat-mode

            } //list policer

          } //container policer-override

          container queue-override {
            presence
                "Apply queue override";
            list queue {
              key "queue-id";
              description
                  "Configure a queue override";
              leaf queue-id {
                type int32 {
                  range "1..8";
                }
              } //queue-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container avg-frame-overhead {
                description
                    "Specify the average frame overhead";
                leaf percentage {
                  type string;
                  description
                      "[0.00..100.00]";
                } //percentage

              } //container avg-frame-overhead

              container burst-limit {
                description
                    "Specify burst limit";
                leaf size {
                  type string;
                  description
                      "Attribute size for burst-limit";
                } //size

                leaf bytes-kilobytes {
                  type enumeration {
                    enum bytes;
                    enum kilobytes;
                  }
                } //bytes-kilobytes

              } //container burst-limit

              container cbs {
                description
                    "Specify CBS";
                leaf size-in-kbytes {
                  type string;
                  description
                      "Attribute size-in-kbytes for cbs";
                } //size-in-kbytes

              } //container cbs

              container high-prio-only {
                status "obsolete";
                description
                    "Specify high priority only burst size";
                leaf percent {
                  type string;
                  description
                      "[0..100 | default]";
                } //percent

              } //container high-prio-only

              container mbs {
                description
                    "Specify MBS";
                leaf size {
                  type string;
                  description
                      "Attribute size for mbs";
                } //size

                leaf bytes-kilobytes {
                  type enumeration {
                    enum bytes;
                    enum kilobytes;
                  }
                } //bytes-kilobytes

              } //container mbs

              leaf monitor-depth {
                type boolean;
                description
                    "Enable/Disable queue-depth monitoring";
              }

              container parent {
                description
                    "Specify the override weights for the queue within its parental scheduling 
                     context";
                leaf weight {
                  type uint32 {
                    range "0..100";
                  }
                } //weight

                leaf cir-weight {
                  type uint32 {
                    range "0..100";
                  }
                } //cir-weight

              } //container parent

              container percent-rate {
                description
                    "Specify percent rates (CIR and PIR)";
                leaf pir-percent {
                  type string;
                  description
                      "[0.01..100.00]";
                } //pir-percent

                leaf cir {
                  type string;
                  description
                      "[0.00..100.00]";
                } //cir

              } //container percent-rate

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container drop-tail {
                description
                    "Specify drop tail";
                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

            } //list queue

          } //container queue-override

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..3200000000|max] Kbps";
                } //pir-rate

                leaf cir {
                  type string;
                  description
                      "[0..3200000000|sum|max] Kbps";
                } //cir

              } //container rate

            } //list scheduler

          } //container scheduler-override

        } //container egress

        container frame-relay {
          description
              "Configure frame-relay parameters";
          container scheduling-class {
            description
                "Configure frf.12 scheduling class";
            leaf class-id {
              type uint32 {
                range "0..3";
              }
            } //class-id

          } //container scheduling-class

        } //container frame-relay

        container ingress {
          description
              "Configure ingress policies";
          container filter {
            description
                "Apply ingress filter";
            leaf ip {
              type string;
              description
                  "[1..65535]|<name:64 char max>";
            } //ip

            leaf ipv6 {
              type string;
              description
                  "[1..65535]|<name:64 char max>";
            } //ipv6

          } //container filter

          container policer-control-policy {
            description
                "Specify policer control policy";
            leaf policy-name {
              type string {
                length "1..32";
              }
            } //policy-name

          } //container policer-control-policy

          list qos {
            key "policy-id";
            description
                "Apply ingress qos policy";
            leaf policy-id {
              type string;
              description
                  "[1..65535]|<name:64 char max>";
            } //policy-id

            leaf shared-queuing {
              type enumeration {
                enum shared-queuing;
              }
              description
                  "enables shared-queuing";
            } //shared-queuing

          } //list qos

          container scheduler-policy {
            description
                "Specify a scheduler-policy";
            leaf scheduler-policy-name {
              type string {
                length "1..32";
              }
            } //scheduler-policy-name

          } //container scheduler-policy

          container policer-control-override {
            description
                "Configure policer control overrides";
            container max-rate {
              description
                  "Configure Max Rate override in kilobits-per-second";
              leaf max-rate-string {
                type string;
                description
                    "[1..2000000000|max] Kbps";
              } //max-rate-string

            } //container max-rate

            container priority-mbs-thresholds {
              description
                  "Configure priority mbs thresholds overrides";
              container min-thresh-separation {
                description
                    "configure min threshold separation override";
                leaf size {
                  type string;
                  description
                      "[0..16777216 default]";
                } //size

                leaf min-thresh-separation-id {
                  type enumeration {
                    enum bytes;
                    enum kilobytes;
                  }
                } //min-thresh-separation-id

              } //container min-thresh-separation

              list priority {
                key "level";
                description
                    "Configure Priority Levels overrides";
                leaf level {
                  type uint32 {
                    range "1..8";
                  }
                } //level

                container mbs-contribution {
                  description
                      "Configure mbs size override";
                  leaf size {
                    type string;
                    description
                        "[0..16777216 default]";
                  } //size

                  leaf mbs-contribution-id {
                    type enumeration {
                      enum bytes;
                      enum kilobytes;
                    }
                  } //mbs-contribution-id

                } //container mbs-contribution

              } //list priority

            } //container priority-mbs-thresholds

          } //container policer-control-override

          container policer-override {
            presence
                "Configure policer overrides";
            list policer {
              key "policer-id";
              description
                  "Configure overrides for the policer";
              leaf policer-id {
                type uint32 {
                  range "1..63";
                }
              } //policer-id

              container cbs {
                description
                    "Specify Cbs override";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs override";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "specify packet byte offset";
                leaf add {
                  type uint32 {
                    range "0..31";
                  }
                } //add

                leaf subtract {
                  type uint32 {
                    range "1..32";
                  }
                } //subtract

              } //container packet-byte-offset

              container percent-rate {
                description
                    "Specify percent rates (CIR and PIR) override";
                leaf pir-percent {
                  type string;
                  description
                      "[0.01..100.00]";
                } //pir-percent

                leaf cir {
                  type string;
                  description
                      "[0.00..100.00]";
                } //cir

              } //container percent-rate

              container rate {
                description
                    "Specify rates (CIR and PIR) override";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-priority-no-cir;
                    enum offered-profile-cir;
                    enum offered-priority-cir;
                    enum offered-total-cir;
                    enum offered-limited-profile-cir;
                  }
                } //stat-mode

              } //container stat-mode

            } //list policer

          } //container policer-override

          container queue-override {
            presence
                "Apply queue override";
            list queue {
              key "queue-id";
              description
                  "Configure a queue override";
              leaf queue-id {
                type int32 {
                  range "1..32";
                }
              } //queue-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container cbs {
                description
                    "Specify CBS";
                leaf size-in-kbytes {
                  type string;
                  description
                      "Attribute size-in-kbytes for cbs";
                } //size-in-kbytes

              } //container cbs

              container high-prio-only {
                status "obsolete";
                description
                    "Specify high priority only burst size";
                leaf percent {
                  type string;
                  description
                      "[0..100 | default]";
                } //percent

              } //container high-prio-only

              container mbs {
                description
                    "Specify MBS";
                leaf size {
                  type string;
                  description
                      "Attribute size for mbs";
                } //size

                leaf bytes-kilobytes {
                  type enumeration {
                    enum bytes;
                    enum kilobytes;
                  }
                } //bytes-kilobytes

              } //container mbs

              leaf monitor-depth {
                type boolean;
                description
                    "Enable/Disable queue-depth monitoring";
              }

              container parent {
                description
                    "Specify the override weights for the queue within its parental scheduling 
                     context";
                leaf weight {
                  type uint32 {
                    range "0..100";
                  }
                } //weight

                leaf cir-weight {
                  type uint32 {
                    range "0..100";
                  }
                } //cir-weight

              } //container parent

              container percent-rate {
                description
                    "Specify percent rates (CIR and PIR)";
                leaf pir-percent {
                  type string;
                  description
                      "[0.01..100.00]";
                } //pir-percent

                leaf cir {
                  type string;
                  description
                      "[0.00..100.00]";
                } //cir

              } //container percent-rate

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container drop-tail {
                description
                    "Specify drop tail";
                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

            } //list queue

          } //container queue-override

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..3200000000|max] Kbps";
                } //pir-rate

                leaf cir {
                  type string;
                  description
                      "[0..3200000000|sum|max] Kbps";
                } //cir

              } //container rate

            } //list scheduler

          } //container scheduler-override

        } //container ingress

      } //list sap

      list spoke-sdp {
        key "sdp-id-vc-id";
        description
            "Provision a spoke SDP binding";
        leaf sdp-id-vc-id {
          type string;
          description
              "sdp-id - [1..32767] 
               vc-id - [1..4294967295]";
        } //sdp-id-vc-id

        leaf endpoint {
          type string {
            length "1..32";
          }
        } //endpoint

        leaf no-endpoint {
          type boolean;
          description
              "keyword - used to remove an endpoint association";
        } //no-endpoint

        leaf icb {
          type boolean;
          description
              "keyword - configure spoke-sdp as inter-chassis backup";
        } //icb

        container bandwidth {
          description
              "Configure the spoke-sdp bandwidth";
          leaf bw-value {
            type uint32 {
              range "0..100000000";
            }
            description
                "[0..100000000] Kbps";
          } //bw-value

          leaf max {
            type boolean;
          } //max

        } //container bandwidth

        leaf bfd-enable {
          type boolean;
          description
              "Enable/disable BFD";
        }

        container bfd-template {
          description
              "Configure BFD template";
          leaf bfd-template-string {
            type string {
            }
          } //bfd-template-string

        } //container bfd-template

        container description {
          description
              "Set description for spoke-sdp";
          leaf description-string {
            type string {
              length "1..80";
            }
            description
                "80 char max";
          } //description-string

        } //container description

        leaf entropy-label {
          type boolean;
          description
              "Enable/disable use of entropy-label";
        }

        container hash-label {
          description
              "Enable/disable use of hash-label";
          leaf signal-capability {
            type boolean;
          } //signal-capability

        } //container hash-label

        container precedence {
          description
              "Configure the spoke-sdp precedence";
          leaf precedence-value {
            type uint32 {
              range "1..4";
            }
          } //precedence-value

          leaf primary {
            type boolean;
            description
                "keyword - used to make this the primary spoke-sdp";
          } //primary

        } //container precedence

        leaf shutdown {
          type boolean;
          description
              "Administratively enable/disable the spoke SDP binding";
        }

        container egress {
          description
              "Spoke SDP egress configuration";
          container filter {
            description
                "Apply egress filter";
            leaf ip {
              type string;
              description
                  "[1..65535]|<name:64 char max>";
            } //ip

            leaf ipv6 {
              type string;
              description
                  "[1..65535]|<name:64 char max>";
            } //ipv6

          } //container filter

          list qos {
            key "network-policy-id";
            description
                "Configure egress qos";
            leaf network-policy-id {
              type uint32 {
                range "1..65535";
              }
            } //network-policy-id

            leaf port-redirect-group {
              type string {
                length "1..32";
              }
            } //port-redirect-group

            leaf instance {
              type uint16 {
                range "1..65535";
              }
            } //instance

          } //list qos

          list vc-label {
            key "egress-vc-label";
            description
                "Configure egress VC label";
            leaf egress-vc-label {
              type int32 {
                range "16..1048575";
              }
            } //egress-vc-label

          } //list vc-label

        } //container egress

        container ingress {
          description
              "Spoke SDP ingress configuration";
          container filter {
            description
                "Apply ingress filter";
            leaf ip {
              type string;
              description
                  "[1..65535]|<name:64 char max>";
            } //ip

            leaf ipv6 {
              type string;
              description
                  "[1..65535]|<name:64 char max>";
            } //ipv6

          } //container filter

          list qos {
            key "network-policy-id";
            description
                "Configure ingress qos";
            leaf network-policy-id {
              type uint32 {
                range "1..65535";
              }
            } //network-policy-id

            leaf fp-redirect-group {
              type string {
                length "1..32";
              }
            } //fp-redirect-group

            leaf instance {
              type uint16 {
                range "1..65535";
              }
            } //instance

          } //list qos

          list vc-label {
            key "ingress-vc-label";
            description
                "Configure ingress VC label";
            leaf ingress-vc-label {
              type string;
              description
                  "Attribute ingress-vc-label for vc-label";
            } //ingress-vc-label

          } //list vc-label

        } //container ingress

      } //list spoke-sdp

    } //list fpipe

  } //grouping alu-conf-svc-fpipe-r13

} //module  alu-conf-svc-fpipe-r13
