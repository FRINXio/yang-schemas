module alu-conf-eth-cfm-r13 {
  yang-version "1";

  namespace "urn:alcatel-lucent.com:sros:ns:yang:conf-eth-cfm-r13";

  prefix "conf-eth-cfm-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure Ethernet Connectivity Fault 
       Management (Eth-CFM) parameters on SR OS based routers. 
       
       Copyright 2014-2015 Alcatel-Lucent, 2016 Nokia. All rights reserved. 
       Reproduction of this document is authorized on the condition that the 
       foregoing copyright notice is included. 
       
       This alu-conf-eth-cfm-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-04-30";

  grouping alu-conf-eth-cfm-r13 {
    container eth-cfm {
      description
          "Configure Ethernet Connectivity Fault Management (Eth-CFM) parameters";
      container default-domain {
        description
            "Configure Eth-CFM default domain parameters";
        container bridge-identifier {
          description
              "Configure the service ID and VLAN for the default domain";
          leaf bridge-id {
            type uint32 {
              range "1..2147483647";
            }
          } //bridge-id

          leaf vlan {
            type string {
              length "1..4";
            }
            description
                "[1..4094]|none";
          } //vlan

          container id-permission {
            description
                "Configure the ID permission for the bridge and VLAN of the default domain";
            leaf chassis-defer {
              type enumeration {
                enum chassis;
                enum defer;
              }
              default "defer";
              description
                  "keywords - Default: defer";
            } //chassis-defer

          } //container id-permission

          container mhf-creation {
            description
                "Configure the MIP Half Function (MHF) and level for the bridge and VLAN of the 
                 default domain";
            leaf none-default-explicit-defer {
              type enumeration {
                enum none;
                enum default;
                enum explicit;
                enum defer;
              }
              default "defer";
              description
                  "keywords - Default: defer";
            } //none-default-explicit-defer

            leaf level {
              type enumeration {
                enum 0;
                enum 1;
                enum 2;
                enum 3;
                enum 4;
                enum 5;
                enum 6;
                enum 7;
                enum defer;
              }
              default "defer";
              description
                  "[0..7]|defer - Default: defer";
            } //level

          } //container mhf-creation

          container mip-ltr-priority {
            description
                "Configure the MIP linkage reply priority for the bridge and VLAN of the 
                 default domain";
            leaf priority {
              type enumeration {
                enum 0;
                enum 1;
                enum 2;
                enum 3;
                enum 4;
                enum 5;
                enum 6;
                enum 7;
                enum defer;
              }
              default "defer";
              description
                  "[0..7]|defer - Default: defer";
            } //priority

          } //container mip-ltr-priority

        } //container bridge-identifier

      } //container default-domain

      list domain {
        key "md-index";
        description
            "Configure Eth-CFM domain parameters";
        leaf md-index {
          type uint32 {
            range "1..4294967295";
          }
        } //md-index

        leaf format {
          type enumeration {
            enum dns;
            enum mac;
            enum none;
            enum string;
          }
          description
              "keywords - format of the md-name: Default string 
               dns - dns name format 
               mac - X:X:X:X:X:X-u 
               X - [0..FF]h 
               u - [0..65535]d 
               none - no name specified 
               string - ascii string";
        } //format

        leaf name {
          type string {
            length "1..43";
          }
          description
              "Maintenance Domain Name (1..43 characters)";
        } //name

        leaf level {
          type uint32 {
            range "0..7";
          }
        } //level

        leaf admin-name {
          type string {
            length "1..64";
          }
        } //admin-name

        list association {
          key "ma-index";
          description
              "Configure a Maintenance Association for the Domain";
          leaf ma-index {
            type uint32 {
              range "1..4294967295";
            }
          } //ma-index

          leaf format {
            type enumeration {
              enum icc-based;
              enum integer;
              enum string;
              enum vid;
              enum vpn-id;
            }
            description
                "keywords - format of the ma-name: Default integer 
                 icc-based - raw ascii - between 8 and 13 
                 characters 
                 integer - [0..65535] 
                 string - raw ascii 
                 vid - [0..4094] 
                 vpn-id - RFC-2685 VPN ID 
                 Format: xxx:xxxx, where x is a value 
                 between 00 and FF. 
                 eg. 00164D:AABBCCDD";
          } //format

          leaf name {
            type string {
              length "1..45";
            }
            description
                "Maintenance Association Name (1..45 characters)";
          } //name

          leaf admin-name {
            type string {
              length "1..64";
            }
          } //admin-name

          leaf auto-mep-discovery {
            type boolean;
            description
                "Enable/Disable the ability to auto-discover remote MEPs in the network";
          }

          container ccm-hold-time {
            description
                "Configure the CCM interval holding timers";
            leaf down {
              type uint32 {
                range "0..1000";
              }
              default 0;
              description
                  "[0..1000] centiseconds - Default: 0";
            } //down

          } //container ccm-hold-time

          container ccm-interval {
            description
                "Configure the CCM transmission interval for all MEPs in the association";
            leaf interval {
              type enumeration {
                enum 10ms;
                enum 100ms;
                enum 1;
                enum 10;
                enum 60;
                enum 600;
              }
              description
                  "Attribute interval for ccm-interval";
            } //interval

          } //container ccm-interval

          container facility-id-permission {
            description
                "Configure the id-permission for facility MEPs for the association";
            leaf facility-id-permission-id {
              type enumeration {
                enum chassis;
              }
            } //facility-id-permission-id

          } //container facility-id-permission

          list remote-mepid {
            key "mep-id";
            description
                "Configure the Remote MEP ID";
            leaf mep-id {
              type int16 {
                range "1..8191";
              }
            } //mep-id

            leaf remote-mac {
              type string {
                length "1..32";
              }
              description
                  "xx:xx:xx:xx:xx:xx or xx-xx-xx-xx-xx-xx or default";
            } //remote-mac

          } //list remote-mepid

          list bridge-identifier {
            key "bridge-id bridge-name";
            description
                "Configure the service ID for the association";
            leaf bridge-id {
              type uint32 {
                range "1..2147483647";
              }
            } //bridge-id

            leaf bridge-name {
              type string {
                length "1..64";
              }
            } //bridge-name

            container id-permission {
              description
                  "Configure the id-permission for the association";
              leaf id-permission-id {
                type enumeration {
                  enum chassis;
                }
              } //id-permission-id

            } //container id-permission

            container mhf-creation {
              description
                  "Configure the MIP Half Function (MHF) for the association";
              leaf default-none-explicit-static {
                type enumeration {
                  enum default;
                  enum none;
                  enum explicit;
                  enum static;
                }
                description
                    "keywords - default none";
              } //default-none-explicit-static

            } //container mhf-creation

            container mip-ltr-priority {
              description
                  "Configure the MIP linktrace reply priority";
              leaf priority {
                type uint32 {
                  range "0..7";
                }
                default 7;
                description
                    "[0..7] - Default: 7";
              } //priority

            } //container mip-ltr-priority

            container vlan {
              description
                  "Configure the Bridge-identifier Primary Vlan-Id";
              leaf vlan-id {
                type string;
                description
                    "[1..4094]";
              } //vlan-id

            } //container vlan

          } //list bridge-identifier

        } //list association

      } //list domain

      container md-auto-id {
        description
            "Configure auto identifier ranges for model-driven configuration-mode";
        container ma-index-range {
          description
              "Configure the Maintenance Association index range for model-driven 
               configuration-mode auto assignment";
          leaf start {
            type uint32 {
              range "1..4294967295";
            }
          } //start

          leaf end {
            type uint32 {
              range "1..4294967295";
            }
          } //end

        } //container ma-index-range

        container md-index-range {
          description
              "Configure the Maintenance Domain index range for model-driven 
               configuration-mode auto assignment";
          leaf start {
            type uint32 {
              range "1..4294967295";
            }
          } //start

          leaf end {
            type uint32 {
              range "1..4294967295";
            }
          } //end

        } //container md-index-range

      } //container md-auto-id

      container redundancy {
        description
            "Configure Eth-CFM redundancy parameters";
        container mc-lag {
          description
              "Configure CFM Redundancy Multi-Chassis LAG parameters";
          container propagate-hold-time {
            description
                "Configure the MC-LAG SAP fault delay timer";
            leaf seconds {
              type uint32 {
                range "0..60";
              }
              default 1;
              description
                  "[0..60] seconds - Default: 1";
            } //seconds

          } //container propagate-hold-time

          leaf standby-mep-shutdown {
            type boolean;
            description
                "Configure MEPs on standby MC-LAG to act administratively down";
          }

        } //container mc-lag

      } //container redundancy

      container slm {
        description
            "Configure Eth-CFM Synthetic Loss Measurement (SLM) parameters";
        container inactivity-timer {
          description
              "Configure the SLR inactivity timer for maintaining stale test data";
          leaf timer {
            type uint32 {
              range "10..100";
            }
            default 100;
            description
                "[10..100] seconds - Default: 100";
          } //timer

        } //container inactivity-timer

      } //container slm

      container system {
        description
            "Configure Eth-CFM general system parameters";
        leaf grace-tx-enable {
          type boolean;
          description
              "Enable/disable the overall system level capability of grace messaging for 
               ETH-CFM MEPs";
        }

        container sender-id {
          description
              "Configure the ETH-CFM sender-id used in CFM PDUs";
          leaf system {
            type boolean;
            description
                "system - Use the system name";
          } //system

          leaf local {
            type string {
              length "1..45";
            }
            description
                "[1..45 alpha-num characters]";
          } //local

        } //container sender-id

      } //container system

    } //container eth-cfm

  } //grouping alu-conf-eth-cfm-r13

} //module  alu-conf-eth-cfm-r13
