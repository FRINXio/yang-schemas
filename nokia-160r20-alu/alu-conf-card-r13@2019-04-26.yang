module alu-conf-card-r13 {
  yang-version "1";

  namespace "urn:alcatel-lucent.com:sros:ns:yang:conf-card-r13";

  prefix "conf-card-r13";

  import alu-conf-mda-cellular-r13 {
    prefix "conf-mda-cellular-r13";
  }
  import alu-types {
    prefix "alu";
  }

  alu:alu-major-release "rel16";

  organization "Alcatel-Lucent";

  contact
      "Alcatel-Lucent SR OS Support 
       Web: <http://www.alcatel-lucent.com>";

  description
      "Alcatel-Lucent YANG Data model to configure physical cards in a specified slot 
       on SR OS based routers. 
       
       Copyright 2014-2015 Alcatel-Lucent, 2016 Nokia. All rights reserved. 
       Reproduction of this document is authorized on the condition that the 
       foregoing copyright notice is included. 
       
       This alu-conf-card-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-04-26";

  grouping alu-conf-card-r13 {
    list card {
      key "slot-number";
      description
          "Configure physical cards in a specified slot";
      leaf slot-number {
        type uint32 {
          range "1..22";
        }
        description
            "Attribute slot-number for card";
      } //slot-number

      container capability {
        description
            "Configure the I/O module for SR or ESS operation";
        leaf sr-ess {
          type enumeration {
            enum sr;
            enum ess;
          }
          description
              "keywords - Service Router or Ethernet Service Switch capability";
        } //sr-ess

        leaf now {
          type boolean;
          description
              "keyword - change the capability without prompting";
        } //now

      } //container capability

      container card-type {
        description
            "Add/remove an I/O module to/from the device configuration for the slot";
        leaf card-type {
          type string {
            length "1..32";
          }
          description
              "Attribute card-type for card-type";
        } //card-type

        leaf level {
          type string {
            length "1..32";
          }
        } //level

      } //container card-type

      leaf fail-on-error {
        type boolean;
        description
            "Configure the behavior of the card state when an error is detected";
      }

      container filter-profile {
        description
            "Configure the filter allocation profile for the card";
        leaf filter-profile-id {
          type enumeration {
            enum none;
            enum profile-a;
          }
        } //filter-profile-id

      } //container filter-profile

      list named-pool-mode {
        key "now";
        description
            "Enable/Disable named pool mode (card reset required)";
        leaf now {
          type boolean;
          description
              "now - Change named-pool-mode without prompting.";
        } //now

      } //list named-pool-mode

      leaf power-save {
        type boolean;
        description
            "Card Power Save configuration";
      }

      leaf reset-on-recoverable-error {
        type boolean;
        description
            "Configure the behavior of the card state when a fatal memory parity error is 
             detected on a Q-chip of the card";
      }

      leaf shutdown {
        type boolean;
        description
            "Administratively shut down an I/O module";
      }

      list upgrade {
        key "index";
        description
            "Apply a functional level upgrade to this card";
        leaf index {
          type uint32 {
            range "1..6";
          }
        } //index

        leaf path {
          type string {
            length "1..32";
          }
        } //path

      } //list upgrade

      container fp {
        description
            "Configure forwarding plane";
        leaf fp-number {
          type string;
          description
              "Attribute fp-number for fp";
        } //fp-number

        container hi-bw-mcast-src {
          description
              "Enable/disable allocation of resources for high bandwidth multicast streams 
               for FP";
          leaf alarm {
            type boolean;
          } //alarm

          leaf group {
            type uint32 {
              range "0..32";
            }
            description
                "(0..32) group-id 0 removes FP from group";
          } //group

          leaf default-paths-only {
            type boolean;
            description
                "keyword - only assign default paths to hi-bw-mcast";
          } //default-paths-only

        } //container hi-bw-mcast-src

        container ingress-buffer-allocation {
          description
              "Configure ingress buffer pool percentage for the forwarding plane";
          leaf percentage {
            type string;
            description
                "[20.00..80.00]";
          } //percentage

        } //container ingress-buffer-allocation

        container init-extract-prio-mode {
          description
              "Configure mode for initial drop priority of extracted control plane packets";
          leaf mode {
            type enumeration {
              enum uniform;
              enum l3-classify;
            }
            description
                "Attribute mode for init-extract-prio-mode";
          } //mode

        } //container init-extract-prio-mode

        container policy-accounting {
          description
              "Configure number of stats resource for policy accounting";
          leaf limit {
            type uint32 {
              range "1000..128000";
            }
            description
                "Attribute limit for policy-accounting";
          } //limit

        } //container policy-accounting

        leaf stable-pool-sizing {
          type boolean;
          description
              "Enable Stable Pool Sizing";
        }

        container dist-cpu-protection {
          description
              "Configure Distributed CPU Protection FP parameters";
          container dynamic-enforcement-policer-pool {
            description
                "Configure dynamic-enforcement-policer-pool";
            leaf dynamic-enforcement-policer-pool-id {
              type int32 {
                range "1000..32000";
              }
            } //dynamic-enforcement-policer-pool-id

          } //container dynamic-enforcement-policer-pool

        } //container dist-cpu-protection

        container egress {
          description
              "Configure egress FP parameters";
          container hs-fixed-high-thresh-delta {
            description
                "Specify high threshold delta";
            leaf size-in-bytes {
              type uint32 {
                range "0..65536";
              }
            } //size-in-bytes

          } //container hs-fixed-high-thresh-delta

          container hs-pool-policy {
            description
                "Configure egress HS pool policy";
            leaf name {
              type string;
            } //name

          } //container hs-pool-policy

          container wred-queue-control {
            description
                "Configure WRED Queue control parameters";
            container buffer-allocation {
              description
                  "Configure FP settings for WRED queues egress buffer allocation";
              leaf min {
                type string;
                description
                    "[0.00..99.99]";
              } //min

              leaf max {
                type string;
                description
                    "[0.01..99.99]";
              } //max

            } //container buffer-allocation

            container resv-cbs {
              description
                  "Configure FP egress WRED queue reserved CBS";
              leaf min {
                type string;
                description
                    "[00.00..99.99]";
              } //min

              leaf max {
                type string;
                description
                    "[00.01..99.99]";
              } //max

            } //container resv-cbs

            leaf shutdown {
              type boolean;
              description
                  "Configure administrative state of FP egress WRED queue control";
            }

            container slope-policy {
              description
                  "Configure FP egress WRED queue control slope-policy";
              leaf slope-policy-name {
                type string {
                  length "1..32";
                }
                description
                    "[32 char max]";
              } //slope-policy-name

            } //container slope-policy

          } //container wred-queue-control

        } //container egress

        container ingress {
          description
              "Configure ingress FP parameters";
          container access {
            description
                "Configure access FP parameters";
            list queue-group {
              key "queue-group-name instance";
              description
                  "Configure ingress access FP queue-group parameters";
              leaf queue-group-name {
                type string {
                  length "1..32";
                }
              } //queue-group-name

              leaf instance {
                type uint16 {
                  range "1..65535";
                }
              } //instance

              container accounting-policy {
                description
                    "Configure accounting-policy";
                leaf acct-policy-id {
                  type uint64 {
                    range "1..99";
                  }
                } //acct-policy-id

              } //container accounting-policy

              leaf collect-stats {
                type boolean;
                description
                    "Configure statistics collection";
              }

              container description {
                description
                    "Configure description";
                leaf description-string {
                  type string {
                    length "1..80";
                  }
                } //description-string

              } //container description

              container policer-control-policy {
                description
                    "Configure policer-control-policy";
                leaf policer-control-policy-name {
                  type string {
                    length "1..32";
                  }
                } //policer-control-policy-name

              } //container policer-control-policy

              container policer-control-override {
                description
                    "Configure policer control overrides";
                container max-rate {
                  description
                      "Configure Max Rate override in kilobits-per-second";
                  leaf rate {
                    type string;
                    description
                        "[1..2000000000|max] Kbps";
                  } //rate

                } //container max-rate

                container priority-mbs-thresholds {
                  description
                      "Configure priority mbs thresholds overrides";
                  container min-thresh-separation {
                    description
                        "configure min threshold separation override";
                    leaf size {
                      type string;
                      description
                          "[0..16777216 default]";
                    } //size

                    leaf bytes-kilobytes {
                      type enumeration {
                        enum bytes;
                        enum kilobytes;
                      }
                    } //bytes-kilobytes

                  } //container min-thresh-separation

                  list priority {
                    key "level";
                    description
                        "Configure Priority Levels overrides";
                    leaf level {
                      type uint32 {
                        range "1..8";
                      }
                    } //level

                    container mbs-contribution {
                      description
                          "Configure mbs size override";
                      leaf size {
                        type string;
                        description
                            "[0..16777216 default]";
                      } //size

                      leaf bytes-kilobytes {
                        type enumeration {
                          enum bytes;
                          enum kilobytes;
                        }
                      } //bytes-kilobytes

                    } //container mbs-contribution

                  } //list priority

                } //container priority-mbs-thresholds

              } //container policer-control-override

              container policer-override {
                presence
                    "Configure policer overrides";
                list policer {
                  key "policer-id";
                  description
                      "Configure overrides for the policer";
                  leaf policer-id {
                    type uint32 {
                      range "1..32";
                    }
                  } //policer-id

                  container cbs {
                    description
                        "Specify Cbs override";
                    leaf size {
                      type string;
                      description
                          "[0..16777216 default]";
                    } //size

                    leaf bytes-kilobytes {
                      type enumeration {
                        enum bytes;
                        enum kilobytes;
                      }
                    } //bytes-kilobytes

                  } //container cbs

                  container mbs {
                    description
                        "Specify Mbs override";
                    leaf size {
                      type string;
                      description
                          "[0..16777216 default]";
                    } //size

                    leaf bytes-kilobytes {
                      type enumeration {
                        enum bytes;
                        enum kilobytes;
                      }
                    } //bytes-kilobytes

                  } //container mbs

                  container packet-byte-offset {
                    description
                        "specify packet byte offset";
                    leaf add {
                      type uint32 {
                        range "0..31";
                      }
                    } //add

                    leaf subtract {
                      type uint32 {
                        range "1..32";
                      }
                    } //subtract

                  } //container packet-byte-offset

                  container rate {
                    description
                        "Specify rates (CIR and PIR) override";
                    leaf pir-rate {
                      type string;
                      description
                          "[1..2000000000|max] Kbps";
                    } //pir-rate

                    leaf cir {
                      type string;
                      description
                          "[0..2000000000|max] Kbps";
                    } //cir

                  } //container rate

                  container stat-mode {
                    description
                        "Specify Stat Mode for the policer";
                    leaf stat-mode {
                      type enumeration {
                        enum no-stats;
                        enum minimal;
                        enum offered-profile-no-cir;
                        enum offered-priority-no-cir;
                        enum offered-profile-cir;
                        enum offered-priority-cir;
                        enum offered-total-cir;
                        enum offered-limited-profile-cir;
                        enum offered-profile-capped-cir;
                        enum offered-limited-capped-cir;
                      }
                    } //stat-mode

                  } //container stat-mode

                } //list policer

              } //container policer-override

            } //list queue-group

          } //container access

          container mcast-path-management {
            description
                "Configure local FP settings for ingress multicast path management";
            container bandwidth-policy {
              description
                  "Configure the bandwidth policy associated with FP for ingress path management";
              leaf policy-name {
                type string {
                  length "1..32";
                }
                description
                    "Max 32 chars";
              } //policy-name

            } //container bandwidth-policy

            leaf shutdown {
              type boolean;
              description
                  "Configure administrative state of ingress multicast path management";
            }

          } //container mcast-path-management

          container network {
            description
                "Configure network FP parameters";
            list queue-group {
              key "queue-group-name instance";
              description
                  "Configure ingress network FP queue-group parameters";
              leaf queue-group-name {
                type string {
                  length "1..32";
                }
              } //queue-group-name

              leaf instance {
                type uint16 {
                  range "1..65535";
                }
                description
                    "[1..65535]";
              } //instance

              container accounting-policy {
                description
                    "Configure accounting-policy";
                leaf acct-policy-id {
                  type uint64 {
                    range "1..99";
                  }
                } //acct-policy-id

              } //container accounting-policy

              leaf collect-stats {
                type boolean;
                description
                    "Configure statistics collection";
              }

              container description {
                description
                    "Configure description";
                leaf description-string {
                  type string {
                    length "1..80";
                  }
                } //description-string

              } //container description

              container policer-control-policy {
                description
                    "Configure policer-control-policy";
                leaf policer-control-policy-name {
                  type string {
                    length "1..32";
                  }
                } //policer-control-policy-name

              } //container policer-control-policy

              container policer-control-override {
                description
                    "Configure policer control overrides";
                container max-rate {
                  description
                      "Configure Max Rate override in kilobits-per-second";
                  leaf rate {
                    type string;
                    description
                        "[1..2000000000|max] Kbps";
                  } //rate

                } //container max-rate

                container priority-mbs-thresholds {
                  description
                      "Configure priority mbs thresholds overrides";
                  container min-thresh-separation {
                    description
                        "configure min threshold separation override";
                    leaf size {
                      type string;
                      description
                          "[0..16777216 default]";
                    } //size

                    leaf bytes-kilobytes {
                      type enumeration {
                        enum bytes;
                        enum kilobytes;
                      }
                    } //bytes-kilobytes

                  } //container min-thresh-separation

                  list priority {
                    key "level";
                    description
                        "Configure Priority Levels overrides";
                    leaf level {
                      type uint32 {
                        range "1..8";
                      }
                    } //level

                    container mbs-contribution {
                      description
                          "Configure mbs size override";
                      leaf size {
                        type string;
                        description
                            "[0..16777216 default]";
                      } //size

                      leaf bytes-kilobytes {
                        type enumeration {
                          enum bytes;
                          enum kilobytes;
                        }
                      } //bytes-kilobytes

                    } //container mbs-contribution

                  } //list priority

                } //container priority-mbs-thresholds

              } //container policer-control-override

              container policer-override {
                presence
                    "Configure policer overrides";
                list policer {
                  key "policer-id";
                  description
                      "Configure overrides for the policer";
                  leaf policer-id {
                    type uint32 {
                      range "1..32";
                    }
                  } //policer-id

                  container cbs {
                    description
                        "Specify Cbs override";
                    leaf size {
                      type string;
                      description
                          "[0..16777216 default]";
                    } //size

                    leaf bytes-kilobytes {
                      type enumeration {
                        enum bytes;
                        enum kilobytes;
                      }
                    } //bytes-kilobytes

                  } //container cbs

                  container mbs {
                    description
                        "Specify Mbs override";
                    leaf size {
                      type string;
                      description
                          "[0..16777216 default]";
                    } //size

                    leaf bytes-kilobytes {
                      type enumeration {
                        enum bytes;
                        enum kilobytes;
                      }
                    } //bytes-kilobytes

                  } //container mbs

                  container packet-byte-offset {
                    description
                        "specify packet byte offset";
                    leaf add {
                      type uint32 {
                        range "0..31";
                      }
                    } //add

                    leaf subtract {
                      type uint32 {
                        range "1..32";
                      }
                    } //subtract

                  } //container packet-byte-offset

                  container rate {
                    description
                        "Specify rates (CIR and PIR) override";
                    leaf pir-rate {
                      type string;
                      description
                          "[1..2000000000|max] Kbps";
                    } //pir-rate

                    leaf cir {
                      type string;
                      description
                          "[0..2000000000|max] Kbps";
                    } //cir

                  } //container rate

                  container stat-mode {
                    description
                        "Specify Stat Mode for the policer";
                    leaf stat-mode {
                      type enumeration {
                        enum no-stats;
                        enum minimal;
                        enum offered-profile-no-cir;
                        enum offered-priority-no-cir;
                        enum offered-profile-cir;
                        enum offered-priority-cir;
                        enum offered-total-cir;
                        enum offered-limited-profile-cir;
                        enum offered-profile-capped-cir;
                        enum offered-limited-capped-cir;
                      }
                    } //stat-mode

                  } //container stat-mode

                } //list policer

              } //container policer-override

            } //list queue-group

          } //container network

        } //container ingress

      } //container fp

      list mcm {
        key "mcm-slot";
        description
            "Configure a mda carrier module";
        leaf mcm-slot {
          type uint32;
          description
              "Attribute mcm-slot for mcm";
        } //mcm-slot

        container mcm-type {
          description
              "Provisions/de-provisions an MCM to/from the device configuration for the slot";
          leaf mcm-type {
            type string {
              length "1..32";
            }
            description
                "Attribute mcm-type for mcm-type";
          } //mcm-type

        } //container mcm-type

        leaf shutdown {
          type boolean;
          description
              "Administratively shut down an mcm";
        }

      } //list mcm

      list mda {
        key "mda-slot";
        description
            "Configure a media dependant adapter";
        leaf mda-slot {
          type uint32 {
            range "1..12";
          }
          description
              "Attribute mda-slot for mda";
        } //mda-slot

        container clock-mode {
          description
              "Configure clock mode and timestamp frequency";
          leaf adaptive {
            type boolean;
          } //adaptive

          leaf differential {
            type boolean;
          } //differential

          leaf timestamp-freq {
            type enumeration {
              enum 19440;
              enum 77760;
              enum 103680;
            }
            description
                "keywords";
          } //timestamp-freq

        } //container clock-mode

        leaf fail-on-error {
          type boolean;
          description
              "Configure the behavior of the MDA state when an error is detected";
        }

        container hi-bw-mcast-src {
          status "obsolete";
          description
              "Enable/disable allocation of resources for high bandwidth multicast streams";
          leaf alarm {
            type boolean;
          } //alarm

          leaf group {
            type uint32 {
              range "0..32";
            }
            description
                "(0..32) group-id 0 removes MDA from group";
          } //group

        } //container hi-bw-mcast-src

        container mda-type {
          description
              "Provisions/de-provisions an MDA to/from the device configuration for the slot";
          leaf mda-type {
            type string {
              length "1..32";
            }
            description
                "Attribute mda-type for mda-type";
          } //mda-type

          leaf level {
            type string {
              length "1..32";
            }
          } //level

        } //container mda-type

        container power-priority-level {
          description
              "Configure the power priority level of the MDA";
          leaf priority {
            type uint32 {
              range "1..200";
            }
            default 150;
            description
                "[1..200] - shutdown priority. Default: 150";
          } //priority

        } //container power-priority-level

        leaf reset-on-recoverable-error {
          type boolean;
          description
              "Configure the behavior of the MDA state when a fatal memory parity error is 
               detected on a Q-chip of the card";
        }

        leaf shutdown {
          type boolean;
          description
              "Administratively shut down an mda";
        }

        leaf sync-e {
          type boolean;
          description
              "Enable/Disable Synchronous Ethernet";
        }

        list upgrade {
          key "index";
          description
              "Apply a functional level upgrade to this card";
          leaf index {
            type uint32 {
              range "1..6";
            }
          } //index

          leaf path {
            type string {
              length "1..32";
            }
          } //path

        } //list upgrade

        container access {
          description
              "Configure access MDA parameters";
          container egress {
            description
                "Configure access egress MDA parameters";
            list pool {
              key "name";
              description
                  "Configure the egress pool policy for the MDA";
              leaf name {
                type string {
                  length "1..32";
                }
              } //name

              container amber-alarm-threshold {
                description
                    "Configure amber alarm threshold";
                leaf percentage {
                  type uint32 {
                    range "1..1000";
                  }
                } //percentage

              } //container amber-alarm-threshold

              container red-alarm-threshold {
                description
                    "Configure red alarm threshold";
                leaf percentage {
                  type uint32 {
                    range "1..1000";
                  }
                } //percentage

              } //container red-alarm-threshold

              container resv-cbs {
                description
                    "Configure the reserved CBS for the MDA";
                leaf percent-or-default {
                  type string;
                  description
                      "[0..100|default]";
                } //percent-or-default

                leaf amber-alarm-action {
                  type boolean;
                } //amber-alarm-action

                leaf step {
                  type uint32 {
                    range "1..100";
                  }
                } //step

                leaf max {
                  type uint32 {
                    range "1..100";
                  }
                } //max

              } //container resv-cbs

              container slope-policy {
                description
                    "Configure the slope policy";
                leaf name {
                  type string {
                    length "1..32";
                  }
                  default "default";
                } //name

              } //container slope-policy

            } //list pool

          } //container egress

          container ingress {
            description
                "Configure access ingress MDA parameters";
            list pool {
              key "name";
              description
                  "Configure the ingress pool policy for the MDA";
              leaf name {
                type string {
                  length "1..32";
                }
              } //name

              container amber-alarm-threshold {
                description
                    "Configure amber alarm threshold";
                leaf percentage {
                  type uint32 {
                    range "1..1000";
                  }
                } //percentage

              } //container amber-alarm-threshold

              container red-alarm-threshold {
                description
                    "Configure red alarm threshold";
                leaf percentage {
                  type uint32 {
                    range "1..1000";
                  }
                } //percentage

              } //container red-alarm-threshold

              container resv-cbs {
                description
                    "Configure the reserved CBS for the MDA";
                leaf percent-or-default {
                  type string;
                  description
                      "[0..100|default]";
                } //percent-or-default

                leaf amber-alarm-action {
                  type boolean;
                } //amber-alarm-action

                leaf step {
                  type uint32 {
                    range "1..100";
                  }
                } //step

                leaf max {
                  type uint32 {
                    range "1..100";
                  }
                } //max

              } //container resv-cbs

              container slope-policy {
                description
                    "Configure the slope policy";
                leaf name {
                  type string {
                    length "1..32";
                  }
                  default "default";
                } //name

              } //container slope-policy

            } //list pool

          } //container ingress

        } //container access

        container atm {
          description
              "Configure ATM MDA parameters";
          container mode {
            description
                "Configure the mode of operation";
            leaf mode-id {
              type enumeration {
                enum max8k-vc;
                enum max16k-vc;
              }
            } //mode-id

            leaf now {
              type boolean;
              description
                  "force execution without confirmation prompt";
            } //now

          } //container mode

        } //container atm

        uses "conf-mda-cellular-r13:alu-conf-mda-cellular-r13";
        container egress {
          description
              "Configure egress MDA parameters";
          container hsmda-pool-policy {
            description
                "Configure egress HSMDA pool policy";
            leaf policy-name {
              type string {
                length "1..32";
              }
            } //policy-name

          } //container hsmda-pool-policy

          container hsmda-agg-queue-burst {
            description
                "Configure egress HSMDA aggregate Queue burst";
            container high-burst-increase {
              description
                  "Specify high burst increase";
              leaf size-in-bytes {
                type uint32 {
                  range "0..65536";
                }
              } //size-in-bytes

            } //container high-burst-increase

            container low-burst-multiplier {
              description
                  "Specify low burst multiplier";
              leaf bytes-per-megabit-of-rate {
                type uint32 {
                  range "1..65536";
                }
              } //bytes-per-megabit-of-rate

            } //container low-burst-multiplier

          } //container hsmda-agg-queue-burst

        } //container egress

        container egress-xpl {
          description
              "Configure egress MDA XPL interface error parameters";
          container threshold {
            description
                "Configure the threshold value for egress XPL errors";
            leaf xpl-errors {
              type uint32 {
                range "1..1000000";
              }
              default 1000;
              description
                  "[1..1000000] - Default: 1000";
            } //xpl-errors

          } //container threshold

          container window {
            description
                "Configure the window size (in minutes) for egress XPL errors";
            leaf minutes {
              type uint32 {
                range "1..1440";
              }
              default 60;
              description
                  "[1..1440] - Default: 60";
            } //minutes

          } //container window

        } //container egress-xpl

        container gnss {
          description
              "Configure the GNSS receiver";
          container constellation {
            description
                "Configure the satellite constellation of the GNSS receiver";
            leaf gps-gps-glonass {
              type enumeration {
                enum gps;
                enum gps-glonass;
              }
            } //gps-gps-glonass

          } //container constellation

          leaf shutdown {
            type boolean;
            description
                "Administratively enable/disable the GNSS receiver";
          }

          container nmea {
            description
                "Configure NMEA sentence generation on the GNSS receiver";
            container sentence-interval {
              description
                  "Configure the interval between NMEA sentences, in seconds";
              leaf interval {
                type uint16 {
                  range "1..3600";
                }
                default 5;
                description
                    "[1..3600] - Default: 5";
              } //interval

            } //container sentence-interval

            container sentence-types {
              description
                  "Configure the types of NMEA sentences to generate";
              leaf-list sentence-type {
                type enumeration {
                  enum gpgga;
                  enum gprmc;
                  enum gpvtg;
                  enum gngns;
                }
                max-elements 4;
              } //sentence-type

            } //container sentence-types

            leaf shutdown {
              type boolean;
              description
                  "Administratively enable/disable NMEA sentence generation";
            }

          } //container nmea

        } //container gnss

        container ingress {
          status "obsolete";
          description
              "Configure ingress MDA parameters";
          container mcast-path-management {
            status "obsolete";
            description
                "Configure local MDA settings for ingress multicast path management";
            container bandwidth-policy {
              status "obsolete";
              description
                  "Configure the bandwidth policy associated with MDA for ingress path management";
              leaf policy-name {
                type string {
                  length "1..32";
                }
                description
                    "Max 32 chars";
              } //policy-name

            } //container bandwidth-policy

            leaf shutdown {
              type boolean;
              status "obsolete";
              description
                  "Configure administrative state of ingress multicast path management";
            }

            container ancillary-override {
              status "obsolete";
              description
                  "Configure ancillary path bandwidth override";
              container path-limit {
                status "obsolete";
                description
                    "Configure path-limit";
                leaf megabits-per-second {
                  type uint32 {
                    range "1..5000";
                  }
                } //megabits-per-second

              } //container path-limit

            } //container ancillary-override

            container primary-override {
              status "obsolete";
              description
                  "Configure primary path bandwidth override";
              container path-limit {
                status "obsolete";
                description
                    "Configure path limit";
                leaf megabits-per-second {
                  type uint32 {
                    range "1..2000";
                  }
                } //megabits-per-second

              } //container path-limit

            } //container primary-override

            container secondary-override {
              status "obsolete";
              description
                  "Configure secondary path bandwidth override";
              container path-limit {
                status "obsolete";
                description
                    "Configure path limit";
                leaf megabits-per-second {
                  type uint32 {
                    range "1..2000";
                  }
                } //megabits-per-second

              } //container path-limit

            } //container secondary-override

          } //container mcast-path-management

        } //container ingress

        container ingress-xpl {
          description
              "Configure ingress MDA XPL interface error parameters";
          container threshold {
            description
                "Configure the threshold value for ingress XPL errors";
            leaf xpl-errors {
              type uint32 {
                range "1..1000000";
              }
              default 1000;
              description
                  "[1..1000000] - Default: 1000";
            } //xpl-errors

          } //container threshold

          container window {
            description
                "Configure the window size (in minutes) for ingress XPL errors";
            leaf minutes {
              type uint32 {
                range "1..1440";
              }
              default 60;
              description
                  "[1..1440] - Default: 60";
            } //minutes

          } //container window

        } //container ingress-xpl

        container named-pool-mode {
          description
              "Enable/Disable named pool mode";
          container egress {
            description
                "Configure named pool mode egress MDA parameters";
            container named-pool-policy {
              description
                  "Configure egress named pool policy";
              leaf policy-name {
                type string {
                  length "1..32";
                }
              } //policy-name

            } //container named-pool-policy

          } //container egress

          container ingress {
            description
                "Configure named pool mode ingress MDA parameters";
            container named-pool-policy {
              description
                  "Configure ingress named pool policy";
              leaf policy-name {
                type string {
                  length "1..32";
                }
              } //policy-name

            } //container named-pool-policy

          } //container ingress

        } //container named-pool-mode

        container network {
          description
              "Configure network MDA parameters";
          container egress {
            description
                "Configure network egress MDA parameters";
            list pool {
              key "name";
              description
                  "Configure the egress pool policy for the MDA";
              leaf name {
                type string {
                  length "1..32";
                }
              } //name

              container amber-alarm-threshold {
                description
                    "Configure amber alarm threshold";
                leaf percentage {
                  type uint32 {
                    range "1..1000";
                  }
                } //percentage

              } //container amber-alarm-threshold

              container red-alarm-threshold {
                description
                    "Configure red alarm threshold";
                leaf percentage {
                  type uint32 {
                    range "1..1000";
                  }
                } //percentage

              } //container red-alarm-threshold

              container resv-cbs {
                description
                    "Configure the reserved CBS for the MDA";
                leaf percent-or-default {
                  type string;
                  description
                      "[0..100|default]";
                } //percent-or-default

                leaf amber-alarm-action {
                  type boolean;
                } //amber-alarm-action

                leaf step {
                  type uint32 {
                    range "1..100";
                  }
                } //step

                leaf max {
                  type uint32 {
                    range "1..100";
                  }
                } //max

              } //container resv-cbs

              container slope-policy {
                description
                    "Configure the slope policy";
                leaf name {
                  type string {
                    length "1..32";
                  }
                  default "default";
                } //name

              } //container slope-policy

            } //list pool

          } //container egress

          container ingress {
            description
                "Configure network ingress MDA parameters";
            container queue-policy {
              description
                  "Configure the network policy";
              leaf name {
                type string {
                  length "1..32";
                }
                default "default";
              } //name

            } //container queue-policy

            list pool {
              key "name";
              description
                  "Configure the ingress pool policy for the MDA";
              leaf name {
                type string {
                  length "1..32";
                }
              } //name

              container amber-alarm-threshold {
                description
                    "Configure amber alarm threshold";
                leaf percentage {
                  type uint32 {
                    range "1..1000";
                  }
                } //percentage

              } //container amber-alarm-threshold

              container red-alarm-threshold {
                description
                    "Configure red alarm threshold";
                leaf percentage {
                  type uint32 {
                    range "1..1000";
                  }
                } //percentage

              } //container red-alarm-threshold

              container resv-cbs {
                description
                    "Configure the reserved CBS for the MDA";
                leaf percent-or-default {
                  type string;
                  description
                      "[0..100|default]";
                } //percent-or-default

                leaf amber-alarm-action {
                  type boolean;
                } //amber-alarm-action

                leaf step {
                  type uint32 {
                    range "1..100";
                  }
                } //step

                leaf max {
                  type uint32 {
                    range "1..100";
                  }
                } //max

              } //container resv-cbs

              container slope-policy {
                description
                    "Configure the slope policy";
                leaf name {
                  type string {
                    length "1..32";
                  }
                  default "default";
                } //name

              } //container slope-policy

            } //list pool

          } //container ingress

        } //container network

        container wlan-radio {
          description
              "Configure WLAN Radio configuration";
          container country {
            description
                "Configure country radio is operating in";
            leaf country-id {
              type enumeration {
                enum australia;
                enum belgium;
                enum bolivia;
                enum brazil;
                enum canada;
                enum chile;
                enum colombia;
                enum france;
                enum germany;
                enum india;
                enum iran;
                enum italy;
                enum japan;
                enum malaysia;
                enum mexico;
                enum new-zealand;
                enum peru;
                enum russia;
                enum singapore;
                enum south-africa;
                enum usa;
                enum venezuela;
              }
            } //country-id

          } //container country

          leaf shutdown {
            type boolean;
            description
                "Enable/Disable WLAN Radio";
          }

          container access-point {
            description
                "Configure Access Point Parameters";
            container bandwidth {
              description
                  "Configure AP channel bandwidth";
              leaf t20Mhz-40Mhz {
                type enumeration {
                  enum 20Mhz;
                  enum 40Mhz;
                }
              } //t20Mhz-40Mhz

            } //container bandwidth

            container beacon-interval {
              description
                  "Configure the beacon transmission interval";
              leaf msecs {
                type uint32 {
                  range "75..999";
                }
                description
                    "[75..999]";
              } //msecs

            } //container beacon-interval

            container channel {
              description
                  "Configure AP Channel";
              leaf auto {
                type boolean;
              } //auto

              leaf channel-id {
                type uint32 {
                  range "1..4294967295";
                }
                description
                    "Dependant on Country";
              } //channel-id

            } //container channel

            container frequency-band {
              description
                  "Configure AP frequency-band";
              leaf t2400-5000 {
                type enumeration {
                  enum 2400;
                  enum 5000;
                }
              } //t2400-5000

            } //container frequency-band

          } //container access-point

        } //container wlan-radio

      } //list mda

      container virtual-scheduler-adjustment {
        description
            "Configure hqos fine tune parameters";
        container internal-scheduler-weight-mode {
          description
              "Specify internal scheduler weight mode";
          leaf weight-mode {
            type enumeration {
              enum default;
              enum force-equal;
              enum offered-load;
              enum capped-offered-load;
            }
            description
                "default|force-equal|offered-load|capped-offered-load - Default: default";
          } //weight-mode

        } //container internal-scheduler-weight-mode

        container rate-calc-min-int {
          description
              "Configure Rate Calculation Min Interval";
          leaf fast-queue {
            type string;
            description
                "[0.01..1000.00]";
          } //fast-queue

          leaf slow-queue {
            type string;
            description
                "[0.01..1000.00]";
          } //slow-queue

        } //container rate-calc-min-int

        container sched-run-min-int {
          description
              "Configure Scheduler Run Min Interval";
          leaf percent-of-default {
            type string;
            description
                "[0.01..1000.00]";
          } //percent-of-default

        } //container sched-run-min-int

        container slow-queue-threshold {
          description
              "Configure Slow Queue Threshold Rate";
          leaf kilobits-per-second {
            type string;
            description
                "[0..1000000]";
          } //kilobits-per-second

        } //container slow-queue-threshold

        container task-scheduling-int {
          description
              "Configure Task Scheduling Interval";
          leaf percent-of-default {
            type string;
            description
                "[0.01..1000.00]";
          } //percent-of-default

        } //container task-scheduling-int

      } //container virtual-scheduler-adjustment

    } //list card

  } //grouping alu-conf-card-r13

} //module  alu-conf-card-r13
