module alu-conf-svc-vpls-r13 {
  yang-version "1";

  namespace "urn:alcatel-lucent.com:sros:ns:yang:conf-svc-vpls-r13";

  prefix "conf-svc-vpls-r13";

  import alu-conf-svc-vpls-igmp-r13 {
    prefix "conf-svc-vpls-igmp-r13";
  }
  import alu-conf-svc-vpls-macmo-r13 {
    prefix "conf-svc-vpls-macmo-r13";
  }
  import alu-conf-svc-vpls-macpr-r13 {
    prefix "conf-svc-vpls-macpr-r13";
  }
  import alu-conf-svc-vpls-meshs-r13 {
    prefix "conf-svc-vpls-meshs-r13";
  }
  import alu-conf-svc-vpls-mld-r13 {
    prefix "conf-svc-vpls-mld-r13";
  }
  import alu-conf-svc-vpls-pim-r13 {
    prefix "conf-svc-vpls-pim-r13";
  }
  import alu-conf-svc-vpls-sap-r13 {
    prefix "conf-svc-vpls-sap-r13";
  }
  import alu-conf-svc-vpls-split-r13 {
    prefix "conf-svc-vpls-split-r13";
  }
  import alu-conf-svc-vpls-spoke-r13 {
    prefix "conf-svc-vpls-spoke-r13";
  }
  import alu-conf-svc-vpls-stp-r13 {
    prefix "conf-svc-vpls-stp-r13";
  }
  import alu-types {
    prefix "alu";
  }
  import ietf-inet-types {
    prefix "inet";
  }
  import ietf-yang-types {
    prefix "yang";
  }

  alu:alu-major-release "rel16";

  organization "Alcatel-Lucent";

  contact
      "Alcatel-Lucent SR OS Support 
       Web: <http://www.alcatel-lucent.com>";

  description
      "Alcatel-Lucent YANG Data model to configure Virtual Private LAN Services on SR 
       OS based routers. 
       
       Copyright 2014-2015 Alcatel-Lucent, 2016 Nokia. All rights reserved. 
       Reproduction of this document is authorized on the condition that the 
       foregoing copyright notice is included. 
       
       This alu-conf-svc-vpls-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-05-22";

  grouping alu-conf-svc-vpls-r13 {
    list vpls {
      key "service-id";
      description
          "Configure Virtual Private LAN Services";
      leaf service-id {
        type string;
        description
            "Attribute service-id for vpls";
      } //service-id

      leaf customer {
        type uint32 {
          range "1..2147483647";
        }
      } //customer

      leaf vpn {
        type uint32 {
          range "1..2147483647";
        }
      } //vpn

      leaf m-vpls {
        type boolean;
        description
            "keyword - creates a management VPLS";
      } //m-vpls

      leaf b-vpls-i-vpls {
        type enumeration {
          enum b-vpls;
          enum i-vpls;
        }
        description
            "b-vpls - PBB backbone-vpls 
             i-vpls - PBB customer vpls instance";
      } //b-vpls-i-vpls

      leaf etree {
        type boolean;
      } //etree

      leaf name {
        type string;
        description
            "64-char max";
      } //name

      list def-mesh-vc-id {
        key "vc-id";
        status "obsolete";
        description
            "Configure default mesh vc-id";
        leaf vc-id {
          type uint32 {
            range "1..4294967295";
          }
        } //vc-id

      } //list def-mesh-vc-id

      list description {
        key "description-string";
        description
            "Description for the service";
        leaf description-string {
          type string {
            length "1..80";
          }
        } //description-string

      } //list description

      leaf disable-aging {
        type boolean;
        description
            "Enable/disable aging of MAC addresses";
      }

      leaf disable-learning {
        type boolean;
        description
            "Enable/disable learning of new MAC addresses";
      }

      leaf discard-unknown {
        type boolean;
        description
            "Enable/disable discarding of packets with unknown destination mac addresses";
      }

      list fdb-table-high-wmark {
        key "high-water-mark";
        description
            "Configure the high watermark for the FDB table";
        leaf high-water-mark {
          type uint32 {
            range "0..100";
          }
        } //high-water-mark

      } //list fdb-table-high-wmark

      list fdb-table-low-wmark {
        key "low-water-mark";
        description
            "Configure the low watermark for the FDB table";
        leaf low-water-mark {
          type uint32 {
            range "0..100";
          }
        } //low-water-mark

      } //list fdb-table-low-wmark

      list fdb-table-size {
        key "table-size";
        description
            "Configure the maximum number of MAC entries in the FDB";
        leaf table-size {
          type string;
          description
              "Attribute table-size for fdb-table-size";
        } //table-size

      } //list fdb-table-size

      container host-connectivity-verify {
        description
            "Enable/disable host connectivity verification for all hosts";
        leaf source-ip {
          type inet:ip-address;
          description
              "a.b.c.d";
        } //source-ip

        leaf source-mac {
          type alu:ieee-address;
          description
              "xx:xx:xx:xx:xx:xx or xx-xx-xx-xx-xx-xx";
        } //source-mac

        leaf interval {
          type uint64 {
            range "1..6000";
          }
          description
              "[1..6000] minutes";
        } //interval

        leaf action {
          type enumeration {
            enum remove;
            enum alarm;
          }
          description
              "keywords";
        } //action

        leaf timeout {
          type uint8 {
            range "10..60";
          }
          description
              "[10..60] seconds";
        } //timeout

        leaf retry-count {
          type uint8 {
            range "2..29";
          }
          description
              "[2..29]";
        } //retry-count

      } //container host-connectivity-verify

      list local-age {
        key "aging-timer";
        description
            "Configure aging time for locally learned mac addresses";
        leaf aging-timer {
          type uint32 {
            range "60..86400";
          }
        } //aging-timer

      } //list local-age

      container mac-subnet-length {
        description
            "Configure MAC sub-net length";
        leaf subnet-length {
          type uint32 {
            range "24..48";
          }
          description
              "24..48";
        } //subnet-length

      } //container mac-subnet-length

      container mcast-ipv6-snooping-scope {
        description
            "Configure the IPv6 multicast snooping scope";
        leaf mcast-ipv6-snooping-scope-id {
          type enumeration {
            enum sg-based;
            enum mac-based;
          }
        } //mcast-ipv6-snooping-scope-id

      } //container mcast-ipv6-snooping-scope

      container mfib-table-high-wmark {
        description
            "Configure the high watermark for the MFIB table";
        leaf high-water-mark {
          type uint32 {
            range "0..100";
          }
        } //high-water-mark

      } //container mfib-table-high-wmark

      container mfib-table-low-wmark {
        description
            "Configure the low watermark for the MFIB table";
        leaf low-water-mark {
          type uint32 {
            range "0..100";
          }
        } //low-water-mark

      } //container mfib-table-low-wmark

      container mfib-table-size {
        description
            "Configure the maximum number of SG entries in the MFIB";
        leaf table-size {
          type uint32 {
            range "1..40959";
          }
          description
              "Attribute table-size for mfib-table-size";
        } //table-size

      } //container mfib-table-size

      container multicast-info-policy {
        description
            "Configure multicast information policy";
        leaf policy-name {
          type string {
            length "1..32";
          }
          description
              "[Max 32 chars]";
        } //policy-name

      } //container multicast-info-policy

      leaf propagate-mac-flush {
        type boolean;
        description
            "Propagate MAC flush frames from LDP peer to all mesh-SDP and Spoke-SDPs";
      }

      list remote-age {
        key "aging-timer";
        description
            "Configure aging time for remotely learned mac addresses";
        leaf aging-timer {
          type uint32 {
            range "60..86400";
          }
        } //aging-timer

      } //list remote-age

      leaf selective-learned-fdb {
        type boolean;
        description
            "Configure selective learned fdb";
      }

      leaf send-flush-on-failure {
        type boolean;
        description
            "Enable/disable sending MAC withdraw message on SAP/Spoke-SDP failure";
      }

      container service-mtu {
        description
            "Configure service MTU";
        leaf octets {
          type uint32 {
            range "1..9194";
          }
        } //octets

      } //container service-mtu

      container service-name {
        status "obsolete";
        description
            "Configure a service name";
        leaf service-name {
          type string;
          description
              "64-char max";
        } //service-name

      } //container service-name

      container shcv-policy-ipv4 {
        description
            "Configure the Subscriber Host Connectivity Verification policy for IPv4";
        leaf policy-name {
          type string;
        } //policy-name

      } //container shcv-policy-ipv4

      leaf shutdown {
        type boolean;
        description
            "Administratively enable/disable the service";
      }

      container spbm-control-vpls {
        description
            "Configure SPB control vpls parameters";
        leaf service-id {
          type string;
          description
              "Attribute service-id for spbm-control-vpls";
        } //service-id

        leaf fid {
          type uint32 {
            range "1..4095";
          }
        } //fid

      } //container spbm-control-vpls

      container temp-flooding {
        description
            "Configure temporary flooding";
        leaf flood-time {
          type uint32 {
            range "3..600";
          }
          description
              "[3..600] seconds";
        } //flood-time

      } //container temp-flooding

      container vsd-domain {
        description
            "Configure the VPLS VSD domain";
        leaf name {
          type string;
        } //name

      } //container vsd-domain

      container vxlan-src-vtep {
        description
            "Configure termination IP in the VPLS service for VXLAN tunnels";
        leaf ip-address {
          type string;
          description
              "Attribute ip-address for vxlan-src-vtep";
        } //ip-address

      } //container vxlan-src-vtep

      container allow-ip-int-bind {
        presence
            "Configure to allow IP interface binding";
        leaf forward-ipv4-multicast-to-ip-int {
          type boolean;
          description
              "Configure multicast forwarding from RVPLS to VPLS L3 interface";
        }

        leaf forward-ipv6-multicast-to-ip-int {
          type boolean;
          description
              "Configure IPv6 multicast forwarding from RVPLS to VPLS L3 interface";
        }

        leaf vxlan-ipv4-tep-ecmp {
          type boolean;
          description
              "Enable/disable ECMP behavior on R-VPLS services,";
        }

        container igmp-snooping {
          description
              "Configure IGMP snooping parameters";
          leaf mrouter-port {
            type boolean;
            description
                "Configure the VPLS L3 interface as a multicast router port";
          }

        } //container igmp-snooping

        container mld-snooping {
          description
              "Configure MLD snooping parameters";
          leaf mrouter-port {
            type boolean;
            description
                "Configure the VPLS L3 interface as an IPv6 multicast router port";
          }

        } //container mld-snooping

      } //container allow-ip-int-bind

      list bgp {
        key "bgp-instance";
        description
            "Configure BGP";
        leaf bgp-instance {
          type uint32 {
            range "1..2";
          }
        } //bgp-instance

        container route-distinguisher {
          description
              "Configure route distinguisher";
          leaf rd {
            type string {
              length "1..21";
            }
            description
                "<ip-addr:comm-val>|<2byte-asnumber:ext-comm-val>|<4byte-asnumber:comm-val> 
                 ip-addr - a.b.c.d 
                 comm-val - [0..65535] 
                 2byte-asnumber - [1..65535] 
                 ext-comm-val - [0..4294967295] 
                 4byte-asnumber - [1..4294967295]";
          } //rd

          leaf auto-rd {
            type boolean;
          } //auto-rd

        } //container route-distinguisher

        container route-target {
          description
              "Configure route target";
          leaf ext-community {
            type string;
            description
                "Attribute ext-community for route-target";
          } //ext-community

          leaf export {
            type string;
          } //export

          leaf import {
            type string;
          } //import

        } //container route-target

        container vsi-export {
          description
              "VSI export route policies";
          leaf-list policy-name {
            type string {
              length "1..32";
            }
            max-elements 5;
          } //policy-name

        } //container vsi-export

        container vsi-import {
          description
              "VSI import route policies";
          leaf-list policy-name {
            type string {
              length "1..32";
            }
            max-elements 5;
          } //policy-name

        } //container vsi-import

        list pw-template-binding {
          key "policy-id";
          description
              "Configure pw-template bind policy";
          leaf policy-id {
            type uint32 {
              range "1..2147483647";
            }
          } //policy-id

          leaf split-horizon-group {
            type string {
              length "1..32";
            }
          } //split-horizon-group

          leaf-list import-rt {
            type string;
            max-elements 5;
            description
                "Attribute ext-community for pw-template-binding";
          } //import-rt

          leaf bfd-enable {
            type boolean;
            description
                "Enable/disable BFD";
          }

          container bfd-template {
            description
                "Configure BFD template";
            leaf bfd-template-string {
              type string {
              }
            } //bfd-template-string

          } //container bfd-template

          container monitor-oper-group {
            description
                "Configure a monitoring operational-group";
            leaf group-name {
              type string {
                length "1..32";
              }
            } //group-name

          } //container monitor-oper-group

          container oper-group {
            description
                "Configure an Operational-Group";
            leaf group-name {
              type string;
            } //group-name

          } //container oper-group

        } //list pw-template-binding

      } //list bgp

      container bgp-ad {
        presence
            "Configure BGP auto-discovery";
        leaf shutdown {
          type boolean;
          description
              "Administratively enable/disable BGP auto-discovery";
        }

        container vpls-id {
          description
              "Configure VPLS-ID";
          leaf vpls-id {
            type string;
            description
                "<ip-addr:comm-val>|<2byte-asnumber:ext-comm-val>|<4byte-asnumber:comm-val> 
                 ip-addr - a.b.c.d 
                 comm-val - [0..65535] 
                 2byte-asnumber - [1..65535] 
                 ext-comm-val - [0..4294967295] 
                 4byte-asnumber - [1..4294967295]";
          } //vpls-id

        } //container vpls-id

        container vsi-id {
          description
              "Configure VSI-id";
          container prefix {
            description
                "Configure VSI prefix";
            leaf low-order-vsi-id {
              type string {
              }
              description
                  "<ip-addr>|<raw-prefix> 
                   ip-addr - a.b.c.d 
                   raw-prefix - [0..4294967295]";
            } //low-order-vsi-id

          } //container prefix

        } //container vsi-id

      } //container bgp-ad

      container bgp-evpn {
        presence
            "Configure BGP Ethernet VPN";
        leaf accept-ivpls-evpn-flush {
          type boolean;
          description
              "Configure to accept non-zero ethernet-tag MAC routes and process for CMAC 
               flushing";
        }

        leaf cfm-mac-advertisement {
          type boolean;
          description
              "Enable/disable the advertisement of MEP, MIP, and VMEP MAC addresses over the 
               BGP EVPN";
        }

        container evi {
          description
              "EVPN Identifier";
          leaf value {
            type uint32 {
              range "1..65535";
            }
          } //value

        } //container evi

        container incl-mcast-orig-ip {
          description
              "Configure originating IP address";
          leaf ip-address {
            type string;
            description
                "a.b.c.d";
          } //ip-address

        } //container incl-mcast-orig-ip

        leaf ingress-repl-inc-mcast-advertisement {
          type boolean;
          description
              "Configure BGP EVPN IMET-IR route advertisement";
        }

        container ip-route-advertisement {
          description
              "Configure BGP EVPN IP Route Advertisement";
          leaf incl-host {
            type boolean;
          } //incl-host

        } //container ip-route-advertisement

        leaf mac-advertisement {
          type boolean;
          description
              "Configure BGP EVPN MAC Advertisement";
        }

        leaf unknown-mac-route {
          type boolean;
          description
              "Configure BGP EVPN Unknown MAC Route";
        }

        container isid-route-target {
          description
              "configure ISID route target information";
          list isid-range {
            key "from";
            description
                "Configure ISID range information";
            leaf from {
              type uint32 {
                range "1..16777215";
              }
            } //from

            leaf to {
              type uint32 {
                range "1..16777215";
              }
            } //to

            leaf auto-rt {
              type boolean;
            } //auto-rt

            leaf route-target {
              type string;
              description
                  "Attribute rt for isid-range";
            } //route-target

          } //list isid-range

        } //container isid-route-target

        container mac-duplication {
          description
              "Configure BGP EVPN MAC Duplication";
          leaf black-hole-dup-mac {
            type boolean;
            description
                "Enable/disable BGP-EVPN black-hole duplicate MAC traffic";
          }

          container detect {
            description
                "Configure BGP EVPN Mac Duplication Detection";
            leaf num-moves {
              type uint32 {
                range "3..10";
              }
            } //num-moves

            leaf window {
              type uint32 {
                range "1..15";
              }
            } //window

          } //container detect

          container retry {
            description
                "Configure BGP EVPN Mac Duplication Retry";
            leaf minutes {
              type uint32 {
                range "2..60";
              }
            } //minutes

          } //container retry

        } //container mac-duplication

        list mpls {
          key "bgp";
          description
              "Configure BGP EVPN mpls";
          leaf bgp {
            type uint32 {
              range "1..2";
            }
          } //bgp

          container bgp-instance {
            status "obsolete";
            description
                "Configure BGP instance";
            leaf bgp-instance {
              type uint32 {
                range "1..2";
              }
            } //bgp-instance

          } //container bgp-instance

          leaf control-word {
            type boolean;
            description
                "Enable/disable setting the CW bit in the label message";
          }

          container default-route-tag {
            description
                "Configure default-route-tag to match against export policies";
            leaf t0x01..0xff {
              type string;
              description
                  "[1..255] - accepts in decimal or hex";
            } //t0x01..0xff

          } //container default-route-tag

          container ecmp {
            description
                "Configure maximum ECMP routes information";
            leaf max-ecmp-routes {
              type string;
              description
                  "[1..32]: default 1";
            } //max-ecmp-routes

          } //container ecmp

          leaf entropy-label {
            type boolean;
            description
                "Enable/disable use of entropy-label";
          }

          leaf force-vlan-vc-forwarding {
            type boolean;
            description
                "Forces vlan-vc-type forwarding in the data-path";
          }

          leaf ingress-replication-bum-label {
            type boolean;
            description
                "Use the same label as the one advertised for unicast traffic";
          }

          container restrict-protected-src {
            description
                "Enable/disable protected src MAC restriction";
            leaf discard-frame {
              type boolean;
              description
                  "keyword - discard frame and trap on a protected MAC";
            } //discard-frame

          } //container restrict-protected-src

          container send-evpn-encap {
            description
                "Configure encapsulation for this service";
            leaf mpls {
              type boolean;
            } //mpls

            leaf mplsoudp {
              type boolean;
            } //mplsoudp

          } //container send-evpn-encap

          leaf shutdown {
            type boolean;
            description
                "Administratively Enable/Disable BGP-EVPN mpls";
          }

          container split-horizon-group {
            description
                "Configure a split-horizon-group";
            leaf group-name {
              type string {
                length "1..32";
              }
            } //group-name

          } //container split-horizon-group

          container auto-bind-tunnel {
            description
                "Configure BGP EVPN mpls auto-bind-tunnel";
            leaf enforce-strict-tunnel-tagging {
              type boolean;
              description
                  "Enable/disable enforcement of strict tunnel tagging";
            }

            container resolution {
              description
                  "Configure resolution method for tunnel selection";
              leaf disabled-any-filter {
                type enumeration {
                  enum disabled;
                  enum any;
                  enum filter;
                }
              } //disabled-any-filter

            } //container resolution

            container resolution-filter {
              description
                  "Configure auto-bind-tunnel resolution filter information";
              leaf bgp {
                type boolean;
                description
                    "Enable/disable setting BGP type for auto-bind-tunnel";
              }

              leaf ldp {
                type boolean;
                description
                    "Enable/disable setting LDP type for auto-bind-tunnel";
              }

              leaf rsvp {
                type boolean;
                description
                    "Enable/disable setting RSVP-TE type for auto-bind-tunnel";
              }

              leaf sr-isis {
                type boolean;
                description
                    "Enable/disable setting SR-ISIS type for auto-bind-tunnel";
              }

              leaf sr-ospf {
                type boolean;
                description
                    "Enable/disable setting SR-OSPF type for auto-bind-tunnel";
              }

              leaf sr-policy {
                type boolean;
                description
                    "Enable/disable setting SR-Policy type for auto-bind-tunnel";
              }

              leaf sr-te {
                type boolean;
                description
                    "Enable/disable setting SR-TE type for auto-bind-tunnel";
              }

              leaf udp {
                type boolean;
                description
                    "Enable/disable setting UDP type for auto-bind-tunnel";
              }

            } //container resolution-filter

          } //container auto-bind-tunnel

        } //list mpls

        list vxlan {
          key "bgp";
          description
              "Configure BGP EVPN vxlan";
          leaf bgp {
            type uint32 {
              range "1..2";
            }
          } //bgp

          leaf vxlan-instance {
            type uint32 {
              range "1..2";
            }
          } //vxlan-instance

          container default-route-tag {
            description
                "Configure default-route-tag to match against export policies";
            leaf t0x01..0xff {
              type string;
              description
                  "[1..255] - accepts in decimal or hex";
            } //t0x01..0xff

          } //container default-route-tag

          leaf send-evpn-encap {
            type boolean;
            description
                "Enable/Disable sending Vxlan Encap";
          }

          leaf send-imet-ir-on-ndf {
            type boolean;
            description
                "Configure IMET-IR on NDF";
          }

          leaf shutdown {
            type boolean;
            description
                "Administratively Enable/Disable BGP-EVPN vxlan";
          }

        } //list vxlan

      } //container bgp-evpn

      container bgp-vpls {
        presence
            "Configure BGP-VPLS";
        container max-ve-id {
          description
              "Configure maximum vpls-edge id for BGP-VPLS";
          leaf value {
            type uint32 {
              range "1..65535";
            }
          } //value

        } //container max-ve-id

        leaf shutdown {
          type boolean;
          description
              "Administratively Enable/Disable BGP-VPLS";
        }

        container ve-name {
          description
              "Configure vpls-edge name for BGP-VPLS";
          leaf name {
            type string {
              length "1..32";
            }
          } //name

          container ve-id {
            description
                "Configure vpls-edge identifier";
            leaf value {
              type uint32 {
                range "1..65535";
              }
            } //value

          } //container ve-id

        } //container ve-name

      } //container bgp-vpls

      list endpoint {
        key "endpoint-name";
        description
            "Configure a service end-point";
        leaf endpoint-name {
          type string {
            length "1..32";
          }
        } //endpoint-name

        leaf auto-learn-mac-protect {
          type boolean;
          description
              "Enable/disable automatic update of MAC protect list";
        }

        leaf block-on-mesh-failure {
          type boolean;
          description
              "Block traffic on mesh-SDP failure";
        }

        container description {
          description
              "Description for the service end-point";
          leaf description-string {
            type string {
              length "1..80";
            }
          } //description-string

        } //container description

        leaf ignore-standby-signaling {
          type boolean;
          description
              "Ignore 'standby-bit' received from LDP peer";
        }

        leaf mac-pinning {
          type boolean;
          description
              "Enable/disable MAC address pinning on this endpoint";
        }

        container max-nbr-mac-addr {
          description
              "Configure the maximum number of MAC entries in the FDB from this endpoint";
          leaf table-size {
            type string;
            description
                "Attribute table-size for max-nbr-mac-addr";
          } //table-size

        } //container max-nbr-mac-addr

        container restrict-protected-src {
          description
              "Enable/disable protected src MAC restriction";
          leaf discard-frame {
            type boolean;
            description
                "keyword - discard frame and trap on a protected MAC";
          } //discard-frame

          leaf alarm-only {
            type boolean;
            description
                "keyword: trap on a protected MAC";
          } //alarm-only

        } //container restrict-protected-src

        container revert-time {
          description
              "Configure the time to wait before reverting to primary spoke-sdp";
          leaf revert-time {
            type uint32 {
              range "0..600";
            }
            description
                "[0..600] seconds";
          } //revert-time

          leaf infinite {
            type boolean;
            description
                "keyword - makes endpoint non-revertive";
          } //infinite

        } //container revert-time

        list static-mac {
          key "ieee-address";
          description
              "Configure a static mac entry";
          leaf ieee-address {
            type string;
            description
                "xx:xx:xx:xx:xx:xx or xx-xx-xx-xx-xx-xx (cannot be all zeros)";
          } //ieee-address

        } //list static-mac

        leaf suppress-standby-signaling {
          type boolean;
          description
              "Suppress sending of 'standby-bit' to the LDP peer";
        }

        container mc-endpoint {
          description
              "Configure Multi-Chassis end-point";
          leaf mc-ep-id {
            type uint64 {
              range "1..4294967295";
            }
          } //mc-ep-id

          container mc-ep-peer {
            description
                "Configure multi-chassis end-point peer";
            leaf ip-address {
              type inet:ip-address;
              description
                  "ip-address a.b.c.d (no multicast address)";
            } //ip-address

            leaf name {
              type string {
                length "1..32";
              }
              description
                  "32 char max";
            } //name

          } //container mc-ep-peer

        } //container mc-endpoint

      } //list endpoint

      container eth-cfm {
        description
            "Configure CFM parameters";
        container tunnel-fault {
          description
              "Accept/Ignore tunnel fault notification";
          leaf tunnel-fault-id {
            type enumeration {
              enum accept;
              enum ignore;
            }
          } //tunnel-fault-id

        } //container tunnel-fault

        leaf vmep-extensions {
          type boolean;
          status "obsolete";
          description
              "Enable/Disable enhanced Virtual MEP functionality";
        }

        list mep {
          key "mep-id domain association";
          description
              "Configure a CFM Virtual Maintenance Endpoint";
          leaf mep-id {
            type int16 {
              range "1..8191";
            }
          } //mep-id

          leaf domain {
            type uint32 {
              range "1..4294967295";
            }
          } //domain

          leaf association {
            type uint32 {
              range "1..4294967295";
            }
          } //association

          leaf ccm-enable {
            type boolean;
            description
                "Enable/Disable Generation of CCM messages";
          }

          container ccm-ltm-priority {
            description
                "Configure the priority of CCM and LTM messages";
            leaf priority {
              type uint16 {
                range "0..7";
              }
              description
                  "[0..7] - Default highest priority on bridge-port";
            } //priority

          } //container ccm-ltm-priority

          container ccm-padding-size {
            description
                "Insert additional padding in the CCM packets";
            leaf ccm-padding {
              type uint32 {
                range "3..1500";
              }
              description
                  "3..1500 octets";
            } //ccm-padding

          } //container ccm-padding-size

          container description {
            description
                "Add/remove a text description for the MEP";
            leaf description-string {
              type string {
              }
              description
                  "[80 chars max]";
            } //description-string

          } //container description

          container low-priority-defect {
            description
                "Configure the Lowest Priority Defect for the MEP";
            leaf allDef-macRemErrXcon-remErrXcon-errXcon-xcon-noXcon {
              type enumeration {
                enum allDef;
                enum macRemErrXcon;
                enum remErrXcon;
                enum errXcon;
                enum xcon;
                enum noXcon;
              }
              description
                  "keywords";
            } //allDef-macRemErrXcon-remErrXcon-errXcon-xcon-noXcon

          } //container low-priority-defect

          container mac-address {
            description
                "Configure the MAC Address for the MEP";
            leaf mac-address {
              type yang:mac-address;
            } //mac-address

          } //container mac-address

          container one-way-delay-threshold {
            description
                "Configure the one-way-delay test threshold";
            leaf seconds {
              type uint32 {
                range "0..600";
              }
              default 3;
              description
                  "[0..600] Default: 3";
            } //seconds

          } //container one-way-delay-threshold

          leaf shutdown {
            type boolean;
            description
                "Administratively enable/disable the MEP";
          }

          container alarm-notification {
            description
                "Configure the MEP alarm notification parameters";
            container fng-alarm-time {
              description
                  "Configure the Fault Notification Generation (FNG) alarm time";
              leaf time {
                type enumeration {
                  enum 0;
                  enum 250;
                  enum 500;
                  enum 1000;
                }
                default 0;
                description
                    "[0,250,500,1000] centi-seconds - Default: 0";
              } //time

            } //container fng-alarm-time

            container fng-reset-time {
              description
                  "Configure the Fault Notification Generation (FNG) reset time";
              leaf time {
                type enumeration {
                  enum 0;
                  enum 250;
                  enum 500;
                  enum 1000;
                }
                default 0;
                description
                    "[0,250,500,1000] centi-seconds - Default: 0";
              } //time

            } //container fng-reset-time

          } //container alarm-notification

          container eth-test-enable {
            presence
                "Enable/Disable eth-test functionality on MEP";
            container bit-error-threshold {
              description
                  "Configure the bit error trap threshold";
              leaf bit-errors {
                type uint32 {
                  range "0..11840";
                }
                default 1;
                description
                    "[0..11840] Default: 1";
              } //bit-errors

            } //container bit-error-threshold

            container test-pattern {
              description
                  "Configure the test pattern for eth-test frames";
              leaf all-zeros-all-ones {
                type enumeration {
                  enum all-zeros;
                  enum all-ones;
                }
                default "all-zeros";
                description
                    "keywords - Test pattern - default: all-zeros";
              } //all-zeros-all-ones

              leaf crc-enable {
                type boolean;
                description
                    "keyword - Generate CRC checksum";
              } //crc-enable

            } //container test-pattern

          } //container eth-test-enable

          container grace {
            description
                "Configure the generation and reception of grace period parameters";
            container eth-ed {
              description
                  "Configure the generation and reception of eth-ed grace period parameters";
              container max-rx-defect-window {
                description
                    "Configure/Disable an upper maximum defect window length; when disabled the 
                     advertised value from the peer will be used; when enabled the lower of the 
                     configured value or the advertised value from the peer will be used";
                leaf seconds {
                  type uint32 {
                    range "1..86400";
                  }
                  description
                      "[1..86400] - Default: no max-rx-defect-window";
                } //seconds

              } //container max-rx-defect-window

              container priority {
                description
                    "Configure/Disable the transmission priority value for ETH-ED PDUs; when 
                     disabled the priority value of ccm-ltm-priority associated with this MEP will 
                     be used";
                leaf priority {
                  type int32 {
                    range "0..7";
                  }
                  default 0;
                  description
                      "[0..7] - Default: no priority";
                } //priority

              } //container priority

              leaf rx-eth-ed {
                type boolean;
                description
                    "Enable/Disable the receiving and processing of ETH-ED PDUs";
              }

              leaf tx-eth-ed {
                type boolean;
                description
                    "Enable/Disable the transmission of ETH-ED PDUs";
              }

            } //container eth-ed

            container eth-vsm-grace {
              description
                  "Configure the generation and reception of sros vendor specific message (vsm) 
                   grace period parameters";
              leaf rx-eth-vsm-grace {
                type boolean;
                description
                    "Enable/Disable the receiving and processing of vendor specific message (vsm) 
                     grace period notifications";
              }

              leaf tx-eth-vsm-grace {
                type boolean;
                description
                    "Enable/Disable the transmission of vsm grace period notifications";
              }

            } //container eth-vsm-grace

          } //container grace

        } //list mep

      } //container eth-cfm

      container gsmp {
        description
            "Configure GSMP connections maintained in this service";
        leaf shutdown {
          type boolean;
          description
              "Administratively enable/disable GSMP";
        }

        list group {
          key "name";
          description
              "Provision a GSMP neighbor group";
          leaf name {
            type string {
              length "1..32";
            }
          } //name

          container description {
            description
                "Description for the GSMP group";
            leaf description-string {
              type string {
                length "1..80";
              }
            } //description-string

          } //container description

          container hold-multiplier {
            description
                "Configure hold-multiplier for the GSMP connections in this group";
            leaf multiplier {
              type uint32 {
                range "1..100";
              }
            } //multiplier

          } //container hold-multiplier

          leaf idle-filter {
            type boolean;
            description
                "enable/disable filtering ANCP messages from IDLE DSL lines";
          }

          container keepalive {
            description
                "Configure keepalive value for the GSMP connections in this group";
            leaf seconds {
              type uint32 {
                range "1..25";
              }
            } //seconds

          } //container keepalive

          leaf persistency-database {
            type boolean;
            description
                "enable/disable storing of DSL line information when the GSMP connection 
                 terminates";
          }

          leaf shutdown {
            type boolean;
            description
                "Administratively enable/disable the GSMP group";
          }

          container ancp {
            presence
                "configure ANCP parameters for this GSMP group";
            leaf dynamic-topology-discover {
              type boolean;
              description
                  "Enable/disable the ANCP dynamic topology discovery capability";
            }

            leaf oam {
              type boolean;
              description
                  "Enable/disable the ANCP OAM capability";
            }

          } //container ancp

          list neighbor {
            key "ip-address";
            description
                "Add/remove a neighbor in the GSMP group";
            leaf ip-address {
              type inet:ip-address;
              description
                  "ip-address a.b.c.d ( unicast address only)";
            } //ip-address

            container description {
              description
                  "Description for the GSMP neighbor";
              leaf description-string {
                type string {
                  length "1..80";
                }
              } //description-string

            } //container description

            container local-address {
              description
                  "Configure the local address for this neighbor";
              leaf ip-address {
                type inet:ip-address;
                description
                    "ip-address a.b.c.d ( unicast address only)";
              } //ip-address

            } //container local-address

            container priority-marking {
              description
                  "Configure the type of priority marking to be used";
              leaf prec {
                type int32 {
                  range "0..7";
                }
              } //prec

              leaf dscp {
                type string {
                  length "1..32";
                }
                description
                    "Attribute dscp-name for priority-marking";
              } //dscp

            } //container priority-marking

            leaf shutdown {
              type boolean;
              description
                  "Administratively enable/disable the neighbor";
            }

          } //list neighbor

        } //list group

      } //container gsmp

      container igmp-host-tracking {
        description
            "Configure IGMP host tracking";
        container expiry-time {
          description
              "Configure the time that the system continues to track inactive hosts";
          leaf expiry-time {
            type uint32 {
              range "1..65535";
            }
            description
                "[1..65535] seconds";
          } //expiry-time

        } //container expiry-time

        leaf shutdown {
          type boolean;
          description
              "Administratively enable/disable IGMP host tracking";
        }

      } //container igmp-host-tracking

      uses "conf-svc-vpls-igmp-r13:alu-conf-svc-vpls-igmp-r13";
      list interface {
        key "ip-int-name";
        description
            "Create/delete or configure an IP interface";
        leaf ip-int-name {
          type string {
            length "1..32";
          }
          description
              "[32 chars max] (must start with a letter)";
        } //ip-int-name

        container address {
          description
              "Assigns an IP address/IP subnet/broadcast address format to the interface";
          leaf ip-address-mask {
            type string;
            description
                "ip-address a.b.c.d (no multicast address)";
          } //ip-address-mask

          leaf netmask {
            type string;
            description
                "a.b.c.d (network bits all 1 and host bits all 0)";
          } //netmask

        } //container address

        container arp-timeout {
          description
              "Configures timeout for an ARP entry learned on the interface";
          leaf seconds {
            type uint32 {
              range "0..65535";
            }
            default 14400;
          } //seconds

        } //container arp-timeout

        container delayed-enable {
          status "obsolete";
          leaf seconds {
            type uint32 {
              range "1..65535";
            }
          } //seconds

          leaf init-only {
            type boolean;
          } //init-only

        } //container delayed-enable

        container description {
          description
              "Description for VPLS interface";
          leaf long-description-string {
            type string {
              length "1..160";
            }
          } //long-description-string

        } //container description

        container mac {
          description
              "Assign a MAC address to the interface";
          leaf ieee-address {
            type string;
            description
                "xx:xx:xx:xx:xx:xx or xx-xx-xx-xx-xx-xx (cannot be all zeros)";
          } //ieee-address

        } //container mac

        leaf shutdown {
          type boolean;
          description
              "Administratively enable/disable the interface";
        }

        list static-arp {
          key "ieee-address";
          description
              "Configure a static ARP entry for the interface";
          leaf ip-address {
            type inet:ip-address;
          } //ip-address

          leaf ieee-address {
            type string;
            description
                "xx:xx:xx:xx:xx:xx or xx-xx-xx-xx-xx-xx (cannot be all zeros)";
          } //ieee-address

          leaf unnumbered {
            type boolean;
          } //unnumbered

        } //list static-arp

        container unnumbered {
          status "obsolete";
          description
              "Configure the interface as an unnumbered interface";
          leaf ip-int-name-ip-address {
            type string;
            description
                "Attribute ip-int-name|ip-address for unnumbered";
          } //ip-int-name-ip-address

        } //container unnumbered

        container hold-time {
          description
              "Configure the hold times (up/down) for the interface";
          list down {
            key "ip";
            description
                "Configure the hold time when the interface is coming up";
            leaf ip {
              type boolean;
            } //ip

            leaf seconds {
              type uint32 {
                range "1..1200";
              }
            } //seconds

            leaf init-only {
              type boolean;
            } //init-only

          } //list down

          list up {
            key "ip";
            description
                "Configure the hold time when the interface is going down";
            leaf ip {
              type boolean;
            } //ip

            leaf seconds {
              type uint32 {
                range "1..1200";
              }
            } //seconds

          } //list up

        } //container hold-time

      } //list interface

      container isid-policy {
        description
            "Configure ISID policy information";
        list entry {
          key "range-entry-id";
          description
              "Configure ISID policy entry information";
          leaf range-entry-id {
            type uint32 {
              range "1..8191";
            }
          } //range-entry-id

          leaf advertise-local {
            type boolean;
            description
                "Configure local advertisement of the range";
          }

          container range {
            description
                "Configure ISID range for the entry";
            leaf isid {
              type uint32 {
                range "1..16777215";
              }
            } //isid

            leaf to {
              type uint32 {
                range "1..16777215";
              }
            } //to

          } //container range

          leaf use-def-mcast {
            type boolean;
            description
                "Use default multicast tree to propogate ISID range";
          }

        } //list entry

      } //container isid-policy

      container load-balancing {
        description
            "Configure load balancing information";
        leaf per-service-hashing {
          type boolean;
          description
              "Enable/disable per service hashing";
        }

        leaf spi-load-balancing {
          type boolean;
          description
              "Enable/disable SPI load balancing";
        }

        leaf teid-load-balancing {
          type boolean;
          description
              "Enable/disable TEID load balancing";
        }

      } //container load-balancing

      uses "conf-svc-vpls-macmo-r13:alu-conf-svc-vpls-macmo-r13";
      container mac-notification {
        description
            "Configure MAC-notification messages for vpls service";
        container count {
          description
              "Configure count for MAC-notification messages";
          leaf value {
            type uint32 {
              range "1..10";
            }
          } //value

        } //container count

        container interval {
          description
              "Configure interval for MAC-notification messages";
          leaf deci-seconds {
            type uint32 {
              range "1..100";
            }
            description
                "[1..100] tenth of a second";
          } //deci-seconds

        } //container interval

        container renotify {
          description
              "Configure re-notify interval for MAC-notification messages";
          leaf seconds {
            type uint32 {
              range "240..840";
            }
          } //seconds

        } //container renotify

        leaf shutdown {
          type boolean;
          description
              "Configure admin state for MAC-notification messages";
        }

      } //container mac-notification

      uses "conf-svc-vpls-macpr-r13:alu-conf-svc-vpls-macpr-r13";
      container mcr-default-gtw {
        description
            "Configure a multi-chassis-ring default gateway";
        container ip {
          description
              "Configure the mc-ring default gateway ip address";
          leaf ip-address {
            type inet:ip-address;
          } //ip-address

        } //container ip

        container mac {
          description
              "Configure the mc-ring default gateway mac address";
          leaf ieee-address {
            type string;
            description
                "xx:xx:xx:xx:xx:xx or xx-xx-xx-xx-xx-xx (cannot be all zeros)";
          } //ieee-address

        } //container mac

      } //container mcr-default-gtw

      uses "conf-svc-vpls-meshs-r13:alu-conf-svc-vpls-meshs-r13";
      uses "conf-svc-vpls-mld-r13:alu-conf-svc-vpls-mld-r13";
      container mrp {
        description
            "Configure MRP attributes";
        leaf shutdown {
          type boolean;
          description
              "Administratively enable or disable MRP";
        }

        container mmrp {
          description
              "Configure MMRP attributes";
          container attribute-table-high-wmark {
            description
                "Configure the high watermark for the MMRP attribute table";
            leaf high-water-mark {
              type uint32 {
                range "0..100";
              }
            } //high-water-mark

          } //container attribute-table-high-wmark

          container attribute-table-low-wmark {
            description
                "Configure the low watermark for the MMRP attribute table";
            leaf low-water-mark {
              type uint32 {
                range "0..100";
              }
            } //low-water-mark

          } //container attribute-table-low-wmark

          container attribute-table-size {
            description
                "Configure MMRP max attributes";
            leaf max-attributes {
              type uint32 {
                range "1..8192";
              }
              description
                  "Attribute max-attributes for attribute-table-size";
            } //max-attributes

          } //container attribute-table-size

          leaf end-station-only {
            type boolean;
            description
                "Specify if only for end-station";
          }

          container flood-time {
            description
                "Configure MMRP flood-time";
            leaf flood-time {
              type int32 {
                range "3..600";
              }
              description
                  "[3..600] secs";
            } //flood-time

          } //container flood-time

          leaf shutdown {
            type boolean;
            description
                "Administratively enable or disable MMRP";
          }

        } //container mmrp

        container mvrp {
          description
              "Configure MVRP attributes";
          container attribute-table-high-wmark {
            description
                "Configure the high watermark for the MVRP attribute table";
            leaf high-water-mark {
              type uint32 {
                range "0..100";
              }
            } //high-water-mark

          } //container attribute-table-high-wmark

          container attribute-table-low-wmark {
            description
                "Configure the low watermark for the MVRP attribute table";
            leaf low-water-mark {
              type uint32 {
                range "0..100";
              }
            } //low-water-mark

          } //container attribute-table-low-wmark

          container attribute-table-size {
            description
                "Configure MVRP max attributes";
            leaf max-attributes {
              type uint32 {
                range "1..4095";
              }
            } //max-attributes

          } //container attribute-table-size

          container hold-time {
            description
                "Configure MVRP hold-time";
            leaf minutes {
              type int32 {
                range "1..30";
              }
            } //minutes

          } //container hold-time

          leaf shutdown {
            type boolean;
            description
                "Administratively enable or disable MVRP";
          }

        } //container mvrp

      } //container mrp

      container pbb {
        description
            "Configure PBB parameters for VPLS service";
        leaf force-qtag-forwarding {
          type boolean;
          description
              "Enable/Disable 802.1q tag forwarding";
        }

        leaf propagate-mac-flush-from-bvpls {
          type boolean;
          description
              "Configure to propagate mac-flush from b-vpls into local i-vpls";
        }

        leaf send-bvpls-evpn-flush {
          type boolean;
          description
              "Configure whether to send b-VPLS EVPN flush";
        }

        container send-bvpls-flush {
          description
              "Enable/disable sending MAC withdraw message in b-vpls for i-vpls";
          leaf all-but-mine {
            type boolean;
          } //all-but-mine

          leaf all-from-me {
            type boolean;
          } //all-from-me

        } //container send-bvpls-flush

        leaf send-flush-on-bvpls-failure {
          type boolean;
          description
              "Configure to send flush-all-from-me on b-vpls failure";
        }

        container source-bmac {
          description
              "Configure backbone source MAC address used for PBB";
          leaf ieee-address {
            type alu:ieee-address;
            description
                "xx:xx:xx:xx:xx:xx or xx-xx-xx-xx-xx-xx";
          } //ieee-address

        } //container source-bmac

        leaf use-es-bmac {
          type boolean;
          description
              "Configure to enable dual-homing to use ethernet-segment backbone-mac";
        }

        leaf use-sap-bmac {
          type boolean;
          description
              "Configure to enable dual-homing to use sap backbone-mac lsb";
        }

        container backbone-vpls {
          description
              "Configure b-vpls service associated with this i-vpls";
          leaf service-id {
            type string;
            description
                "Attribute service-id for backbone-vpls";
          } //service-id

          leaf isid {
            type uint32 {
              range "0..16777215";
            }
          } //isid

          leaf stp {
            type boolean;
            description
                "Enable/disable STP through Backbone VPLS service";
          }

          container igmp-snooping {
            description
                "Configure IGMP snooping attributes of the Backbone VPLS service";
            list mrouter-dest {
              key "mac-name";
              description
                  "Configure Destination MAC-Address-Name in the Backbone VPLS to reach a 
                   specific IGMP Snooping MRouter";
              leaf mac-name {
                type string {
                  length "1..32";
                }
              } //mac-name

            } //list mrouter-dest

          } //container igmp-snooping

          container mld-snooping {
            description
                "Configure MLD snooping attributes of the Backbone VPLS service";
            list mrouter-dest {
              key "mac-name";
              description
                  "Configure Destination MAC-Address-Name in the Backbone VPLS to reach a 
                   specific MLD Snooping MRouter";
              leaf mac-name {
                type string {
                  length "1..32";
                }
              } //mac-name

            } //list mrouter-dest

          } //container mld-snooping

          list sap {
            key "sap-id";
            description
                "Configure attributes of a SAP on the Backbone VPLS service";
            leaf sap-id {
              type string;
              description
                  "Attribute sap-id for sap";
            } //sap-id

            container igmp-snooping {
              description
                  "Configure IGMP snooping attributes of a SAP on the Backbone VPLS service";
              leaf mrouter-port {
                type boolean;
                description
                    "Configure the SDP Binding on the Backbone VPLS service as a multicast router 
                     port";
              }

            } //container igmp-snooping

            container mld-snooping {
              description
                  "Configure MLD snooping attributes of a SAP on the Backbone VPLS service";
              leaf mrouter-port {
                type boolean;
                description
                    "Configure the SDP Binding on the Backbone VPLS service as a multicast router 
                     port";
              }

            } //container mld-snooping

          } //list sap

          list sdp {
            key "sdp-id-vc-id";
            description
                "Configure attributes of an SDP Binding on the Backbone VPLS service";
            leaf sdp-id-vc-id {
              type string;
              description
                  "sdp-id - [1..32767] 
                   vc-id - [1..4294967295]";
            } //sdp-id-vc-id

            container igmp-snooping {
              description
                  "Configure IGMP snooping attributes of an SDP Binding on the Backbone VPLS 
                   service";
              leaf mrouter-port {
                type boolean;
                description
                    "Configure the SDP Binding on the Backbone VPLS service as a multicast router 
                     port";
              }

            } //container igmp-snooping

            container mld-snooping {
              description
                  "Configure MLD snooping attributes of an SDP Binding on the Backbone VPLS 
                   service";
              leaf mrouter-port {
                type boolean;
                description
                    "Configure the SDP Binding on the Backbone VPLS service as a multicast router 
                     port";
              }

            } //container mld-snooping

          } //list sdp

        } //container backbone-vpls

      } //container pbb

      uses "conf-svc-vpls-pim-r13:alu-conf-svc-vpls-pim-r13";
      container provider-tunnel {
        presence
            "Configure P2MP BUM provider tunnel";
        container inclusive {
          description
              "Configure inclusive provider tunnel parameters";
          container data-delay-interval {
            description
                "Configure data delay interval";
            leaf seconds {
              type int32 {
                range "3..180";
              }
            } //seconds

          } //container data-delay-interval

          leaf mldp {
            type boolean;
            description
                "Enable/Disable MLDP";
          }

          container owner {
            description
                "Configure provider-tunnel owner";
            leaf owner-id {
              type enumeration {
                enum bgp-ad;
                enum bgp-vpls;
                enum bgp-evpn-mpls;
              }
            } //owner-id

          } //container owner

          leaf root-and-leaf {
            type boolean;
            description
                "Configure LSP node type";
          }

          leaf shutdown {
            type boolean;
            description
                "Administratively enable/disable the service";
          }

          container rsvp {
            presence
                "Configure RSVP parameters";
            container lsp-template {
              description
                  "Configure LSP template name";
              leaf p2mp-lsp-template-name {
                type string {
                  length "1..32";
                }
              } //p2mp-lsp-template-name

            } //container lsp-template

          } //container rsvp

        } //container inclusive

      } //container provider-tunnel

      container proxy-arp {
        presence
            "Configure proxy ARP information";
        container age-time {
          description
              "Configure aging timer for proxy ARP entries";
          leaf seconds {
            type int32 {
              range "60..86400";
            }
          } //seconds

        } //container age-time

        container dup-detect {
          description
              "Configure anti-spoofing MAC address information";
          leaf anti-spoof-mac {
            type alu:ieee-address;
            description
                "xx-xx-xx-xx-xx-xx or xx:xx:xx:xx:xx:xx (hex chars)";
          } //anti-spoof-mac

          leaf window {
            type int32 {
              range "1..15";
            }
            default 3;
            description
                "[1..15] minutes - default:3";
          } //window

          leaf num-moves {
            type int32 {
              range "3..10";
            }
            default 5;
            description
                "[3..10] - default:5";
          } //num-moves

          leaf hold-down {
            type string;
            description
                "[2..60] default=9 | max - permanent hold";
          } //hold-down

          leaf static-black-hole {
            type boolean;
          } //static-black-hole

        } //container dup-detect

        leaf dynamic-arp-populate {
          type boolean;
          description
              "Configure population of dynamic proxy ARP entries";
        }

        container evpn-route-tag {
          description
              "Configure EVPN Route Tag information";
          leaf t0x01..0xff {
            type string;
            description
                "[1..255] - accepts in decimal or hex";
          } //t0x01..0xff

        } //container evpn-route-tag

        leaf garp-flood-evpn {
          type boolean;
          description
              "Configure to flood GARP request/replys into EVPN";
        }

        container send-refresh {
          description
              "Configure send refresh time";
          leaf seconds {
            type int32 {
              range "120..86400";
            }
          } //seconds

        } //container send-refresh

        leaf shutdown {
          type boolean;
          description
              "Administratively enable/disable proxy ARP configuration";
        }

        list static {
          key "ip-address";
          description
              "Configure static IP address to MAC address associations";
          leaf ip-address {
            type inet:ip-address;
          } //ip-address

          leaf ieee-address {
            type alu:ieee-address;
            description
                "xx-xx-xx-xx-xx-xx or xx:xx:xx:xx:xx:xx";
          } //ieee-address

        } //list static

        container table-size {
          description
              "Configure the maximum number of entries in the proxy ARP table";
          leaf table-size {
            type uint32 {
              range "1..16383";
            }
            description
                "Attribute table-size for table-size";
          } //table-size

        } //container table-size

        leaf unknown-arp-request-flood-evpn {
          type boolean;
          description
              "Configure to flood unknown ARP request";
        }

        list dynamic {
          key "ip-address";
          description
              "Configure dynamic entry information";
          leaf ip-address {
            type inet:ip-address;
          } //ip-address

          container mac-list {
            description
                "Configure MAC list";
            leaf name {
              type string;
            } //name

          } //container mac-list

          container resolve {
            description
                "Configure address resolve time in minutes";
            leaf mins {
              type uint32 {
                range "1..60";
              }
              description
                  "[1..60 mins] - default is 5 min";
            } //mins

          } //container resolve

        } //list dynamic

      } //container proxy-arp

      container proxy-nd {
        presence
            "Configure proxy ND information";
        container age-time {
          description
              "Configure aging timer for proxy ND entries";
          leaf seconds {
            type int32 {
              range "60..86400";
            }
          } //seconds

        } //container age-time

        container dup-detect {
          description
              "Configure anti-spoofing MAC address information";
          leaf anti-spoof-mac {
            type alu:ieee-address;
            description
                "xx-xx-xx-xx-xx-xx or xx:xx:xx:xx:xx:xx (hex chars)";
          } //anti-spoof-mac

          leaf window {
            type int32 {
              range "1..15";
            }
            default 3;
            description
                "[1..15] minutes - default:3";
          } //window

          leaf num-moves {
            type int32 {
              range "3..10";
            }
            default 5;
            description
                "[3..10] - default:5";
          } //num-moves

          leaf hold-down {
            type string;
            description
                "[2..60] default=9 | max - permanent hold";
          } //hold-down

          leaf static-black-hole {
            type boolean;
          } //static-black-hole

        } //container dup-detect

        leaf dynamic-nd-populate {
          type boolean;
          description
              "Configure population of dynamic proxy ND entries";
        }

        container evpn-nd-advertise {
          description
              "Configure EVPN Neighbor Discovery advertisements";
          leaf evpn-nd-advertise-id {
            type enumeration {
              enum host;
              enum router;
            }
          } //evpn-nd-advertise-id

        } //container evpn-nd-advertise

        container evpn-route-tag {
          description
              "Configure EVPN Route Tag information";
          leaf t0x01..0xff {
            type string;
            description
                "[1..255] - accepts in decimal or hex";
          } //t0x01..0xff

        } //container evpn-route-tag

        leaf host-unsolicited-na-flood-evpn {
          type boolean;
          description
              "Configure whether to flood evpn with host neighbor advertisement";
        }

        leaf router-unsolicited-na-flood-evpn {
          type boolean;
          description
              "Configure whether to flood evpn with router neighbor advertisement";
        }

        container send-refresh {
          description
              "Configure send refresh time";
          leaf seconds {
            type int32 {
              range "120..86400";
            }
          } //seconds

        } //container send-refresh

        leaf shutdown {
          type boolean;
          description
              "Administratively enable/disable proxy ND configuration";
        }

        list static {
          key "ipv6-address";
          description
              "Configure static IP address to MAC address associations";
          leaf ipv6-address {
            type inet:ipv6-address;
            description
                "Attribute ipv6-address for static";
          } //ipv6-address

          leaf ieee-address {
            type alu:ieee-address;
            description
                "xx-xx-xx-xx-xx-xx or xx:xx:xx:xx:xx:xx";
          } //ieee-address

          leaf static-id {
            type enumeration {
              enum host;
              enum router;
            }
          } //static-id

        } //list static

        container table-size {
          description
              "Configure the maximum number of entries in the proxy ND table";
          leaf table-size {
            type uint32 {
              range "1..16383";
            }
            description
                "Attribute table-size for table-size";
          } //table-size

        } //container table-size

        leaf unknown-ns-flood-evpn {
          type boolean;
          description
              "Configure to flood unknown ND solicitation";
        }

        list dynamic {
          key "ipv6-address";
          description
              "Configure dynamic entry information";
          leaf ipv6-address {
            type inet:ipv6-address;
            description
                "Attribute ipv6-address for dynamic";
          } //ipv6-address

          container mac-list {
            description
                "Configure MAC list";
            leaf name {
              type string;
            } //name

          } //container mac-list

          container resolve {
            description
                "Configure address resolve time in minutes";
            leaf mins {
              type uint32 {
                range "1..60";
              }
              description
                  "[1..60 mins] - default is 5 min";
            } //mins

          } //container resolve

        } //list dynamic

      } //container proxy-nd

      uses "conf-svc-vpls-sap-r13:alu-conf-svc-vpls-sap-r13";
      list site {
        key "name";
        description
            "Configure a VPLS site";
        leaf name {
          type string {
            length "1..32";
          }
        } //name

        container boot-timer {
          description
              "Configure/Override site boot-timer";
          leaf seconds {
            type int32 {
              range "0..600";
            }
          } //seconds

        } //container boot-timer

        container failed-threshold {
          description
              "Configure threshold for the site to be declared down";
          leaf all {
            type boolean;
          } //all

          leaf failed-threshold-id {
            type int32 {
              range "1..1000";
            }
          } //failed-threshold-id

        } //container failed-threshold

        leaf mesh-sdp-binding {
          type boolean;
          description
              "Enable/Disable application to all Mesh-SDP";
        }

        container monitor-oper-group {
          description
              "Configure an Operational-Group to monitor";
          leaf name {
            type string {
              length "1..32";
            }
          } //name

        } //container monitor-oper-group

        container sap {
          description
              "Configure a SAP for the site";
          leaf sap-id {
            type string;
            description
                "Attribute sap-id for sap";
          } //sap-id

        } //container sap

        leaf shutdown {
          type boolean;
          description
              "Administratively enable/disable the site";
        }

        container site-activation-timer {
          description
              "Configure/Override site activation timer";
          leaf seconds {
            type int32 {
              range "0..100";
            }
          } //seconds

        } //container site-activation-timer

        container site-id {
          description
              "Configure site identifier";
          leaf value {
            type uint32 {
              range "1..65535";
            }
          } //value

        } //container site-id

        container site-min-down-timer {
          description
              "Configure minimum down timer for the site";
          leaf seconds {
            type int32 {
              range "0..100";
            }
          } //seconds

        } //container site-min-down-timer

        container split-horizon-group {
          description
              "Configure a split-horizon-group";
          leaf group-name {
            type string {
              length "1..32";
            }
          } //group-name

        } //container split-horizon-group

        container spoke-sdp {
          description
              "Configure a spoke-SDP";
          leaf sdp-id-vc-id {
            type string;
          } //sdp-id-vc-id

        } //container spoke-sdp

      } //list site

      container spb {
        description
            "Configure Shortest Path Bridging";
        leaf isis-instance-id {
          type uint32 {
            range "1024..2047";
          }
        } //isis-instance-id

        leaf spb-id {
          type uint32 {
            range "1024..2047";
          }
          description
              "isis-instance";
        } //spb-id

        leaf fid {
          type uint32 {
            range "1..4095";
          }
        } //fid

        container lsp-lifetime {
          description
              "Configure LSP lifetime";
          leaf seconds {
            type int32 {
              range "350..65535";
            }
          } //seconds

        } //container lsp-lifetime

        container lsp-refresh-interval {
          description
              "Configure LSP refresh interval";
          leaf seconds {
            type uint32 {
              range "150..65535";
            }
            default 600;
          } //seconds

          leaf half-lifetime {
            type enumeration {
              enum enable;
              enum disable;
            }
          } //half-lifetime

        } //container lsp-refresh-interval

        container lsp-wait {
          status "obsolete";
          description
              "Configure ISIS LSP wait times";
          leaf lsp-wait {
            type int32 {
              range "1..120";
            }
            description
                "[1..120] - seconds";
          } //lsp-wait

          leaf initial-wait {
            type uint32 {
              range "0..100";
            }
            description
                "[0..100] - seconds";
          } //initial-wait

          leaf second-wait {
            type uint32 {
              range "1..100";
            }
            description
                "[1..100] - seconds";
          } //second-wait

        } //container lsp-wait

        container overload {
          description
              "Configure the local router so that it appears to be overloaded";
          leaf timeout {
            type int32 {
              range "60..1800";
            }
          } //timeout

        } //container overload

        container overload-on-boot {
          description
              "Configure the local router so that it appears to be overloaded at boot up";
          leaf timeout {
            type int32 {
              range "60..1800";
            }
          } //timeout

        } //container overload-on-boot

        leaf shutdown {
          type boolean;
          description
              "Administratively enable or disable the operation of ISIS";
        }

        container spf-wait {
          status "obsolete";
          description
              "Configure ISIS SPF wait times";
          leaf spf-wait {
            type int32 {
              range "1..120";
            }
            description
                "[1..120] - seconds";
          } //spf-wait

          leaf initial-wait {
            type int32 {
              range "10..100000";
            }
            description
                "[10..100000] - milliseconds";
          } //initial-wait

          leaf second-wait {
            type int32 {
              range "1..100000";
            }
            description
                "[1..100000] - milliseconds";
          } //second-wait

        } //container spf-wait

        container level {
          description
              "Configure SPB level information";
          leaf level-id {
            type uint32 {
            }
          } //level-id

          container bridge-priority {
            description
                "Configure bridge priority";
            leaf bridge-priority {
              type int32 {
                range "0..15";
              }
            } //bridge-priority

          } //container bridge-priority

          list ect-algorithm {
            key "fid-range";
            description
                "Configure ECT algorithm of forwarding range";
            leaf fid-range {
              type string {
                length "1..9";
              }
              description
                  "<1..4095>-<1..4095>";
            } //fid-range

            leaf low-path-id-high-path-id {
              type enumeration {
                enum low-path-id;
                enum high-path-id;
              }
            } //low-path-id-high-path-id

          } //list ect-algorithm

          container forwarding-tree-topology {
            description
                "Configure forwarding tree topology parameters";
            leaf unicast {
              type enumeration {
                enum spf;
                enum st;
              }
            } //unicast

          } //container forwarding-tree-topology

        } //container level

        container timers {
          description
              "Configure ISIS timers";
          container lsp-wait {
            leaf lsp-wait {
              type uint32 {
                range "10..120000";
              }
              description
                  "[10..120000] in milliseconds";
            } //lsp-wait

            leaf lsp-initial-wait {
              type uint32 {
                range "10..100000";
              }
              description
                  "[10..100000] in milliseconds";
            } //lsp-initial-wait

            leaf lsp-second-wait {
              type uint32 {
                range "10..100000";
              }
              description
                  "[10..100000] in milliseconds";
            } //lsp-second-wait

          } //container lsp-wait

          container spf-wait {
            leaf spf-wait {
              type uint32 {
                range "10..120000";
              }
              description
                  "[10..120000] in milliseconds";
            } //spf-wait

            leaf spf-initial-wait {
              type uint32 {
                range "10..100000";
              }
              description
                  "[10..100000] in milliseconds";
            } //spf-initial-wait

            leaf spf-second-wait {
              type uint32 {
                range "10..100000";
              }
              description
                  "[10..100000] in milliseconds";
            } //spf-second-wait

          } //container spf-wait

        } //container timers

      } //container spb

      uses "conf-svc-vpls-split-r13:alu-conf-svc-vpls-split-r13";
      uses "conf-svc-vpls-spoke-r13:alu-conf-svc-vpls-spoke-r13";
      container static-mac {
        description
            "Configure static MAC address information";
        list mac {
          key "ieee-address";
          description
              "Configure a static MAC address";
          leaf ieee-address {
            type string;
          } //ieee-address

          leaf sap {
            type string;
            description
                "Attribute sap-id for mac";
          } //sap

          leaf spoke-sdp {
            type string;
            description
                "sdp-id - [1..32767] 
                 vc-id - [1..4294967295]";
          } //spoke-sdp

          leaf monitor {
            type enumeration {
              enum fwd-status;
            }
          } //monitor

          leaf black-hole {
            type boolean;
          } //black-hole

        } //list mac

      } //container static-mac

      uses "conf-svc-vpls-stp-r13:alu-conf-svc-vpls-stp-r13";
      list video-interface {
        key "ip-int-name";
        description
            "Configure a video interface";
        leaf ip-int-name {
          type string {
            length "1..30";
          }
          description
              "[29 chars max] (must start with a letter)";
        } //ip-int-name

        container accounting-policy {
          description
              "Configure Accounting Policy";
          leaf acct-policy-id {
            type uint32 {
              range "1..99";
            }
          } //acct-policy-id

        } //container accounting-policy

        list address {
          key "ip-address-mask";
          description
              "Assigns an IP address to the interface";
          leaf ip-address-mask {
            type inet:ip-prefix;
            description
                "ip-address a.b.c.d 
                 mask [1..32]";
          } //ip-address-mask

        } //list address

        container cpu-protection {
          description
              "Configure a CPU protection policy";
          leaf policy-id {
            type uint32 {
              range "1..255";
            }
          } //policy-id

        } //container cpu-protection

        container description {
          description
              "Description for video interface";
          leaf description-string {
            type string {
              length "1..80";
            }
          } //description-string

        } //container description

        container gateway-ip {
          description
              "Configure gateway IP address";
          leaf ip-address {
            type inet:ip-address;
          } //ip-address

        } //container gateway-ip

        container multicast-service {
          description
              "Configure service ID of the associated multicast service";
          leaf service-id {
            type string;
            description
                "Attribute service-id for multicast-service";
          } //service-id

        } //container multicast-service

        container rt-client-src-address {
          description
              "Configure an IP address for the RT client";
          leaf ip-address {
            type inet:ip-address;
          } //ip-address

        } //container rt-client-src-address

        leaf shutdown {
          type boolean;
          description
              "Administratively enable/disable the video interface";
        }

        container video-sap {
          description
              "Configure group id for the video interface";
          leaf video-group-id {
            type uint32 {
              range "1..4";
            }
          } //video-group-id

          container egress {
            description
                "Configure egress parameters";
            container filter {
              description
                  "Configure an egress filter";
              leaf mac {
                type string;
                description
                    "[1..65535]|<name:64 char max>";
              } //mac

              leaf ip {
                type string;
                description
                    "[1..65535]|<name:64 char max>";
              } //ip

            } //container filter

            container qos {
              description
                  "Configure qos policy";
              leaf egress-qos-policy-id {
                type string;
                description
                    "[1..65535]|<name:64 char max>";
              } //egress-qos-policy-id

            } //container qos

          } //container egress

          container ingress {
            description
                "Configure ingress parameters";
            container filter {
              description
                  "Configure an ingress filter";
              leaf mac {
                type string;
                description
                    "[1..65535]|<name:64 char max>";
              } //mac

              leaf ip {
                type string;
                description
                    "[1..65535]|<name:64 char max>";
              } //ip

            } //container filter

            container qos {
              description
                  "Configure qos policy";
              leaf ingress-qos-policy-id {
                type string;
                description
                    "[1..65535]|<name:64 char max>";
              } //ingress-qos-policy-id

            } //container qos

          } //container ingress

        } //container video-sap

      } //list video-interface

      list vpls-group {
        key "vpls-group-id";
        description
            "Configure VPLS group";
        leaf vpls-group-id {
          type int32 {
            range "1..4094";
          }
        } //vpls-group-id

        leaf mvrp-control {
          type boolean;
          description
              "Enable/Disable MVRP";
        }

        container sap-template-binding {
          description
              "Bind to a SAP template";
          leaf name {
            type string {
              length "1..32";
            }
          } //name

        } //container sap-template-binding

        container service-range {
          description
              "Specify a service range for VLAN";
          leaf service-range {
            type string {
            }
            description
                "Attribute service-range for service-range";
          } //service-range

          leaf vlan-id {
            type uint32 {
              range "1..4094";
            }
            description
                "1..4094";
          } //vlan-id

        } //container service-range

        leaf shutdown {
          type boolean;
          description
              "Administratively enable/disable the vpls-group";
        }

        container vpls-template-binding {
          description
              "Bind to a VPLS template";
          leaf name {
            type string {
              length "1..32";
            }
          } //name

        } //container vpls-template-binding

      } //list vpls-group

      list vxlan {
        key "vni instance";
        description
            "Configure vxlan information";
        leaf vni {
          type uint32 {
            range "1..16777215";
          }
        } //vni

        leaf instance {
          type uint32 {
            range "1..2";
          }
        } //instance

        container assisted-replication {
          description
              "Configure AR in the VPLS service for vxlan tunnels";
          leaf replicator-leaf {
            type enumeration {
              enum replicator;
              enum leaf;
            }
          } //replicator-leaf

          leaf replicator-activation-time {
            type uint32 {
              range "1..255";
            }
          } //replicator-activation-time

        } //container assisted-replication

        leaf disable-aging {
          type boolean;
          description
              "Enable/disable aging of MAC addresses";
        }

        leaf disable-learning {
          type boolean;
          description
              "Enable/disable learning of new MAC addresses";
        }

        leaf discard-unknown-source {
          type boolean;
          description
              "Enable/disable discarding of frames with unknown source MAC address";
        }

        list egr-vtep {
          key "ip-address-ipv6-address";
          description
              "Configure vxlan egress vtep information";
          leaf ip-address-ipv6-address {
            type string;
            description
                "Attribute ip-address|ipv6-address for egr-vtep";
          } //ip-address-ipv6-address

        } //list egr-vtep

        container max-nbr-mac-addr {
          description
              "Configure the maximum number of MAC entries in the FDB from this VXLAN 
               instance";
          leaf table-size {
            type string;
            description
                "Attribute table-size for max-nbr-mac-addr";
          } //table-size

        } //container max-nbr-mac-addr

        container restrict-protected-src {
          description
              "Enable/disable protected src MAC restriction";
          leaf discard-frame {
            type boolean;
          } //discard-frame

        } //container restrict-protected-src

        container rx-discard-on-ndf {
          description
              "Configure type of receive traffic to discard on NDF";
          leaf bm-bum-none {
            type enumeration {
              enum bm;
              enum bum;
              enum none;
            }
          } //bm-bum-none

        } //container rx-discard-on-ndf

        leaf source-vtep-security {
          type boolean;
          description
              "Enable/disable source VTEP security on this VXLAN instance";
        }

        container igmp-snooping {
          description
              "Configure igmp-snooping";
          leaf mrouter-port {
            type boolean;
            description
                "Configure multicast router attachment behind VXLAN interfaces";
          }

        } //container igmp-snooping

        container mld-snooping {
          description
              "Configure mld-snooping";
          leaf mrouter-port {
            type boolean;
            description
                "Configure multicast router attachment behind VXLAN interfaces";
          }

        } //container mld-snooping

        container network {
          description
              "Configure network parameters";
          container ingress {
            description
                "Configure ingress policies";
            container qos {
              description
                  "Associate a network Quality of Service (QoS) policy";
              leaf network-policy-id {
                type uint32 {
                  range "1..65535";
                }
              } //network-policy-id

              leaf fp-redirect-group {
                type string {
                  length "1..32";
                }
              } //fp-redirect-group

              leaf instance {
                type uint16 {
                  range "1..65535";
                }
              } //instance

            } //container qos

          } //container ingress

        } //container network

      } //list vxlan

      container wlan-gw {
        description
            "Configure WLAN Gateway";
        container description {
          description
              "Description of the WLAN Gateway";
          leaf description-string {
            type string {
              length "1..80";
            }
          } //description-string

        } //container description

        container sap-template {
          description
              "SAP template of the WLAN Gateway";
          leaf sap-template {
            type string;
          } //sap-template

        } //container sap-template

        leaf shutdown {
          type boolean;
          description
              "Disable/enable WLAN Gateway";
        }

      } //container wlan-gw

    } //list vpls

  } //grouping alu-conf-svc-vpls-r13

} //module  alu-conf-svc-vpls-r13
