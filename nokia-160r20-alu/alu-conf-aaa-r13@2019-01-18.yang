module alu-conf-aaa-r13 {
  yang-version "1";

  namespace "urn:alcatel-lucent.com:sros:ns:yang:conf-aaa-r13";

  prefix "conf-aaa-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure Authentication, Authorization, and 
       Accounting on SR OS based routers. 
       
       Copyright 2014-2015 Alcatel-Lucent, 2016 Nokia. All rights reserved. 
       Reproduction of this document is authorized on the condition that the 
       foregoing copyright notice is included. 
       
       This alu-conf-aaa-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-01-18";

  grouping alu-conf-aaa-r13 {
    container aaa {
      description
          "Configure Authentication, Authorization, and Accounting";
      container radius-coa-port {
        description
            "Configure radius CoA port";
        leaf radius-coa-port-id {
          type enumeration {
            enum 1647;
            enum 1700;
            enum 1812;
            enum 3799;
          }
        } //radius-coa-port-id

      } //container radius-coa-port

      list acct-on-off-group {
        key "group-name";
        description
            "Configure a RADIUS accounting on off group";
        leaf group-name {
          type string {
            length "1..32";
          }
        } //group-name

        container description {
          description
              "Configure the description of this group";
          leaf description-string {
            type string {
              length "1..80";
            }
          } //description-string

        } //container description

      } //list acct-on-off-group

      container diameter {
        description
            "Configure Diameter";
        list node {
          key "origin-host-string";
          description
              "Configure a Diameter node";
          leaf origin-host-string {
            type string {
              length "1..80";
            }
          } //origin-host-string

          leaf origin-realm {
            type string {
              length "1..80";
            }
          } //origin-realm

          container connection-timer {
            description
                "Configure the Diameter node connection timer";
            leaf seconds {
              type uint32 {
                range "1..1000";
              }
            } //seconds

          } //container connection-timer

          container description {
            description
                "Configure the description";
            leaf description-string {
              type string {
                length "1..80";
              }
            } //description-string

          } //container description

          container ipv6-source-address {
            description
                "Configure the Diameter node IPv6 source address";
            leaf ipv6-address {
              type inet:ipv6-address;
              description
                  "Attribute ipv6-address for ipv6-source-address";
            } //ipv6-address

          } //container ipv6-source-address

          container python-policy {
            description
                "Configure the Python policy used to modify Diameter messages";
            leaf python-policy-name {
              type string {
                length "1..32";
              }
            } //python-policy-name

          } //container python-policy

          container router {
            description
                "Configure the Diameter node router";
            leaf router-name {
              type string {
                length "1..32";
              }
              default "Base";
              description
                  "Attribute router-name for router";
            } //router-name

            leaf service {
              type string;
            } //service

          } //container router

          container source-address {
            description
                "Configure the Diameter node IPv4 source address";
            leaf ip-address {
              type inet:ip-address;
            } //ip-address

          } //container source-address

          list peer {
            key "index";
            description
                "Configure a Diameter peer in this node";
            leaf index {
              type uint32 {
                range "1..5";
              }
            } //index

            leaf destination-host-string {
              type string {
                length "1..80";
              }
            } //destination-host-string

            container address {
              description
                  "Configure the peer address";
              leaf ip-address-ipv6-address {
                type string;
                description
                    "Attribute ip-address|ipv6-address for address";
              } //ip-address-ipv6-address

            } //container address

            container connection-timer {
              description
                  "Configure the peer connection timer";
              leaf seconds {
                type uint32 {
                  range "1..1000";
                }
              } //seconds

            } //container connection-timer

            container preference {
              description
                  "Configure the preference of this peer";
              leaf preference {
                type uint32 {
                  range "1..100";
                }
              } //preference

            } //container preference

            leaf shutdown {
              type boolean;
              description
                  "Administratively enable/disable the peer";
            }

            container watchdog-timer {
              description
                  "Configure the peer watchdog timer";
              leaf seconds {
                type uint32 {
                  range "1..1000";
                }
              } //seconds

            } //container watchdog-timer

          } //list peer

        } //list node

      } //container diameter

      list diameter-peer-policy {
        key "peer-policy-name";
        description
            "Configure a Diameter peer policy";
        leaf peer-policy-name {
          type string;
        } //peer-policy-name

        leaf role {
          type enumeration {
            enum client;
            enum proxy;
          }
        } //role

        container applications {
          description
              "Configure the supported applications";
          leaf-list applications-id {
            type enumeration {
              enum gx;
              enum gy;
              enum nasreq;
            }
            max-elements 3;
          } //applications-id

        } //container applications

        container connection-timer {
          description
              "Configure the Diameter peer policy connection timer (seconds)";
          leaf connection-time {
            type uint32 {
              range "1..1000";
            }
          } //connection-time

        } //container connection-timer

        container description {
          description
              "Configure the description";
          leaf description-string {
            type string {
              length "1..80";
            }
          } //description-string

        } //container description

        container ipv6-source-address {
          description
              "Configure the Diameter peer policy IPv6 source address";
          leaf ipv6-address {
            type inet:ipv6-address;
            description
                "Attribute ipv6-address for ipv6-source-address";
          } //ipv6-address

        } //container ipv6-source-address

        container origin-host {
          description
              "Configure the Diameter peer policy origin host string";
          leaf origin-host-string {
            type string {
              length "1..80";
            }
          } //origin-host-string

        } //container origin-host

        container origin-realm {
          description
              "Configure the Diameter peer policy origin realm string";
          leaf origin-realm-string {
            type string {
              length "1..80";
            }
          } //origin-realm-string

        } //container origin-realm

        container python-policy {
          description
              "Configure the Python policy used to modify Diameter messages";
          leaf python-policy-string {
            type string {
              length "1..32";
            }
          } //python-policy-string

        } //container python-policy

        container router {
          description
              "Configure the Diameter peer policy router";
          leaf router-instance {
            type string {
              length "1..32";
            }
            description
                "Attribute router-instance for router";
          } //router-instance

          leaf service {
            type string;
          } //service

        } //container router

        container source-address {
          description
              "Configure the Diameter peer policy source address";
          leaf ip-address {
            type inet:ip-address;
          } //ip-address

        } //container source-address

        container transaction-timer {
          description
              "Configure the Diameter peer policy transaction timer (seconds)";
          leaf transaction-time {
            type uint32 {
              range "1..1000";
            }
          } //transaction-time

        } //container transaction-timer

        container vendor-support {
          description
              "Configure the Diameter peer policy vendor type";
          leaf vendor-support-id {
            type enumeration {
              enum three-gpp;
              enum vodafone;
            }
          } //vendor-support-id

        } //container vendor-support

        container watchdog-timer {
          description
              "Configure the Diameter peer policy watchdog timer (seconds)";
          leaf wd-time {
            type uint32 {
              range "1..1000";
            }
          } //wd-time

        } //container watchdog-timer

        list peer {
          key "name";
          description
              "Configure a peer in this Diameter peer policy";
          leaf name {
            type string {
              length "1..32";
            }
          } //name

          container address {
            description
                "Configure the Diameter peer policy peer address";
            leaf ip-address {
              type string;
              description
                  "Attribute ip-address for address";
            } //ip-address

          } //container address

          container connection-timer {
            description
                "Configure the peer connection timer (seconds)";
            leaf connection-time {
              type uint16 {
                range "1..1000";
              }
            } //connection-time

          } //container connection-timer

          container destination-host {
            description
                "Configure the peer destination host string";
            leaf destination-host-string {
              type string {
                length "1..80";
              }
            } //destination-host-string

          } //container destination-host

          container destination-realm {
            description
                "Configure the Diameter peer policy peer destination realm string";
            leaf destination-realm-string {
              type string {
                length "1..80";
              }
            } //destination-realm-string

          } //container destination-realm

          container preference {
            description
                "Configure the preference of this Diameter peer policy peer";
            leaf preference {
              type uint32 {
                range "1..100";
              }
            } //preference

          } //container preference

          leaf shutdown {
            type boolean;
            description
                "Administratively enable/disable the peer";
          }

          container transaction-timer {
            description
                "Configure the peer transaction timer (seconds)";
            leaf seconds {
              type uint32 {
                range "1..1000";
              }
            } //seconds

          } //container transaction-timer

          container transport {
            description
                "Configure the Diameter peer policy peer transport protocol";
            leaf tcp {
              type boolean;
            } //tcp

            leaf port {
              type int32 {
                range "1..65535";
              }
            } //port

          } //container transport

          container watchdog-timer {
            description
                "Configure the peer watchdog timer (seconds)";
            leaf wd-time {
              type uint32 {
                range "1..1000";
              }
            } //wd-time

          } //container watchdog-timer

        } //list peer

        container proxy {
          description
              "Configure for the proxy role";
          container mcs-peer {
            description
                "Configure the Multi-chassis redundancy synchronization peer and tag";
            leaf ip-address {
              type string;
              description
                  "Attribute ip-address for mcs-peer";
            } //ip-address

            leaf sync-tag {
              type string;
            } //sync-tag

          } //container mcs-peer

          container router {
            description
                "Configure the IP address and router instance";
            leaf router-instance {
              type string {
                length "1..32";
              }
              description
                  "Attribute router-instance for router";
            } //router-instance

            leaf address {
              type string;
              description
                  "Attribute ip-address for router";
            } //address

          } //container router

          leaf shutdown {
            type boolean;
            description
                "Disable/enable the proxy function";
          }

        } //container proxy

      } //list diameter-peer-policy

      list isa-radius-policy {
        key "name";
        description
            "Configure an ISA RADIUS policy";
        leaf name {
          type string;
        } //name

        container description {
          description
              "Configure the description of this policy";
          leaf description-string {
            type string {
              length "1..80";
            }
          } //description-string

        } //container description

        container nas-ip-address-origin {
          description
              "Configure what to put in the RADIUS NAS-IP-Address attribute";
          leaf nas-ip-address-origin-id {
            type enumeration {
              enum isa-ip;
              enum system-ip;
            }
          } //nas-ip-address-origin-id

        } //container nas-ip-address-origin

        container password {
          description
              "Configure the password used in the RADIUS request";
          leaf password {
            type string {
              length "1..500";
            }
            description
                "secret-key - [10 chars max] 
                 hash-key 
                 hash2-key 
                 custom-key";
          } //password

          leaf hash-hash2-custom {
            type enumeration {
              enum hash;
              enum hash2;
              enum custom;
            }
            description
                "keywords - specify hashing scheme";
          } //hash-hash2-custom

        } //container password

        container periodic-update {
          description
              "Configure the interval and rate limit for periodic RADIUS Interim-Update 
               messages";
          leaf interval {
            type uint32 {
              range "1..72";
            }
          } //interval

          leaf rate-limit {
            type uint32 {
              range "1..100000";
            }
          } //rate-limit

        } //container periodic-update

        container python-policy {
          description
              "Configure the Python policy used for modifying RADIUS messages";
          leaf policy-name {
            type string;
          } //policy-name

        } //container python-policy

        container user-name-format {
          description
              "Configure what to put in the RADIUS User-Name attribute";
          leaf user-name-format {
            type enumeration {
              enum circuit-id;
              enum dhcp-vendor;
              enum mac;
              enum mac-ip;
            }
          } //user-name-format

          leaf mac-format {
            type enumeration {
              enum alu;
              enum ieee;
            }
          } //mac-format

        } //container user-name-format

        container acct-include-attributes {
          presence
              "Configure attributes to be included in RADIUS accounting messages";
          leaf acct-delay-time {
            type boolean;
            description
                "Enable/disable including the Acct-Delay-Time";
          }

          leaf acct-trigger-reason {
            type boolean;
            description
                "Enable/disable including Alc-Acct-Triggered-Reason";
          }

          leaf called-station-id {
            type boolean;
            description
                "Enable/disable including the Called-Station-Id";
          }

          leaf calling-station-id {
            type boolean;
            description
                "Enable/disable generation of the Calling-Station-Id RADIUS attribute";
          }

          leaf circuit-id {
            type boolean;
            description
                "Enable/disable including the Circuit-Id";
          }

          leaf class {
            type boolean;
            description
                "Enable/disable including the Class attribute";
          }

          leaf dhcp-options {
            type boolean;
            description
                "Enable/disable including the DHCP options";
          }

          leaf dhcp-vendor-class-id {
            type boolean;
            description
                "Enable/disable generation of the Alc-DHCP-Vendor-Class-Id RADIUS attribute";
          }

          leaf dhcp6-options {
            type boolean;
            description
                "Enable/disable including the Alc-ToServer-Dhcp6-Options RADIUS attribute";
          }

          leaf frame-counters {
            type boolean;
            description
                "Enable/disable including the frame-counters attribute";
          }

          leaf framed-ip-addr {
            type boolean;
            description
                "Enable/disable including the Framed-IP-Address attribute";
          }

          leaf framed-ip-netmask {
            type boolean;
            description
                "Enable/disable including the Framed-IP-Netmask";
          }

          leaf framed-ipv6-prefix {
            type boolean;
            description
                "Enable/disable generation of the Framed-IPv6-Prefix RADIUS attribute";
          }

          leaf hardware-timestamp {
            type boolean;
            description
                "Enable/disable including the hardware timestamp attribute";
          }

          leaf inside-service-id {
            type boolean;
            description
                "Enable/disable including the NAT inside service ID";
          }

          leaf ipv6-address {
            type boolean;
            description
                "Enable/disable generation of the IPv6-Address RADIUS attribute";
          }

          leaf mac-address {
            type boolean;
            description
                "Enable/disable generation of the client MAC address RADIUS attribute";
          }

          leaf multi-session-id {
            type boolean;
            description
                "Enable/disable including the multi-session-id attribute";
          }

          leaf nas-identifier {
            type boolean;
            description
                "Enable/disable including the NAS-Identifier attribute";
          }

          leaf nas-ip-address {
            type boolean;
            description
                "Enable/disable including the NAS-IP-Address attribute";
          }

          leaf nas-port {
            type boolean;
            description
                "Enable/disable including the NAS-Port attribute";
          }

          leaf nas-port-id {
            type boolean;
            description
                "Enable/disable generation of the NAS-Port-Id RADIUS attribute";
          }

          leaf nas-port-type {
            type boolean;
            description
                "Enable/disable generation of the NAS-Port-Type RADIUS attribute";
          }

          leaf nat-subscriber-string {
            type boolean;
            description
                "Enable/disable including the NAT subscriber string attribute";
          }

          leaf octet-counters {
            type boolean;
            description
                "Enable/disable including the octet-counters attribute";
          }

          leaf outside-ip {
            type boolean;
            description
                "Enable/disable including the NAT outside IP attribute";
          }

          leaf outside-service-id {
            type boolean;
            description
                "Enable/disable including the NAT outside service ID";
          }

          leaf port-range-block {
            type boolean;
            description
                "Enable/disable including the NAT port range block attribute";
          }

          leaf release-reason {
            type boolean;
            description
                "Enable/disable including the release reason attribute";
          }

          leaf remote-id {
            type boolean;
            description
                "Enable/disable including the Remote-Id";
          }

          leaf session-time {
            type boolean;
            description
                "Enable/disable including the session-time attribute";
          }

          leaf subscriber-data {
            type boolean;
            description
                "Enable/disable including the subscriber data";
          }

          leaf subscriber-id {
            type boolean;
            description
                "Enable/disable including the subscriber ID";
          }

          leaf ue-creation-type {
            type boolean;
            description
                "Enable/disable including the Alc-Wlan-Ue-Creation-Type";
          }

          leaf user-name {
            type boolean;
            description
                "Enable/disable including the user-name attribute";
          }

          leaf wifi-rssi {
            type boolean;
            description
                "Enable/disable including the Alc-RSSI";
          }

          leaf wifi-ssid-vlan {
            type boolean;
            description
                "Enable/disable including the per-SSID VLAN ID in Alc-Wlan-SSID-VLAN";
          }

          leaf xconnect-tunnel-home-address {
            type boolean;
            description
                "Enable/disable generation of the Cross Connect Tunnel Home Address RADIUS 
                 attribute";
          }

          leaf xconnect-tunnel-local-ipv6-address {
            type boolean;
            description
                "Enable/disable including the cross-connect tunnel local IPv6 address";
          }

          leaf xconnect-tunnel-remote-ipv6-address {
            type boolean;
            description
                "Enable/disable including the cross-connect tunnel remote IPv6 address";
          }

          leaf xconnect-tunnel-service {
            type boolean;
            description
                "Enable/disable including the cross-connect tunnel service";
          }

          leaf xconnect-tunnel-type {
            type boolean;
            description
                "Enable/disable including the cross-connect tunnel type";
          }

        } //container acct-include-attributes

        container acct-update-triggers {
          description
              "Configure triggers for RADIUS Interim-Update messages";
          leaf address-state {
            type boolean;
            description
                "Configure update triggers for dhcp/dhcp6/slaac";
          }

        } //container acct-update-triggers

        container auth-include-attributes {
          presence
              "Configure attributes to be included in RADIUS authentication messages";
          leaf called-station-id {
            type boolean;
            description
                "Enable/disable generation of the called-station-id RADIUS attribute";
          }

          leaf calling-station-id {
            type boolean;
            description
                "Enable/disable generation of the calling-station-id RADIUS attribute";
          }

          leaf circuit-id {
            type boolean;
            description
                "Enable/disable generation of the agent-circuit-id RADIUS attribute";
          }

          leaf dhcp-options {
            type boolean;
            description
                "Enable/disable generation of the dhcp-options RADIUS attribute";
          }

          leaf dhcp-vendor-class-id {
            type boolean;
            description
                "Enable/disable generation of the dhcp-vendor-class-id RADIUS attribute";
          }

          leaf dhcp6-options {
            type boolean;
            description
                "Enable/disable including the Alc-ToServer-Dhcp6-Options RADIUS attribute";
          }

          leaf framed-ip-addr {
            type boolean;
            description
                "Enable/disable including the Framed-IP-Address attribute";
          }

          leaf ipv6-address {
            type boolean;
            description
                "Enable/disable generation of the IPv6-Address RADIUS attribute";
          }

          leaf mac-address {
            type boolean;
            description
                "Enable/disable generation of the client MAC address RADIUS attribute";
          }

          leaf nas-identifier {
            type boolean;
            description
                "Enable/disable generation of the NAS-Identifier RADIUS attribute";
          }

          leaf nas-ip-address {
            type boolean;
            description
                "Enable/disable including the NAS-IP-Address attribute";
          }

          leaf nas-port {
            type boolean;
            description
                "Enable/disable including the NAS-Port attribute";
          }

          leaf nas-port-id {
            type boolean;
            description
                "Enable/disable generation of the NAS-Port-Id RADIUS attribute";
          }

          leaf nas-port-type {
            type boolean;
            description
                "Enable/disable generation of the NAS-Port-Type RADIUS attribute";
          }

          leaf remote-id {
            type boolean;
            description
                "Enable/disable generation of the agent-remote-id RADIUS attribute";
          }

          leaf wifi-ssid-vlan {
            type boolean;
            description
                "Enable/disable including the per-SSID VLAN ID in Alc-Wlan-SSID-VLAN";
          }

          leaf xconnect-tunnel-home-address {
            type boolean;
            description
                "Enable/disable generation of the Cross Connect Tunnel Home Address RADIUS 
                 attribute";
          }

        } //container auth-include-attributes

        container servers {
          description
              "Configure the RADIUS servers";
          container access-algorithm {
            description
                "Configure the algorithm used to access the set of RADIUS servers";
            leaf access-algorithm-id {
              type enumeration {
                enum direct;
                enum round-robin;
                enum hash-based;
              }
            } //access-algorithm-id

          } //container access-algorithm

          container retry {
            description
                "Number of retries for contacting the RADIUS server";
            leaf count {
              type uint32 {
                range "1..10";
              }
            } //count

          } //container retry

          container router {
            description
                "Configure the routing instance";
            leaf router-instance {
              type string {
                length "1..32";
              }
              description
                  "Attribute router-instance for router";
            } //router-instance

            leaf service-name {
              type string;
            } //service-name

          } //container router

          container source-address-range {
            description
                "Start of the source address range of the RADIUS messages";
            leaf start-ip-address {
              type inet:ip-address;
            } //start-ip-address

          } //container source-address-range

          container timeout {
            description
                "Timeout for a response from the RADIUS server";
            leaf sec {
              type uint8 {
                range "1..59";
              }
            } //sec

            leaf min {
              type uint8 {
              }
            } //min

          } //container timeout

          list server {
            key "server-index";
            description
                "Configure RADIUS server communication";
            leaf server-index {
              type uint32 {
                range "1..10";
              }
            } //server-index

            container accounting {
              description
                  "Configure accounting";
              leaf port {
                type uint16 {
                  range "1..65535";
                }
              } //port

            } //container accounting

            container authentication {
              description
                  "Configure authentication";
              leaf port {
                type uint16 {
                  range "1..65535";
                }
              } //port

            } //container authentication

            container coa {
              description
                  "Configure Change of Authorization";
              leaf port {
                type uint16 {
                  range "1..65535";
                }
              } //port

            } //container coa

            container ip-address {
              description
                  "Configure the destination IP address to reach the RADIUS server";
              leaf ip-address {
                type inet:ip-address;
              } //ip-address

            } //container ip-address

            container secret {
              description
                  "Configure the secret to authenticate messages from the RADIUS server";
              leaf secret-key---hash-key {
                type string {
                  length "1..500";
                }
                description
                    "secret-key - [64 chars max] 
                     hash-key 
                     hash2-key 
                     custom-key";
              } //secret-key---hash-key

              leaf hash-hash2-custom {
                type enumeration {
                  enum hash;
                  enum hash2;
                  enum custom;
                }
                description
                    "keywords - specify hashing scheme";
              } //hash-hash2-custom

            } //container secret

            leaf shutdown {
              type boolean;
              description
                  "Disable/enable the communication with the RADIUS server";
            }

          } //list server

        } //container servers

      } //list isa-radius-policy

      list l2tp-accounting-policy {
        key "policy-name";
        description
            "Configure an L2TP accounting policy";
        leaf policy-name {
          type string {
            length "1..32";
          }
          description
              "[32 chars max]";
        } //policy-name

        container accounting-type {
          description
              "Configure the type of accounting";
          leaf session {
            type boolean;
          } //session

          leaf tunnel {
            type boolean;
          } //tunnel

        } //container accounting-type

        container acct-tunnel-connection-fmt {
          description
              "Configure the accounting tunnel connection ascii-specification";
          leaf ascii-spec {
            type string {
              length "1..253";
            }
            description
                "Attribute ascii-spec for acct-tunnel-connection-fmt";
          } //ascii-spec

        } //container acct-tunnel-connection-fmt

        container description {
          description
              "Configure the description of this policy";
          leaf description-string {
            type string {
              length "1..80";
            }
          } //description-string

        } //container description

        container radius-server-policy {
          description
              "Configure the radius-server-policy";
          leaf policy-name {
            type string {
              length "1..32";
            }
            description
                "[32 chars max]";
          } //policy-name

        } //container radius-server-policy

        container request-script-policy {
          description
              "Configure a RADIUS script policy to modify Access-Request messages";
          leaf script-policy {
            type string {
              length "1..32";
            }
          } //script-policy

        } //container request-script-policy

        container include-radius-attribute {
          description
              "Configure RADIUS attributes to be included";
          leaf calling-station-id {
            type boolean;
            description
                "Enable/disable the Calling Station ID";
          }

          leaf nas-identifier {
            type boolean;
            description
                "Include the NAS-Identifier attribute";
          }

          container nas-port {
            description
                "Include the NAS-Port attribute";
            leaf binary-spec {
              type string {
                length "1..255";
              }
              description
                  "Attribute binary-spec for nas-port";
            } //binary-spec

          } //container nas-port

          container nas-port-id {
            description
                "Include the NAS-Port-Id attribute";
            leaf prefix-string {
              type string {
                length "1..8";
              }
            } //prefix-string

            leaf suffix {
              type enumeration {
                enum circuit-id;
                enum remote-id;
              }
            } //suffix

          } //container nas-port-id

          container nas-port-type {
            description
                "Include the NAS-Port-Type attribute";
            leaf nas-port-type-id {
              type uint8;
            } //nas-port-type-id

          } //container nas-port-type

        } //container include-radius-attribute

        container radius-accounting-server {
          description
              "Configure RADIUS server for this policy";
          container access-algorithm {
            description
                "Configure the algorithm used to access the set of RADIUS servers";
            leaf direct-round-robin {
              type enumeration {
                enum direct;
                enum round-robin;
              }
              description
                  "keywords";
            } //direct-round-robin

          } //container access-algorithm

          container retry {
            description
                "Number of retries for contacting the RADIUS server";
            leaf count {
              type uint32 {
                range "1..10";
              }
            } //count

          } //container retry

          container router {
            description
                "Configure the routing instance";
            leaf router-instance {
              type string {
                length "1..32";
              }
              default "Base";
              description
                  "Attribute router-instance for router";
            } //router-instance

            leaf service-name {
              type string;
            } //service-name

          } //container router

          list server {
            key "server-index";
            description
                "Add/remove a RADIUS server";
            leaf server-index {
              type uint32 {
                range "1..5";
              }
            } //server-index

            leaf address {
              type inet:ip-address;
            } //address

            leaf secret {
              type string {
                length "1..500";
              }
              description
                  "secret-key - [20 chars max] 
                   hash-key 
                   hash2-key 
                   custom-key";
            } //secret

            leaf hash-hash2-custom {
              type enumeration {
                enum hash;
                enum hash2;
                enum custom;
              }
              description
                  "keywords - specify hashing scheme";
            } //hash-hash2-custom

            leaf port {
              type uint16 {
                range "1..65535";
              }
            } //port

          } //list server

          container source-address {
            description
                "Source address of the RADIUS messages";
            leaf ip-address {
              type inet:ip-address;
            } //ip-address

          } //container source-address

          container timeout {
            description
                "Timeout for a response from the RADIUS server";
            leaf sec {
              type uint8 {
                range "1..59";
              }
            } //sec

            leaf min {
              type uint8 {
              }
            } //min

          } //container timeout

        } //container radius-accounting-server

      } //list l2tp-accounting-policy

      list radius-script-policy {
        key "policy-name";
        description
            "Configure Python scripts to modify RADIUS messages";
        leaf policy-name {
          type string {
            length "1..32";
          }
        } //policy-name

        container action-on-fail {
          description
              "Action taken on script failure";
          leaf action-on-fail-id {
            type enumeration {
              enum drop;
              enum passthrough;
            }
          } //action-on-fail-id

        } //container action-on-fail

        container description {
          description
              "Configure the description of this policy";
          leaf description {
            type string {
              length "1..80";
            }
          } //description

        } //container description

        container primary {
          description
              "Configure primary script";
          container script-url {
            description
                "URL of the primary script";
            leaf primary-script-url {
              type string {
                length "1..180";
              }
            } //primary-script-url

          } //container script-url

          leaf shutdown {
            type boolean;
            description
                "Enable/disable script execution";
          }

        } //container primary

        container secondary {
          description
              "Configure secondary script";
          container script-url {
            description
                "URL of the secondary script";
            leaf secondary-script-url {
              type string {
                length "1..180";
              }
            } //secondary-script-url

          } //container script-url

          leaf shutdown {
            type boolean;
            description
                "Enable/disable script execution";
          }

        } //container secondary

      } //list radius-script-policy

      list radius-server-policy {
        key "policy-name";
        description
            "Configure a RADIUS server policy";
        leaf policy-name {
          type string {
            length "1..32";
          }
          description
              "[32 chars max]";
        } //policy-name

        container accept-script-policy {
          description
              "Configure RADIUS script policy to modify Access-Accept";
          leaf policy-name {
            type string {
              length "1..32";
            }
          } //policy-name

        } //container accept-script-policy

        container acct-on-off {
          description
              "Enable/disable sending of Acct-On/Acct-Off messages upon 
               activation/deactivation";
          leaf oper-state-change {
            type boolean;
          } //oper-state-change

          leaf group {
            type string {
              length "1..32";
            }
          } //group

          leaf monitor-group {
            type string {
              length "1..32";
            }
            description
                "group-name";
          } //monitor-group

        } //container acct-on-off

        container acct-request-script-policy {
          description
              "Configure a RADIUS script policy to modify Accounting-Request messages";
          leaf policy-name {
            type string {
              length "1..32";
            }
          } //policy-name

        } //container acct-request-script-policy

        container auth-request-script-policy {
          description
              "Configure a RADIUS script policy to modify Access-Request messages";
          leaf policy-name {
            type string {
              length "1..32";
            }
          } //policy-name

        } //container auth-request-script-policy

        container description {
          description
              "Configure the description of this policy";
          leaf description-string {
            type string {
              length "1..80";
            }
          } //description-string

        } //container description

        container python-policy {
          description
              "Configure the Python policy to modify the RADIUS messages";
          leaf name {
            type string {
              length "1..32";
            }
          } //name

        } //container python-policy

        container request-script-policy {
          description
              "Configure a RADIUS script policy to modify Access-Request or 
               Accounting-Request messages";
          leaf policy-name {
            type string {
              length "1..32";
            }
          } //policy-name

        } //container request-script-policy

        container servers {
          description
              "Configure RADIUS server for this policy";
          container access-algorithm {
            description
                "Configure the algorithm used to access the set of RADIUS servers";
            leaf access-algorithm-id {
              type enumeration {
                enum direct;
                enum round-robin;
                enum hash-based;
              }
            } //access-algorithm-id

          } //container access-algorithm

          leaf disable-stickiness {
            type boolean;
            description
                "Configure the stickiness to a host in a multi-server application";
          }

          container hold-down-time {
            description
                "Hold time before re-using a RADIUS server that was down";
            leaf sec {
              type uint8 {
                range "1..59";
              }
            } //sec

            leaf min {
              type uint8 {
                range "1..59";
              }
            } //min

            leaf hrs {
              type uint8 {
                range "1..23";
              }
            } //hrs

            leaf days {
              type uint8 {
              }
            } //days

          } //container hold-down-time

          container ipv6-source-address {
            description
                "Configure the source address for IPv6 RADIUS datagrams";
            leaf ipv6-address {
              type inet:ipv6-address;
              description
                  "Attribute ipv6-address for ipv6-source-address";
            } //ipv6-address

          } //container ipv6-source-address

          container retry {
            description
                "Number of retries for contacting the RADIUS server";
            leaf count {
              type uint32 {
                range "1..256";
              }
            } //count

          } //container retry

          container router {
            description
                "Configure the routing instance";
            leaf router-instance {
              type string {
                length "1..32";
              }
              description
                  "Attribute router-instance for router";
            } //router-instance

            leaf service-name {
              type string;
            } //service-name

          } //container router

          list server {
            key "server-index";
            description
                "Add/remove a RADIUS server";
            leaf server-index {
              type uint32 {
                range "1..16";
              }
            } //server-index

            leaf name {
              type string {
                length "1..32";
              }
            } //name

          } //list server

          container source-address {
            description
                "Source address of the RADIUS messages";
            leaf ip-address {
              type inet:ip-address;
            } //ip-address

          } //container source-address

          container timeout {
            description
                "Time until the next retry to the RADIUS server";
            leaf sec {
              type uint8 {
                range "1..59";
              }
            } //sec

            leaf min {
              type uint8 {
                range "1..5";
              }
            } //min

          } //container timeout

          container buffering {
            presence
                "Configure message buffering parameters";
            container acct-interim {
              description
                  "Configure interim update message parameters";
              leaf min {
                type uint32 {
                  range "1..3600";
                }
                description
                    "[1..3600] seconds";
              } //min

              leaf max {
                type uint32 {
                  range "1..3600";
                }
                description
                    "[1..3600] seconds";
              } //max

              leaf lifetime {
                type uint32 {
                  range "1..25";
                }
                description
                    "[1..25] hours";
              } //lifetime

            } //container acct-interim

            container acct-stop {
              description
                  "Configure stop message parameters";
              leaf min {
                type uint32 {
                  range "1..3600";
                }
                description
                    "[1..3600] seconds";
              } //min

              leaf max {
                type uint32 {
                  range "1..3600";
                }
                description
                    "[1..3600] seconds";
              } //max

              leaf lifetime {
                type uint32 {
                  range "1..25";
                }
                description
                    "[1..25] hours";
              } //lifetime

            } //container acct-stop

          } //container buffering

          container health-check {
            description
                "Configure how to test the health of a server";
            container down-timeout {
              description
                  "A server that is unresponsive during this time is declared down";
              leaf sec {
                type uint8 {
                  range "1..59";
                }
              } //sec

              leaf min {
                type uint8 {
                  range "1..5";
                }
              } //min

            } //container down-timeout

            container test-account {
              description
                  "Configure the test-account used for the keep-alive mechanism of a server";
              container interval {
                description
                    "Configure the interval (in seconds) used for health check";
                leaf seconds {
                  type uint32 {
                    range "1..60";
                  }
                } //seconds

              } //container interval

              container password {
                description
                    "Configure the password used for health check";
                leaf password {
                  type string {
                    length "1..500";
                  }
                  description
                      "secret-key - [64 chars max] 
                       hash-key 
                       hash2-key 
                       custom-key";
                } //password

                leaf hash-hash2-custom {
                  type enumeration {
                    enum hash;
                    enum hash2;
                    enum custom;
                  }
                  description
                      "keywords - specify hashing scheme";
                } //hash-hash2-custom

              } //container password

              leaf shutdown {
                type boolean;
                description
                    "Configure the health check state (enabled/disabled)";
              }

              container user-name {
                description
                    "Configure the user-name used for health check";
                leaf user-name-string {
                  type string {
                    length "1..64";
                  }
                } //user-name-string

              } //container user-name

            } //container test-account

          } //container health-check

        } //container servers

      } //list radius-server-policy

      list route-downloader {
        key "name";
        description
            "Configure a route-downloader";
        leaf name {
          type string {
            length "1..32";
          }
        } //name

        container base-user-name {
          description
              "Configure the prefix of the username used by this route-downloader";
          leaf user-name {
            type string {
              length "1..32";
            }
          } //user-name

        } //container base-user-name

        container default-metric {
          description
              "Configure the default metric of this route-downloader";
          leaf metric {
            type uint32 {
              range "0..254";
            }
          } //metric

        } //container default-metric

        container default-tag {
          description
              "Configure the default tag of this route-downloader";
          leaf tag {
            type uint32;
          } //tag

        } //container default-tag

        container description {
          description
              "Configure the description of this route-downloader";
          leaf description-string {
            type string {
              length "1..80";
            }
          } //description-string

        } //container description

        container download-interval {
          description
              "Configure the download interval of this route-downloader";
          leaf minutes {
            type uint32 {
              range "1..1440";
            }
          } //minutes

        } //container download-interval

        container max-routes {
          description
              "Configure the maximum number of routes imported by this route-downloader";
          leaf routes {
            type uint32 {
              range "1..200000";
            }
          } //routes

        } //container max-routes

        container password {
          description
              "Configure the password used this route-downloader";
          leaf password {
            type string {
              length "1..500";
            }
            description
                "secret-key - [32 chars max] 
                 hash-key 
                 hash2-key 
                 custom-key";
          } //password

          leaf hash-hash2-custom {
            type enumeration {
              enum hash;
              enum hash2;
              enum custom;
            }
            description
                "keywords - specify hashing scheme";
          } //hash-hash2-custom

        } //container password

        container radius-server-policy {
          description
              "Configure the radius-server-policy used by this route-downloader";
          leaf policy-name {
            type string {
              length "1..32";
            }
          } //policy-name

        } //container radius-server-policy

        container retry-interval {
          description
              "Configure the retry interval of this route-downloader";
          leaf min {
            type uint32 {
              range "1..1440";
            }
          } //min

          leaf max {
            type uint32 {
              range "1..1440";
            }
          } //max

        } //container retry-interval

        leaf shutdown {
          type boolean;
          description
              "Administratively enable/disable this route-downloader";
        }

      } //list route-downloader

      container wpp {
        description
            "Configure attributes for Web Portal Protocol (WPP)";
        container system-name {
          description
              "Configure the WPP system name";
          leaf name {
            type string {
              length "1..16";
            }
          } //name

        } //container system-name

        container portal-groups {
          description
              "Configure the portal groups for WPP";
          list portal-group {
            key "portal-group-name";
            description
                "Configure a portal group for WPP";
            leaf portal-group-name {
              type string;
            } //portal-group-name

            container description {
              description
                  "Configure the description of this portal group";
              leaf description-string {
                type string {
                  length "1..80";
                }
              } //description-string

            } //container description

            list portal {
              key "router name";
              description
                  "Configure a portal for this portal group";
              leaf router {
                type string {
                  length "1..32";
                }
                description
                    "Attribute router-instance for portal";
              } //router

              leaf name {
                type string {
                  length "1..32";
                }
              } //name

            } //list portal

            leaf shutdown {
              type boolean;
              description
                  "Administratively enable/disable this portal-group";
            }

          } //list portal-group

        } //container portal-groups

      } //container wpp

    } //container aaa

  } //grouping alu-conf-aaa-r13

} //module  alu-conf-aaa-r13
