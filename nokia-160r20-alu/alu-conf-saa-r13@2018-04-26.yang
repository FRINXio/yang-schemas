module alu-conf-saa-r13 {
  yang-version "1";

  namespace "urn:alcatel-lucent.com:sros:ns:yang:conf-saa-r13";

  prefix "conf-saa-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure Service Assurance Agent Tests on 
       SR OS based routers. 
       
       Copyright 2014-2015 Alcatel-Lucent, 2016 Nokia. All rights reserved. 
       Reproduction of this document is authorized on the condition that the 
       foregoing copyright notice is included. 
       
       This alu-conf-saa-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-04-26";

  grouping alu-conf-saa-r13 {
    container saa {
      description
          "Configure Service Assurance Agent Tests";
      list test {
        key "test-name owner";
        description
            "Configure SAA test";
        leaf test-name {
          type string {
            length "1..32";
          }
        } //test-name

        leaf owner {
          type string {
            length "1..32";
          }
          description
              "[32 chars max] Default - \"TiMOS CLI\"";
        } //owner

        container accounting-policy {
          description
              "Configure an accounting-policy";
          leaf acct-policy-id {
            type uint64 {
              range "1..99";
            }
          } //acct-policy-id

        } //container accounting-policy

        leaf continuous {
          type boolean;
          description
              "repeat test indefinitely";
        }

        container description {
          description
              "Description for this SAA test";
          leaf description-string {
            type string {
              length "1..80";
            }
            description
                "[80 chars max]";
          } //description-string

        } //container description

        container jitter-event {
          description
              "Configure jitter event threshold";
          leaf rising-threshold {
            type uint32 {
              range "0..2147483647";
            }
            description
                "[0..2147483] milliseconds";
          } //rising-threshold

          leaf falling-threshold {
            type uint32;
          } //falling-threshold

          leaf direction {
            type enumeration {
              enum inbound;
              enum outbound;
              enum roundtrip;
            }
            description
                "inbound|outbound|roundtrip 
                 keywords - Def: roundtrip";
          } //direction

        } //container jitter-event

        container latency-event {
          description
              "Configure latency event threshold";
          leaf rising-threshold {
            type uint32 {
              range "0..2147483647";
            }
            description
                "[0..2147483] milliseconds";
          } //rising-threshold

          leaf falling-threshold {
            type uint32;
          } //falling-threshold

          leaf direction {
            type enumeration {
              enum inbound;
              enum outbound;
              enum roundtrip;
            }
            description
                "inbound|outbound|roundtrip 
                 keywords - Def: roundtrip 
                 ";
          } //direction

        } //container latency-event

        container loss-event {
          description
              "Configure loss event threshold";
          leaf rising-threshold {
            type uint32 {
              range "0..2147483647";
            }
            description
                "[0..2147483647] packets";
          } //rising-threshold

          leaf falling-threshold {
            type uint32;
          } //falling-threshold

          leaf direction {
            type enumeration {
              enum inbound;
              enum outbound;
              enum roundtrip;
            }
            description
                "inbound|outbound|roundtrip 
                 keywords - Def: roundtrip";
          } //direction

        } //container loss-event

        container probe-history {
          description
              "Configure probe history retention";
          leaf keep-drop-auto {
            type enumeration {
              enum keep;
              enum drop;
              enum auto;
            }
            description
                "keywords - specify the probe history retention option";
          } //keep-drop-auto

        } //container probe-history

        leaf shutdown {
          type boolean;
          description
              "Administratively enable/disable the SAA test";
        }

        container trap-gen {
          description
              "Configure trap generation for the SAA test";
          leaf probe-fail-enable {
            type boolean;
            description
                "enable trap generation on ping probe failure";
          }

          container probe-fail-threshold {
            description
                "configure threshold for trap generation on ping probe failure";
            leaf threshold {
              type uint32 {
                range "0..15";
              }
              description
                  "[0..15]";
            } //threshold

          } //container probe-fail-threshold

          leaf test-completion-enable {
            type boolean;
            description
                "enable trap generation on test completion";
          }

          leaf test-fail-enable {
            type boolean;
            description
                "enable trap generation on test failure";
          }

          container test-fail-threshold {
            description
                "configure threshold for trap generation on test failure";
            leaf threshold {
              type uint32 {
                range "0..15";
              }
              description
                  "[0..15]";
            } //threshold

          } //container test-fail-threshold

        } //container trap-gen

        container type {
          presence
              "Configure type of SAA test";
          container cpe-ping {
            description
                "Configure CPE ping test";
            leaf service {
              type string;
              description
                  "[1..2147483647]|<service-name:64 char max>";
            } //service

            leaf destination {
              type inet:ip-address;
            } //destination

            leaf source {
              type inet:ip-address;
            } //source

            leaf ttl {
              type uint16 {
                range "1..255";
              }
            } //ttl

            leaf return-control {
              type boolean;
              description
                  "keyword - receives on the control plane";
            } //return-control

            leaf source-mac {
              type string;
              description
                  "xx:xx:xx:xx:xx:xx or xx-xx-xx-xx-xx-xx 
                   All zero and multicast not allowed";
            } //source-mac

            leaf interval {
              type uint32 {
                range "1..10";
              }
              description
                  "[1..10] seconds";
            } //interval

            leaf count {
              type uint16 {
                range "1..100";
              }
            } //count

            leaf send-control {
              type boolean;
              status "obsolete";
              description
                  "keyword - sends via the control plane";
            } //send-control

            leaf fc {
              type enumeration {
                enum be;
                enum l2;
                enum af;
                enum l1;
                enum h2;
                enum ef;
                enum h1;
                enum nc;
              }
              default "be";
              description
                  "be|l2|af|l1|h2|ef|h1|nc - Default: be";
            } //fc

            leaf profile {
              type enumeration {
                enum in;
                enum out;
              }
              default "out";
              description
                  "keywords - Default: out";
            } //profile

          } //container cpe-ping

          container dns {
            description
                "Configure DNS name resolution test";
            leaf target-addr {
              type string {
                length "1..255";
              }
              description
                  "[max 255 characters]";
            } //target-addr

            leaf name-server {
              type string;
              description
                  "Attribute ip-address for dns";
            } //name-server

            leaf source {
              type string;
              description
                  "ip-address";
            } //source

            leaf count {
              type uint16 {
                range "1..100";
              }
              default 1;
              description
                  "[1..100] Default: 1";
            } //count

            leaf timeout {
              type uint64 {
                range "1..120";
              }
              default 5;
              description
                  "[1..120] seconds - Default: 5";
            } //timeout

            leaf interval {
              type int32 {
                range "1..10";
              }
              default 1;
              description
                  "[1..10] seconds - Default: 1";
            } //interval

            leaf record-type {
              type enumeration {
                enum ipv4-a-record;
                enum ipv6-aaaa-record;
              }
              description
                  "keyword";
            } //record-type

          } //container dns

          container eth-cfm-linktrace {
            description
                "Configure Ethernet Connectivity Fault Management link trace test";
            leaf mac-address {
              type string {
                length "1..32";
              }
              description
                  "xx:xx:xx:xx:xx:xx or xx-xx-xx-xx-xx-xx";
            } //mac-address

            leaf ttl {
              type uint32 {
                range "1..255";
              }
              default 64;
              description
                  "[1..255] - Default: 64";
            } //ttl

            leaf count {
              type uint16 {
                range "1..10";
              }
              default 1;
              description
                  "[1..10] packets - Default: 1";
            } //count

            leaf timeout {
              type uint64 {
                range "1..10";
              }
              default 5;
              description
                  "[1..10] seconds - Default: 5";
            } //timeout

            leaf interval {
              type int32 {
                range "1..10";
              }
              default 5;
              description
                  "[1..10] seconds - Default: 5";
            } //interval

            leaf fc {
              type enumeration {
                enum be;
                enum l2;
                enum af;
                enum l1;
                enum h2;
                enum ef;
                enum h1;
                enum nc;
              }
              default "nc";
              description
                  "be|l2|af|l1|h2|ef|h1|nc - Default: nc";
            } //fc

            leaf profile {
              type enumeration {
                enum in;
                enum out;
              }
              default "in";
              description
                  "keywords - Default: in";
            } //profile

            leaf remote-mepid {
              type uint32 {
                range "1..8191";
              }
              description
                  "mep-id";
            } //remote-mepid

            leaf mep {
              type uint32 {
                range "1..8191";
              }
            } //mep

            leaf domain {
              type uint32 {
                range "1..4294967295";
              }
            } //domain

            leaf association {
              type uint32 {
                range "1..4294967295";
              }
            } //association

          } //container eth-cfm-linktrace

          container eth-cfm-loopback {
            description
                "Configure Ethernet Connectivity Fault Management loopback test";
            leaf mac-address {
              type string {
                length "1..32";
              }
              description
                  "xx:xx:xx:xx:xx:xx or xx-xx-xx-xx-xx-xx";
            } //mac-address

            leaf size {
              type uint32 {
                range "0..1500";
              }
              default 0;
              description
                  "[0..1500] bytes - Default: 0";
            } //size

            leaf count {
              type uint16 {
                range "1..100";
              }
              default 1;
              description
                  "[1..100] packets - Default: 1";
            } //count

            leaf timeout {
              type uint64 {
                range "1..10";
              }
              default 5;
              description
                  "[1..10] seconds - Default: 5";
            } //timeout

            leaf interval {
              type int32 {
                range "1..10";
              }
              default 5;
              description
                  "[1..10] seconds - Default: 5";
            } //interval

            leaf fc {
              type enumeration {
                enum be;
                enum l2;
                enum af;
                enum l1;
                enum h2;
                enum ef;
                enum h1;
                enum nc;
              }
              default "nc";
              description
                  "be|l2|af|l1|h2|ef|h1|nc - Default: nc";
            } //fc

            leaf profile {
              type enumeration {
                enum in;
                enum out;
              }
              default "in";
              description
                  "keywords - Default: in";
            } //profile

            leaf remote-mepid {
              type uint32 {
                range "1..8191";
              }
              description
                  "mep-id";
            } //remote-mepid

            leaf mep {
              type uint32 {
                range "1..8191";
              }
            } //mep

            leaf domain {
              type uint32 {
                range "1..4294967295";
              }
            } //domain

            leaf association {
              type uint32 {
                range "1..4294967295";
              }
            } //association

          } //container eth-cfm-loopback

          container eth-cfm-two-way-delay {
            description
                "Configure Ethernet Connectivity Fault Management two way delay test";
            leaf mac-address {
              type string {
                length "1..32";
              }
              description
                  "xx:xx:xx:xx:xx:xx or xx-xx-xx-xx-xx-xx";
            } //mac-address

            leaf count {
              type uint32 {
                range "1..1000";
              }
              default 1;
              description
                  "[1..1000] packets - Default: 1";
            } //count

            leaf timeout {
              type uint64 {
                range "1..10";
              }
              default 5;
              description
                  "[1..10] seconds - Default: 5";
            } //timeout

            leaf interval {
              type string;
              description
                  "[0.1, 0.2, .. 0.9] | [1, 2, .. 10] seconds - Default: 5";
            } //interval

            leaf fc {
              type enumeration {
                enum be;
                enum l2;
                enum af;
                enum l1;
                enum h2;
                enum ef;
                enum h1;
                enum nc;
              }
              default "nc";
              description
                  "be|l2|af|l1|h2|ef|h1|nc - Default: nc";
            } //fc

            leaf profile {
              type enumeration {
                enum in;
                enum out;
              }
              default "in";
              description
                  "keywords - Default: in";
            } //profile

            leaf remote-mepid {
              type uint32 {
                range "1..8191";
              }
              description
                  "mep-id";
            } //remote-mepid

            leaf mep {
              type uint32 {
                range "1..8191";
              }
            } //mep

            leaf domain {
              type uint32 {
                range "1..4294967295";
              }
            } //domain

            leaf association {
              type uint32 {
                range "1..4294967295";
              }
            } //association

          } //container eth-cfm-two-way-delay

          container eth-cfm-two-way-slm {
            description
                "Configure Ethernet Connectivity Fault Management two-way SLM test";
            leaf mac-address {
              type string {
                length "1..32";
              }
              description
                  "xx:xx:xx:xx:xx:xx or xx-xx-xx-xx-xx-xx";
            } //mac-address

            leaf count {
              type uint32 {
                range "1..1000";
              }
              default 1;
              description
                  "[1..1000] packets - Default: 1";
            } //count

            leaf size {
              type uint32 {
                range "0..1500";
              }
              default 0;
              description
                  "[0..1500] bytes - Default: 0";
            } //size

            leaf timeout {
              type uint64 {
                range "1..10";
              }
              default 5;
              description
                  "[1..10] seconds - Default: 5";
            } //timeout

            leaf interval {
              type string;
              description
                  "[0.1, 0.2, .. 0.9] | [1, 2, .. 10] seconds - Default: 5";
            } //interval

            leaf fc {
              type enumeration {
                enum be;
                enum l2;
                enum af;
                enum l1;
                enum h2;
                enum ef;
                enum h1;
                enum nc;
              }
              default "nc";
              description
                  "be|l2|af|l1|h2|ef|h1|nc - Default: nc";
            } //fc

            leaf profile {
              type enumeration {
                enum in;
                enum out;
              }
              default "in";
              description
                  "keywords - Default: in";
            } //profile

            leaf remote-mepid {
              type uint32 {
                range "1..8191";
              }
              description
                  "mep-id";
            } //remote-mepid

            leaf mep {
              type uint32 {
                range "1..8191";
              }
            } //mep

            leaf domain {
              type uint32 {
                range "1..4294967295";
              }
            } //domain

            leaf association {
              type uint32 {
                range "1..4294967295";
              }
            } //association

          } //container eth-cfm-two-way-slm

          container icmp-ping {
            description
                "Configure ICMP ping test";
            leaf ip-address-dns-name {
              type string;
              description
                  "Attribute ip-address|dns-name for icmp-ping";
            } //ip-address-dns-name

            leaf rapid {
              type boolean;
              description
                  "keyword - change the units for 'interval' from seconds to centiseconds";
            } //rapid

            leaf ttl {
              type uint16 {
                range "1..128";
              }
              default 64;
              description
                  "[1..128] - Default: 64";
            } //ttl

            leaf tos {
              type uint16 {
                range "0..255";
              }
              default 0;
              description
                  "[0..255] - Default: 0";
            } //tos

            leaf size {
              type uint32 {
                range "0..16384";
              }
              default 56;
              description
                  "[0..16384] bytes - Default: 56";
            } //size

            leaf pattern {
              type uint16;
              default 0;
              description
                  "[0..65535] - Default: system-generated sequential pattern";
            } //pattern

            leaf source {
              type string;
            } //source

            leaf interval {
              type int32 {
                range "1..10000";
              }
              default 1;
              description
                  "If 'rapid' is selected, 1..10000 centiseconds, default: 1 centisecond; 
                   Otherwise, 1..10000 seconds, default: 1 second 
                   ";
            } //interval

            leaf next-hop {
              type string;
              description
                  "Attribute ip-address for icmp-ping";
            } //next-hop

            leaf bypass-routing {
              type boolean;
              description
                  "keyword - bypass the routing table";
            } //bypass-routing

            leaf count {
              type uint32 {
                range "1..100000";
              }
              default 5;
              description
                  "[1..100000] requests - Default: 5";
            } //count

            leaf do-not-fragment {
              type boolean;
              description
                  "keyword - do not allow the echo request packet(s) to be fragmented (valid for 
                   IPv4 only)";
            } //do-not-fragment

            leaf interface {
              type string {
                length "1..32";
              }
            } //interface

            leaf router {
              type string {
                length "1..32";
              }
              description
                  "Attribute router-or-service for icmp-ping";
            } //router

            leaf timeout {
              type uint64 {
                range "1..10";
              }
              default 5;
              description
                  "[1..10] seconds - Default: 5";
            } //timeout

            leaf service-name {
              type string;
              description
                  "[64 chars max] 
                   router-instance is the preferred parameter for specifying the service name.";
            } //service-name

            leaf fc {
              type enumeration {
                enum be;
                enum l2;
                enum af;
                enum l1;
                enum h2;
                enum ef;
                enum h1;
                enum nc;
              }
              default "nc";
              description
                  "be|l2|af|l1|h2|ef|h1|nc - Default: nc";
            } //fc

            leaf router-instance {
              type string {
                length "1..64";
              }
              description
                  "Attribute router-instance for icmp-ping";
            } //router-instance

          } //container icmp-ping

          container icmp-trace {
            description
                "Configure ICMP traceroute test";
            leaf ip-address-dns-name {
              type string;
              description
                  "Attribute ip-address|dns-name for icmp-trace";
            } //ip-address-dns-name

            leaf ttl {
              type int16 {
                range "1..255";
              }
              default 30;
              description
                  "[1..255] - Default: 30 hops";
            } //ttl

            leaf wait {
              type string;
              description
                  "[10..60000] - Default: 5000 milliseconds";
            } //wait

            leaf source {
              type string;
              description
                  "Attribute ip-address for icmp-trace";
            } //source

            leaf tos {
              type uint16 {
                range "0..255";
              }
              default 0;
              description
                  "[0..255] - Default: 0";
            } //tos

            leaf router {
              type string {
                length "1..32";
              }
              description
                  "Attribute router-or-service for icmp-trace";
            } //router

            leaf service-name {
              type string;
              description
                  "[64 chars max] 
                   router-instance is the preferred parameter for specifying the service name.";
            } //service-name

            leaf router-instance {
              type string {
                length "1..64";
              }
              description
                  "Attribute router-instance for icmp-trace";
            } //router-instance

          } //container icmp-trace

          container lsp-ping {
            description
                "Configure LSP ping test";
            leaf size {
              type uint32 {
                range "1..9198";
              }
              default 1;
              description
                  "[1..9198] - Default: 1";
            } //size

            leaf ttl {
              type uint16 {
                range "1..255";
              }
              default 255;
              description
                  "[1..255] - Default: 255";
            } //ttl

            leaf timeout {
              type uint32 {
                range "1..10";
              }
              default 5;
              description
                  "[1..10] seconds - Default: 5";
            } //timeout

            leaf interval {
              type uint32 {
                range "1..10";
              }
              default 1;
              description
                  "[1..10] seconds - Default: 1";
            } //interval

            leaf profile {
              type enumeration {
                enum in;
                enum out;
              }
              default "out";
              description
                  "keywords - Default: out";
            } //profile

            leaf send-count {
              type uint16 {
                range "1..100";
              }
              default 1;
              description
                  "[1..100] packets - Default: 1";
            } //send-count

            leaf path {
              type string {
                length "1..32";
              }
            } //path

            leaf interface {
              type string {
                length "1..32";
              }
            } //interface

            leaf next-hop {
              type string;
            } //next-hop

            leaf src-ip-address {
              type string;
              description
                  "Attribute ip-address for lsp-ping";
            } //src-ip-address

            leaf bgp-label {
              type boolean;
              description
                  "keyword - use the Target FEC Stack sub-type 'BGP labeled IPv4 prefix'";
            } //bgp-label

            leaf static {
              type boolean;
              description
                  "keyword - use the Target FEC Stack sub-type 'Static LSP'";
            } //static

            leaf dest-global-id {
              type uint64;
              default 0;
              description
                  "[0..4294967295] - Default: 0";
            } //dest-global-id

            leaf dest-node-id {
              type string;
              default "0";
              description
                  "a.b.c.d|<1..4294967295> - Default: 0";
            } //dest-node-id

            leaf assoc-channel {
              type enumeration {
                enum ipv4;
                enum non-ip;
                enum none;
              }
              default "non-ip";
              description
                  "keywords - Default: non-ip";
            } //assoc-channel

            leaf path-type {
              type enumeration {
                enum active;
                enum working;
                enum protect;
              }
              default "active";
              description
                  "keywords - Default: active";
            } //path-type

            leaf prefix {
              type string;
              description
                  "Attribute ip-prefix/prefix-length for lsp-ping";
            } //prefix

            leaf lsp-name {
              type string {
                length "1..64";
              }
            } //lsp-name

            leaf fc {
              type enumeration {
                enum be;
                enum l2;
                enum af;
                enum l1;
                enum h2;
                enum ef;
                enum h1;
                enum nc;
              }
              default "be";
              description
                  "be|l2|af|l1|h2|ef|h1|nc - Default: be";
            } //fc

            leaf path-destination {
              type string;
            } //path-destination

            leaf igp-instance {
              type string;
              description
                  "Attribute igp-instance for lsp-ping";
            } //igp-instance

            leaf sr-isis {
              type boolean;
              description
                  "keyword - select a Segment Routing Intermediate System to Intermediate System 
                   (IS-IS) LSP ping";
            } //sr-isis

            leaf sr-ospf {
              type boolean;
              description
                  "keyword - select a Segment Routing Open Shortest Path First (OSPF) LSP ping";
            } //sr-ospf

            leaf sr-te {
              type boolean;
              description
                  "keyword - select a Segment Routing Traffic Engineering (SR-TE) LSP ping";
            } //sr-te

          } //container lsp-ping

          container lsp-trace {
            description
                "Configure LSP trace test";
            leaf size {
              type uint32 {
                range "1..9198";
              }
              default 1;
              description
                  "[1..9198] - Default: 1";
            } //size

            leaf min-ttl {
              type uint16 {
                range "1..255";
              }
              default 1;
              description
                  "[1..255] - Default: 1";
            } //min-ttl

            leaf max-ttl {
              type uint16 {
                range "1..255";
              }
              default 30;
              description
                  "[1..255] - Default: 30";
            } //max-ttl

            leaf max-fail {
              type string;
              description
                  "[1..255] - Default: 5";
            } //max-fail

            leaf probe-count {
              type uint16 {
                range "1..10";
              }
              default 1;
              description
                  "[1..10] - Default: 1";
            } //probe-count

            leaf timeout {
              type uint32 {
                range "1..60";
              }
              default 3;
              description
                  "[1..60] seconds - Default: 3";
            } //timeout

            leaf interval {
              type uint32 {
                range "1..10";
              }
              default 1;
              description
                  "[1..10] seconds - Default: 1";
            } //interval

            leaf profile {
              type enumeration {
                enum in;
                enum out;
              }
              default "out";
              description
                  "keywords - Default: out";
            } //profile

            leaf path {
              type string {
                length "1..32";
              }
            } //path

            leaf interface {
              type string {
                length "1..32";
              }
            } //interface

            leaf next-hop {
              type string;
            } //next-hop

            leaf src-ip-address {
              type string;
              description
                  "Attribute ip-address for lsp-trace";
            } //src-ip-address

            leaf downstream-map-tlv {
              type enumeration {
                enum dsmap;
                enum ddmap;
                enum none;
              }
              description
                  "Attribute downstream-map-tlv for lsp-trace";
            } //downstream-map-tlv

            leaf bgp-label {
              type boolean;
              description
                  "keyword - use the Target FEC Stack sub-type 'BGP labeled IPv4 prefix'";
            } //bgp-label

            leaf static {
              type boolean;
              description
                  "keyword - use the Target FEC Stack sub-type 'Static LSP'";
            } //static

            leaf assoc-channel {
              type enumeration {
                enum ipv4;
                enum non-ip;
                enum none;
              }
              default "non-ip";
              description
                  "keywords - Default: non-ip";
            } //assoc-channel

            leaf path-type {
              type enumeration {
                enum active;
                enum working;
                enum protect;
              }
              default "active";
              description
                  "keywords - Default: active";
            } //path-type

            leaf lsp-name {
              type string {
                length "1..64";
              }
            } //lsp-name

            leaf prefix {
              type string;
              description
                  "Attribute ip-prefix/prefix-length for lsp-trace";
            } //prefix

            leaf fc {
              type enumeration {
                enum be;
                enum l2;
                enum af;
                enum l1;
                enum h2;
                enum ef;
                enum h1;
                enum nc;
              }
              default "be";
              description
                  "be|l2|af|l1|h2|ef|h1|nc - Default: be";
            } //fc

            leaf path-destination {
              type string;
            } //path-destination

            leaf igp-instance {
              type string;
              description
                  "Attribute igp-instance for lsp-trace";
            } //igp-instance

            leaf sr-isis {
              type boolean;
              description
                  "keyword - select a Segment Routing Intermediate System to Intermediate System 
                   (IS-IS) LSP trace";
            } //sr-isis

            leaf sr-ospf {
              type boolean;
              description
                  "keyword - select a Segment Routing Open Shortest Path First (OSPF) LSP trace";
            } //sr-ospf

            leaf sr-te {
              type boolean;
              description
                  "keyword - select a Segment Routing Traffic Engineering (SR-TE) LSP trace";
            } //sr-te

          } //container lsp-trace

          container mac-ping {
            description
                "Configure MAC ping test";
            leaf service {
              type string;
              description
                  "[1..2147483647]|<service-name:64 char max>";
            } //service

            leaf destination {
              type string;
              description
                  "xx:xx:xx:xx:xx:xx or xx-xx-xx-xx-xx-xx 
                   All zero not allowed";
            } //destination

            leaf size {
              type uint32 {
                range "1..9198";
              }
            } //size

            leaf ttl {
              type uint16 {
                range "1..255";
              }
            } //ttl

            leaf send-control {
              type boolean;
              status "obsolete";
              description
                  "keyword - sends via the control plane";
            } //send-control

            leaf return-control {
              type boolean;
              description
                  "keyword - receives on the control plane";
            } //return-control

            leaf source {
              type string;
              description
                  "xx:xx:xx:xx:xx:xx or xx-xx-xx-xx-xx-xx 
                   All zero and multicast not allowed";
            } //source

            leaf interval {
              type uint32 {
                range "1..10";
              }
              description
                  "[1..10] seconds";
            } //interval

            leaf count {
              type uint16 {
                range "1..100";
              }
            } //count

            leaf timeout {
              type uint32 {
                range "1..10";
              }
              description
                  "[1..10] seconds";
            } //timeout

            leaf fc {
              type enumeration {
                enum be;
                enum l2;
                enum af;
                enum l1;
                enum h2;
                enum ef;
                enum h1;
                enum nc;
              }
              default "be";
              description
                  "be|l2|af|l1|h2|ef|h1|nc - Default: be";
            } //fc

            leaf profile {
              type enumeration {
                enum in;
                enum out;
              }
              default "out";
              description
                  "keywords - Default: out";
            } //profile

          } //container mac-ping

          container mac-trace {
            description
                "Configure MAC trace test";
            leaf service {
              type string;
              description
                  "[1..2147483647]|<service-name:64 char max>";
            } //service

            leaf destination {
              type string;
              description
                  "xx:xx:xx:xx:xx:xx or xx-xx-xx-xx-xx-xx 
                   All zero not allowed";
            } //destination

            leaf size {
              type uint32 {
                range "1..9198";
              }
            } //size

            leaf min-ttl {
              type uint16 {
                range "1..255";
              }
            } //min-ttl

            leaf max-ttl {
              type uint16 {
                range "1..255";
              }
              description
                  "vc-label-ttl";
            } //max-ttl

            leaf send-control {
              type boolean;
              status "obsolete";
              description
                  "keyword - sends via the control plane";
            } //send-control

            leaf return-control {
              type boolean;
              description
                  "keyword - receives on the control plane";
            } //return-control

            leaf source {
              type string;
            } //source

            leaf probe-count {
              type uint16 {
                range "1..10";
              }
            } //probe-count

            leaf interval {
              type uint32 {
                range "1..10";
              }
              description
                  "[1..10] seconds";
            } //interval

            leaf timeout {
              type string;
              description
                  "[1..60] seconds";
            } //timeout

            leaf fc {
              type enumeration {
                enum be;
                enum l2;
                enum af;
                enum l1;
                enum h2;
                enum ef;
                enum h1;
                enum nc;
              }
              default "be";
              description
                  "be|l2|af|l1|h2|ef|h1|nc - Default: be";
            } //fc

            leaf profile {
              type enumeration {
                enum in;
                enum out;
              }
              default "out";
              description
                  "keywords - Default: out";
            } //profile

          } //container mac-trace

          container sdp-ping {
            description
                "Configure SDP ping test";
            leaf orig-sdp-id {
              type uint32 {
                range "1..32767";
              }
            } //orig-sdp-id

            leaf resp-sdp {
              type uint32 {
                range "1..32767";
              }
            } //resp-sdp

            leaf fc {
              type enumeration {
                enum be;
                enum l2;
                enum af;
                enum l1;
                enum h2;
                enum ef;
                enum h1;
                enum nc;
              }
              default "be";
              description
                  "be|l2|af|l1|h2|ef|h1|nc - Default: be";
            } //fc

            leaf profile {
              type enumeration {
                enum in;
                enum out;
              }
              default "out";
              description
                  "keywords - Default: out";
            } //profile

            leaf step {
              type uint16 {
                range "1..512";
              }
            } //step

            leaf timeout {
              type uint32 {
                range "1..10";
              }
              default 5;
              description
                  "[1..10] - Default: 5 seconds";
            } //timeout

            leaf interval {
              type uint32 {
                range "1..10";
              }
              default 1;
              description
                  "[1..10] - Default: 1 second";
            } //interval

            leaf size {
              type string;
              description
                  "[72..9198] - Default: 72 octets";
            } //size

            leaf count {
              type uint16 {
                range "1..100";
              }
              default 1;
              description
                  "[1..100] - Default: 1 probe";
            } //count

          } //container sdp-ping

          container vccv-ping {
            description
                "Configure VCCV ping test";
            leaf reply-mode {
              type enumeration {
                enum ip-routed;
                enum control-channel;
              }
              default "control-channel";
              description
                  "keywords - Default: control-channel";
            } //reply-mode

            leaf profile {
              type enumeration {
                enum in;
                enum out;
              }
              default "out";
              description
                  "keywords - specify profile - Default: out";
            } //profile

            leaf size {
              type uint32 {
                range "1..9198";
              }
              default 1;
              description
                  "[1..9198] - Default: 1";
            } //size

            leaf count {
              type uint32 {
                range "1..100";
              }
              default 1;
              description
                  "[1..100] packets - Default: 1";
            } //count

            leaf timeout {
              type uint32 {
                range "1..10";
              }
              default 5;
              description
                  "[1..10] seconds - Default: 5";
            } //timeout

            leaf interval {
              type uint32 {
                range "1..10";
              }
              default 1;
              description
                  "[1..10] seconds - Default: 1";
            } //interval

            leaf ttl {
              type uint32 {
                range "1..255";
              }
              default 1;
              description
                  "[1..255] - Default: 1";
            } //ttl

            leaf spoke-sdp-fec {
              type uint32 {
                range "1..4294967295";
              }
            } //spoke-sdp-fec

            leaf saii-type2 {
              type string {
              }
              description
                  "Attribute global-id:prefix:ac-id for vccv-ping";
            } //saii-type2

            leaf taii-type2 {
              type string {
              }
              description
                  "global-id:prefix:ac-id";
            } //taii-type2

            leaf static {
              type boolean;
              description
                  "keyword - use the Target FEC Stack sub-type 'Static Pseudowire'";
            } //static

            leaf dest-global-id {
              type uint64;
              default 0;
              description
                  "[0..4294967295] - Default: 0";
            } //dest-global-id

            leaf dest-node-id {
              type string;
              default "0";
              description
                  "a.b.c.d|<1..4294967295> - Default: 0";
            } //dest-node-id

            leaf assoc-channel {
              type enumeration {
                enum ipv4;
                enum non-ip;
              }
              default "non-ip";
              description
                  "keywords - Default: non-ip";
            } //assoc-channel

            leaf sdp-id-vc-id {
              type string;
              description
                  "sdp-id - [1..32767] 
                   vc-id - [1..4294967295]";
            } //sdp-id-vc-id

            leaf fc {
              type enumeration {
                enum be;
                enum l2;
                enum af;
                enum l1;
                enum h2;
                enum ef;
                enum h1;
                enum nc;
              }
              default "be";
              description
                  "be|l2|af|l1|h2|ef|h1|nc - Default: be";
            } //fc

            leaf src-ip-address {
              type inet:ip-address;
            } //src-ip-address

            leaf dst-ip-address {
              type inet:ip-address;
            } //dst-ip-address

            leaf pw-id {
              type uint32 {
                range "1..4294967295";
              }
            } //pw-id

            leaf target-fec-type {
              type enumeration {
                enum pw-id-fec;
                enum static-pw-fec;
              }
              description
                  "keywords - used when the VCCV to be tested switches to a different FEC 
                   (Forward Equivalence Class)";
            } //target-fec-type

            leaf sender-src-address {
              type inet:ip-address;
            } //sender-src-address

            leaf remote-dst-address {
              type inet:ip-address;
            } //remote-dst-address

            leaf pw-type {
              type string;
              description
                  "atm-cell (=3) | atm-sdu (=2) | atm-vcc (=9) | atm-vpc (=10) | cesopsn (=21) | 
                   cesopsn-cas (=23) | ether (=5) | satop-e1 (=17) | satop-t1 (=18) | [1..65535]";
            } //pw-type

            leaf agi {
              type string {
                length "1..21";
              }
              description
                  "<0..4294967295>:<0..4294967295>";
            } //agi

            leaf pw-path-id-saii {
              type string {
              }
              description
                  "Attribute global-id:node-id:ac-id for vccv-ping";
            } //pw-path-id-saii

            leaf pw-path-id-taii {
              type string {
              }
              description
                  "global-id:node-id:ac-id";
            } //pw-path-id-taii

          } //container vccv-ping

          container vccv-trace {
            description
                "Configure VCCV traceroute test";
            leaf size {
              type uint32 {
                range "1..9198";
              }
              default 1;
              description
                  "[1..9198] - Default: 1";
            } //size

            leaf min-ttl {
              type int32 {
                range "1..255";
              }
              default 1;
              description
                  "[1..255] - Default: 1";
            } //min-ttl

            leaf max-ttl {
              type int32 {
                range "1..255";
              }
              default 8;
              description
                  "[1..255] - Default: 8";
            } //max-ttl

            leaf max-fail {
              type string;
              description
                  "[1..255] - Default: 5";
            } //max-fail

            leaf probe-count {
              type int32 {
                range "1..10";
              }
              default 1;
              description
                  "[1..10] - Default: 1";
            } //probe-count

            leaf timeout {
              type int32 {
                range "1..60";
              }
              default 3;
              description
                  "[1..60] seconds - Default: 3";
            } //timeout

            leaf interval {
              type int32 {
                range "1..255";
              }
              default 1;
              description
                  "[1..255] seconds - Default: 1";
            } //interval

            leaf profile {
              type enumeration {
                enum in;
                enum out;
              }
              default "out";
              description
                  "keywords - Default: out";
            } //profile

            leaf reply-mode {
              type enumeration {
                enum ip-routed;
                enum control-channel;
              }
              default "control-channel";
              description
                  "keywords - Default: control-channel";
            } //reply-mode

            leaf spoke-sdp-fec {
              type uint32 {
                range "1..4294967295";
              }
            } //spoke-sdp-fec

            leaf saii-type2 {
              type string {
              }
              description
                  "Attribute global-id:prefix:ac-id for vccv-trace";
            } //saii-type2

            leaf taii-type2 {
              type string {
              }
              description
                  "global-id:prefix:ac-id";
            } //taii-type2

            leaf static {
              type boolean;
              description
                  "keyword - use the Target FEC Stack sub-type 'Static Pseudowire'";
            } //static

            leaf assoc-channel {
              type enumeration {
                enum ipv4;
                enum non-ip;
              }
              default "non-ip";
              description
                  "keywords - Default: non-ip";
            } //assoc-channel

            leaf src-ip-address {
              type inet:ip-address;
            } //src-ip-address

            leaf sdp-id-vc-id {
              type string;
              description
                  "sdp-id - [1..32767] 
                   vc-id - [1..4294967295]";
            } //sdp-id-vc-id

            leaf fc {
              type enumeration {
                enum be;
                enum l2;
                enum af;
                enum l1;
                enum h2;
                enum ef;
                enum h1;
                enum nc;
              }
              default "be";
              description
                  "be|l2|af|l1|h2|ef|h1|nc - Default: be";
            } //fc

            leaf target-fec-type {
              type enumeration {
                enum pw-id-fec;
                enum static-pw-fec;
              }
              description
                  "keywords - used when the VCCV to be tested switches to a different FEC 
                   (Forward Equivalence Class)";
            } //target-fec-type

            leaf sender-src-address {
              type inet:ip-address;
            } //sender-src-address

            leaf remote-dst-address {
              type inet:ip-address;
            } //remote-dst-address

            leaf pw-id {
              type uint32 {
                range "1..4294967295";
              }
            } //pw-id

            leaf pw-type {
              type string;
              description
                  "atm-cell (=3) | atm-sdu (=2) | atm-vcc (=9) | atm-vpc (=10) | cesopsn (=21) | 
                   cesopsn-cas (=23) | ether (=5) | satop-e1 (=17) | satop-t1 (=18) | [1..65535]";
            } //pw-type

            leaf agi {
              type string {
                length "1..21";
              }
              description
                  "<0..4294967295>:<0..4294967295>";
            } //agi

            leaf pw-path-id-saii {
              type string {
              }
              description
                  "Attribute global-id:node-id:ac-id for vccv-trace";
            } //pw-path-id-saii

            leaf pw-path-id-taii {
              type string {
              }
              description
                  "global-id:node-id:ac-id";
            } //pw-path-id-taii

          } //container vccv-trace

          container vprn-ping {
            description
                "Configure VPRN ping test";
            leaf service-id {
              type string;
              description
                  "[1..2147483647]";
            } //service-id

            leaf source {
              type string;
              description
                  "Attribute ip-address for vprn-ping";
            } //source

            leaf destination {
              type string;
              description
                  "ip-address";
            } //destination

            leaf size {
              type uint32 {
                range "1..9198";
              }
            } //size

            leaf ttl {
              type uint16 {
                range "1..255";
              }
            } //ttl

            leaf return-control {
              type boolean;
              description
                  "keyword - receives on the control plane";
            } //return-control

            leaf interval {
              type int32 {
                range "1..10";
              }
              description
                  "[1..10] seconds";
            } //interval

            leaf count {
              type uint16 {
                range "1..100";
              }
            } //count

            leaf timeout {
              type uint32 {
                range "1..100";
              }
              description
                  "[1..100] seconds";
            } //timeout

            leaf fc {
              type enumeration {
                enum be;
                enum l2;
                enum af;
                enum l1;
                enum h2;
                enum ef;
                enum h1;
                enum nc;
              }
              default "be";
              description
                  "be|l2|af|l1|h2|ef|h1|nc - Default: be";
            } //fc

            leaf profile {
              type enumeration {
                enum in;
                enum out;
              }
              default "out";
              description
                  "keywords - Default: out";
            } //profile

            leaf service {
              type string;
              description
                  "64 char max";
            } //service

          } //container vprn-ping

          container vprn-trace {
            description
                "Configure VPRN trace test";
            leaf service-id {
              type string;
              description
                  "[1..2147483647]";
            } //service-id

            leaf source {
              type string;
              description
                  "Attribute ip-address for vprn-trace";
            } //source

            leaf destination {
              type string;
              description
                  "ip-address";
            } //destination

            leaf size {
              type uint32 {
                range "1..9198";
              }
            } //size

            leaf min-ttl {
              type uint16 {
                range "1..255";
              }
            } //min-ttl

            leaf max-ttl {
              type uint16 {
                range "1..255";
              }
              description
                  "vc-label-ttl";
            } //max-ttl

            leaf return-control {
              type boolean;
              description
                  "keyword - receives on the control plane";
            } //return-control

            leaf probe-count {
              type uint16 {
                range "1..10";
              }
            } //probe-count

            leaf interval {
              type int32 {
                range "1..10";
              }
              description
                  "[1..10] seconds";
            } //interval

            leaf timeout {
              type string;
              description
                  "[1..60] seconds";
            } //timeout

            leaf fc {
              type enumeration {
                enum be;
                enum l2;
                enum af;
                enum l1;
                enum h2;
                enum ef;
                enum h1;
                enum nc;
              }
              default "be";
              description
                  "be|l2|af|l1|h2|ef|h1|nc - Default: be";
            } //fc

            leaf profile {
              type enumeration {
                enum in;
                enum out;
              }
              default "out";
              description
                  "keywords - Default: out";
            } //profile

            leaf service {
              type string;
              description
                  "64 char max";
            } //service

          } //container vprn-trace

        } //container type

      } //list test

    } //container saa

  } //grouping alu-conf-saa-r13

} //module  alu-conf-saa-r13
