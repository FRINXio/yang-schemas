module alu-conf-sflow-r13 {
  yang-version "1";

  namespace "urn:alcatel-lucent.com:sros:ns:yang:conf-sflow-r13";

  prefix "conf-sflow-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure sFlow on SR OS based routers. 
       
       Copyright 2014-2015 Alcatel-Lucent, 2016 Nokia. All rights reserved. 
       Reproduction of this document is authorized on the condition that the 
       foregoing copyright notice is included. 
       
       This alu-conf-sflow-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2014-09-26";

  grouping alu-conf-sflow-r13 {
    container sflow {
      description
          "Configure sFlow";
      container egress-counter-map {
        description
            "Configure sFlow egress counter map";
        leaf policer {
          type uint32 {
            range "1..8";
          }
        } //policer

        leaf queue {
          type uint32 {
            range "1..8";
          }
        } //queue

        leaf traffic-type {
          type enumeration {
            enum unicast;
            enum multicast;
            enum broadcast;
          }
        } //traffic-type

      } //container egress-counter-map

      container ingress-counter-map {
        description
            "Configure sFlow ingress counter map";
        leaf policer {
          type uint32 {
            range "1..32";
          }
        } //policer

        leaf queue {
          type uint32 {
            range "1..32";
          }
        } //queue

        leaf traffic-type {
          type enumeration {
            enum unicast;
            enum multicast;
            enum broadcast;
          }
        } //traffic-type

      } //container ingress-counter-map

      container receiver {
        description
            "Configure an sFlow receiver";
        leaf receiver-name {
          type string {
            length "1..127";
          }
        } //receiver-name

        container ip-addr-backup {
          description
              "Configure the sFlow receiver backup IP address and port";
          leaf ip-address-port {
            type string;
            default "6343";
            description
                "ip-address - a.b.c.d[:port] (IPv4) 
                 x:x:x:x:x:x:x:x (IPv6) 
                 [x:x:x:x:x:x:x:x]:port (IPv6) 
                 x - [0..FFFF]H 
                 port - [1..65535] - Default: 6343";
          } //ip-address-port

        } //container ip-addr-backup

        container ip-addr-primary {
          description
              "Configure the sFlow receiver primary IP address and port";
          leaf ip-address-port {
            type string;
            default "6343";
            description
                "ip-address - a.b.c.d[:port] (IPv4) 
                 x:x:x:x:x:x:x:x (IPv6) 
                 [x:x:x:x:x:x:x:x]:port (IPv6) 
                 x - [0..FFFF]H 
                 port - [1..65535] - Default: 6343";
          } //ip-address-port

        } //container ip-addr-primary

        container max-data-size {
          description
              "Configure the maximum data size for an sFlow datagram";
          leaf bytes {
            type uint32 {
              range "200..1500";
            }
            default 1400;
            description
                "[200..1500] - Default: 1400";
          } //bytes

        } //container max-data-size

      } //container receiver

    } //container sflow

  } //grouping alu-conf-sflow-r13

} //module  alu-conf-sflow-r13
