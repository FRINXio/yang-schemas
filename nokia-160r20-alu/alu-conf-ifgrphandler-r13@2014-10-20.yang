module alu-conf-ifgrphandler-r13 {
  yang-version "1";

  namespace "urn:alcatel-lucent.com:sros:ns:yang:conf-ifgrphandler-r13";

  prefix "conf-ifgrphandler-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure Interface Group Handlers on SR OS 
       based routers. 
       
       Copyright 2014-2015 Alcatel-Lucent, 2016 Nokia. All rights reserved. 
       Reproduction of this document is authorized on the condition that the 
       foregoing copyright notice is included. 
       
       This alu-conf-ifgrphandler-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2014-10-20";

  grouping alu-conf-ifgrphandler-r13 {
    list interface-group-handler {
      key "index";
      description
          "Configure Interface Group Handlers";
      leaf index {
        type string;
        description
            "Attribute index for interface-group-handler";
      } //index

      list member {
        key "port-id";
        description
            "Configure If-Group-Handler port membership";
        leaf port-id {
          type string {
            length "1..17";
          }
          description
              "slot/mda/port[.channel]";
        } //port-id

      } //list member

      leaf shutdown {
        type boolean;
        description
            "Administratively enable/disable the If-Group-Handler";
      }

      container threshold {
        description
            "Configure the minimum number of active links";
        leaf num-members {
          type string;
          description
              "Attribute num-members for threshold";
        } //num-members

      } //container threshold

    } //list interface-group-handler

  } //grouping alu-conf-ifgrphandler-r13

} //module  alu-conf-ifgrphandler-r13
