module alu-conf-router-fspec-r13 {
  yang-version "1";

  namespace "urn:alcatel-lucent.com:sros:ns:yang:conf-router-fspec-r13";

  prefix "conf-router-fspec-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure flowspec on SR OS based routers. 
       
       Copyright 2014-2015 Alcatel-Lucent, 2016 Nokia. All rights reserved. 
       Reproduction of this document is authorized on the condition that the 
       foregoing copyright notice is included. 
       
       This alu-conf-router-fspec-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-03-01";

  grouping alu-conf-router-fspec-r13 {
    container flowspec {
      description
          "Configure flowspec";
      container ip-filter-max-size {
        description
            "Set the maximum number of entries reserved in the auto-created embedded IP 
             filter for flowspec rules";
        leaf ip-filter-max-size-id {
          type uint32 {
            range "0..262143";
          }
        } //ip-filter-max-size-id

        leaf default {
          type boolean;
        } //default

      } //container ip-filter-max-size

      container ipv6-filter-max-size {
        description
            "Set the maximum number of entries reserved in the auto-created embedded IPv6 
             filter for flowspec rules";
        leaf ipv6-filter-max-size-id {
          type uint32 {
            range "0..262143";
          }
        } //ipv6-filter-max-size-id

        leaf default {
          type boolean;
        } //default

      } //container ipv6-filter-max-size

    } //container flowspec

  } //grouping alu-conf-router-fspec-r13

} //module  alu-conf-router-fspec-r13
