module alu-conf-mirror-r13 {
  yang-version "1";

  namespace "urn:alcatel-lucent.com:sros:ns:yang:conf-mirror-r13";

  prefix "conf-mirror-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure mirror services on SR OS based 
       routers. 
       
       Copyright 2014-2015 Alcatel-Lucent, 2016 Nokia. All rights reserved. 
       Reproduction of this document is authorized on the condition that the 
       foregoing copyright notice is included. 
       
       This alu-conf-mirror-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-03-01";

  grouping alu-conf-mirror-r13 {
    container mirror {
      description
          "Configure mirror services";
      list mirror-dest {
        key "service-id";
        description
            "Configure a mirror destination";
        leaf service-id {
          type string;
          description
              "Attribute service-id for mirror-dest";
        } //service-id

        leaf type {
          type enumeration {
            enum ether;
            enum frame-relay;
            enum ppp;
            enum ip-only;
            enum atm-sdu;
            enum satop-e1;
            enum satop-t1;
            enum satop-e3;
            enum satop-t3;
            enum cesopsn;
            enum cesopsn-cas;
          }
          description
              "Attribute mirror-type for mirror-dest";
        } //type

        leaf name {
          type string;
          description
              "64-char max";
        } //name

        container description {
          description
              "Description for this mirror destination";
          leaf description-string {
            type string {
              length "1..80";
            }
          } //description-string

        } //container description

        leaf enable-port-id {
          type boolean;
          description
              "Include port-id of the system in the packet";
        }

        container fc {
          description
              "Configure forwarding class for destination traffic";
          leaf fc-name {
            type enumeration {
              enum be;
              enum l2;
              enum af;
              enum l1;
              enum h2;
              enum ef;
              enum h1;
              enum nc;
            }
          } //fc-name

        } //container fc

        container service-name {
          status "obsolete";
          description
              "Configure a service-name";
          leaf service-name {
            type string;
            description
                "64-char max";
          } //service-name

        } //container service-name

        leaf shutdown {
          type boolean;
          description
              "Administratively enable/disable the mirror service";
        }

        container slice-size {
          description
              "Configure slice-size";
          leaf slice-size {
            type uint32 {
              range "128..9216";
            }
          } //slice-size

        } //container slice-size

        container encap {
          description
              "Encapsulation header";
          container layer-3-encap {
            description
                "Layer-3 header encapsulation";
            leaf layer-3-encap-id {
              type enumeration {
                enum ip-udp-shim;
                enum ip-gre;
              }
            } //layer-3-encap-id

            leaf direction-bit {
              type boolean;
              description
                  "Use the direction bit to indicate ingress/egress";
            }

            container router {
              description
                  "Configure the router instance to transmit the packets in";
              leaf router-instance {
                type string {
                  length "1..32";
                }
                default "Base";
                description
                    "Attribute router-instance for router";
              } //router-instance

              leaf service-name {
                type string;
              } //service-name

            } //container router

            container gateway {
              description
                  "The gateway to send the packets to";
              container ip {
                description
                    "The IP addresses to use";
                leaf src {
                  type inet:ip-address;
                  description
                      "a.b.c.d";
                } //src

                leaf dest {
                  type inet:ip-address;
                  description
                      "ip-address";
                } //dest

              } //container ip

              container udp {
                description
                    "The UDP ports to use";
                leaf src {
                  type int32 {
                    range "1..65535";
                  }
                } //src

                leaf dest {
                  type int32 {
                    range "1..65535";
                  }
                  description
                      "udp-port";
                } //dest

              } //container udp

            } //container gateway

          } //container layer-3-encap

        } //container encap

        list endpoint {
          key "endpoint-name";
          description
              "Configure a service end-point";
          leaf endpoint-name {
            type string {
              length "1..32";
            }
          } //endpoint-name

          container description {
            description
                "Description for the service end-point";
            leaf description-string {
              type string {
                length "1..80";
              }
            } //description-string

          } //container description

          container revert-time {
            description
                "Configure the time to wait before reverting to primary spoke-sdp";
            leaf revert-time {
              type uint32 {
                range "0..600";
              }
              description
                  "[0..600] seconds";
            } //revert-time

            leaf infinite {
              type boolean;
              description
                  "keyword - makes endpoint non-revertive";
            } //infinite

          } //container revert-time

        } //list endpoint

        list pcap {
          key "session-name";
          description
              "Configure PCAP session on mirror-dest.";
          leaf session-name {
            type string {
              length "1..32";
            }
          } //session-name

          container file-url {
            description
                "Specify the file to be used for the PCAP session.";
            leaf file-url {
              type string {
              }
              description
                  "Attribute file-url for file-url";
            } //file-url

          } //container file-url

        } //list pcap

        container remote-source {
          presence
              "Enable/disable remote-source";
          list far-end {
            key "ip-address";
            description
                "Configure Mirror far-end";
            leaf ip-address {
              type inet:ip-address;
            } //ip-address

            leaf ing-svc-label {
              type string;
              description
                  "Attribute ingress-vc-label for far-end";
            } //ing-svc-label

            leaf tldp {
              type boolean;
              description
                  "keyword - specifies signaling to be used";
            } //tldp

            leaf icb {
              type boolean;
              description
                  "keyword - configure spoke-sdp as inter-chassis backup";
            } //icb

            leaf vc-id {
              type uint32 {
                range "1..4294967295";
              }
            } //vc-id

          } //list far-end

          list spoke-sdp {
            key "sdp-id-vc-id";
            description
                "Specify SDP";
            leaf sdp-id-vc-id {
              type string;
              description
                  "sdp-id - [1..32767] 
                   vc-id - [1..4294967295]";
            } //sdp-id-vc-id

            leaf endpoint {
              type string;
            } //endpoint

            leaf no-endpoint {
              type boolean;
            } //no-endpoint

            leaf icb {
              type boolean;
            } //icb

            leaf control-word {
              type boolean;
              description
                  "Enable/disable setting the CW bit in the label message";
            }

            leaf shutdown {
              type boolean;
              description
                  "Administratively enable/disable the spoke SDP binding";
            }

            container control-channel-status {
              description
                  "Configure control channel status information";
              leaf acknowledgment {
                type boolean;
                description
                    "Enable/disable acknowledgment";
              }

              container refresh-timer {
                description
                    "Configure refresh timer";
                leaf seconds {
                  type uint32 {
                    range "10..65535";
                  }
                } //seconds

              } //container refresh-timer

              container request-timer {
                description
                    "Configure request-timer for the control channel status";
                leaf request-timer-secs {
                  type uint32 {
                    range "10..65535";
                  }
                } //request-timer-secs

                leaf retry-timer {
                  type uint32 {
                    range "3..60";
                  }
                } //retry-timer

                leaf timeout-multiplier {
                  type uint32 {
                    range "3..15";
                  }
                } //timeout-multiplier

              } //container request-timer

              leaf shutdown {
                type boolean;
                description
                    "Administratively enable/disable the control channel status";
              }

            } //container control-channel-status

            container egress {
              description
                  "Spoke SDP egress configuration";
              list vc-label {
                key "egress-vc-label";
                description
                    "Configure egress VC label";
                leaf egress-vc-label {
                  type int32 {
                    range "16..1048575";
                  }
                } //egress-vc-label

              } //list vc-label

            } //container egress

            container ingress {
              description
                  "Spoke SDP ingress configuration";
              list vc-label {
                key "ingress-vc-label";
                description
                    "Configure ingress VC label";
                leaf ingress-vc-label {
                  type string;
                  description
                      "Attribute ingress-vc-label for vc-label";
                } //ingress-vc-label

              } //list vc-label

              container l2tpv3 {
                description
                    "Configure L2TPv3 parameters";
                container cookie {
                  description
                      "Configure cookie value for the tunnel";
                  leaf cookie1-value {
                    type string;
                    description
                        "xx-xx-xx-xx-xx-xx-xx-xx or xx:xx:xx:xx:xx:xx:xx:xx";
                  } //cookie1-value

                  leaf cookie2-value {
                    type string;
                    description
                        "xx-xx-xx-xx-xx-xx-xx-xx or xx:xx:xx:xx:xx:xx:xx:xx";
                  } //cookie2-value

                } //container cookie

              } //container l2tpv3

            } //container ingress

            container pw-path-id {
              presence
                  "Configure PW path identifier information";
              container agi {
                description
                    "Configure Attachment Group Identifier";
                leaf route-identifier {
                  type string {
                  }
                  description
                      "<number>:<number>";
                } //route-identifier

              } //container agi

              container saii-type2 {
                description
                    "Configure Source Attachment Individual Identifier (SAII)";
                leaf global-id-node-id-ac-id {
                  type string {
                  }
                  description
                      "Attribute global-id:node-id:ac-id for saii-type2";
                } //global-id-node-id-ac-id

              } //container saii-type2

              container taii-type2 {
                description
                    "Configure Target Attachment Individual Identifier (TAII)";
                leaf global-id-node-id-ac-id {
                  type string {
                  }
                  description
                      "Attribute global-id:node-id:ac-id for taii-type2";
                } //global-id-node-id-ac-id

              } //container taii-type2

            } //container pw-path-id

          } //list spoke-sdp

        } //container remote-source

        container sap {
          description
              "Specify SAP";
          leaf sap-id {
            type string;
            description
                "Attribute sap-id for sap";
          } //sap-id

          leaf endpoint {
            type string {
              length "1..32";
            }
          } //endpoint

          leaf no-endpoint {
            type boolean;
          } //no-endpoint

          container cem {
            description
                "Configure CEM properties";
            container packet {
              description
                  "Configure jitter buffer and payload size";
              leaf jitter-buffer {
                type uint32 {
                  range "0..250";
                }
                description
                    "[1..250]";
              } //jitter-buffer

              leaf payload-size {
                type uint32 {
                  range "16..2048";
                }
              } //payload-size

            } //container packet

            leaf rtp-header {
              type boolean;
              description
                  "Enable/Disable RTP header";
            }

          } //container cem

          container egress {
            presence
                "Configure SAP egress policies";
            container qos {
              description
                  "Configure an egress QoS policy for the SAP";
              leaf policy-id {
                type string;
                description
                    "[1..65535]|<name:64 char max>";
              } //policy-id

              leaf port-redirect-group {
                type string {
                  length "1..32";
                }
              } //port-redirect-group

              leaf instance {
                type uint16 {
                  range "1..65535";
                }
              } //instance

            } //container qos

            container ip-mirror {
              description
                  "Configure IP Mirror information";
              container sa-mac {
                description
                    "Configure Source and Destination MAC address";
                leaf ieee-address {
                  type string;
                  description
                      "Source MAC address: Multicast/Broadcast/Zeros not allowed";
                } //ieee-address

                leaf da-mac {
                  type string;
                  description
                      "Destination MAC Address: Zeroes not allowed";
                } //da-mac

              } //container sa-mac

            } //container ip-mirror

          } //container egress

        } //container sap

        list spoke-sdp {
          key "sdp-id-vc-id";
          description
              "Specify SDP";
          leaf sdp-id-vc-id {
            type string;
            description
                "sdp-id - [1..32767] 
                 vc-id - [1..4294967295]";
          } //sdp-id-vc-id

          leaf endpoint {
            type string {
              length "1..32";
            }
          } //endpoint

          leaf no-endpoint {
            type boolean;
          } //no-endpoint

          leaf icb {
            type boolean;
          } //icb

          leaf control-word {
            type boolean;
            description
                "Enable/disable setting the CW bit in the label message";
          }

          container precedence {
            description
                "Configure the sdp precedence";
            leaf precedence-value {
              type uint32 {
                range "1..4";
              }
            } //precedence-value

            leaf primary {
              type boolean;
              description
                  "keyword - used to make this the primary spoke-sdp";
            } //primary

          } //container precedence

          leaf shutdown {
            type boolean;
            description
                "Administratively enable/disable the spoke SDP binding";
          }

          container control-channel-status {
            description
                "Configure control channel status information";
            leaf acknowledgment {
              type boolean;
              description
                  "Enable/disable acknowledgment";
            }

            container refresh-timer {
              description
                  "Configure refresh timer";
              leaf seconds {
                type uint32 {
                  range "10..65535";
                }
              } //seconds

            } //container refresh-timer

            container request-timer {
              description
                  "Configure request-timer for the control channel status";
              leaf request-timer-secs {
                type uint32 {
                  range "10..65535";
                }
              } //request-timer-secs

              leaf retry-timer {
                type uint32 {
                  range "3..60";
                }
              } //retry-timer

              leaf timeout-multiplier {
                type uint32 {
                  range "3..15";
                }
              } //timeout-multiplier

            } //container request-timer

            leaf shutdown {
              type boolean;
              description
                  "Administratively enable/disable the control channel status";
            }

          } //container control-channel-status

          container egress {
            description
                "Spoke SDP egress configuration";
            list vc-label {
              key "egress-vc-label";
              description
                  "Configure egress VC label";
              leaf egress-vc-label {
                type int32 {
                  range "16..1048575";
                }
              } //egress-vc-label

            } //list vc-label

            container l2tpv3 {
              description
                  "Configure L2TPv3 parameters";
              container cookie {
                description
                    "Configure cookie value for the tunnel";
                leaf t64-bit-value {
                  type string;
                  description
                      "xx-xx-xx-xx-xx-xx-xx-xx or xx:xx:xx:xx:xx:xx:xx:xx";
                } //t64-bit-value

              } //container cookie

            } //container l2tpv3

          } //container egress

          container ingress {
            description
                "Spoke SDP ingress configuration";
            list vc-label {
              key "ingress-vc-label";
              description
                  "Configure ingress VC label";
              leaf ingress-vc-label {
                type string;
                description
                    "Attribute ingress-vc-label for vc-label";
              } //ingress-vc-label

            } //list vc-label

          } //container ingress

          container pw-path-id {
            presence
                "Configure PW path identifier information";
            container agi {
              description
                  "Configure Attachment Group Identifier";
              leaf route-identifier {
                type string {
                }
                description
                    "<number>:<number>";
              } //route-identifier

            } //container agi

            container saii-type2 {
              description
                  "Configure Source Attachment Individual Identifier (SAII)";
              leaf global-id-node-id-ac-id {
                type string {
                }
                description
                    "Attribute global-id:node-id:ac-id for saii-type2";
              } //global-id-node-id-ac-id

            } //container saii-type2

            container taii-type2 {
              description
                  "Configure Target Attachment Individual Identifier (TAII)";
              leaf global-id-node-id-ac-id {
                type string {
                }
                description
                    "Attribute global-id:node-id:ac-id for taii-type2";
              } //global-id-node-id-ac-id

            } //container taii-type2

          } //container pw-path-id

        } //list spoke-sdp

      } //list mirror-dest

      list mirror-source {
        key "service-id";
        description
            "Configure a mirror source";
        leaf service-id {
          type string;
          description
              "Attribute service-id for mirror-source";
        } //service-id

        list ip-filter {
          key "ip-filter-id";
          description
              "Configure mirroring of packets matching entries for an IP filter to a mirror 
               destination";
          leaf ip-filter-id {
            type string;
            description
                "[1..65535]|<name:64 char max>";
          } //ip-filter-id

          leaf-list entry {
            type uint32 {
              range "1..2097151";
            }
            max-elements 8;
          } //entry

        } //list ip-filter

        list ipv6-filter {
          key "ipv6-filter-id";
          description
              "Configure mirroring of packets matching entries for an IPv6 filter to a mirror 
               destination";
          leaf ipv6-filter-id {
            type string;
            description
                "[1..65535]|<name:64 char max>";
          } //ipv6-filter-id

          leaf-list entry {
            type uint32 {
              range "1..2097151";
            }
            max-elements 8;
          } //entry

        } //list ipv6-filter

        list mac-filter {
          key "mac-filter-id";
          description
              "Configure mirroring of packets matching entries of a mac filter to a mirror 
               destination";
          leaf mac-filter-id {
            type string;
            description
                "[1..65535]|<name:64 char max>";
          } //mac-filter-id

          leaf-list entry {
            type uint32 {
              range "1..2097151";
            }
            max-elements 8;
          } //entry

        } //list mac-filter

        container port {
          description
              "Associate a port with a mirror source";
          leaf port-id {
            type string {
              length "1..64";
            }
            description
                "Attribute port-id for port";
          } //port-id

          leaf lag {
            type string;
            description
                "Attribute lag-id for port";
          } //lag

          leaf egress {
            type boolean;
          } //egress

          leaf ingress {
            type boolean;
          } //ingress

        } //container port

        container sap {
          description
              "Associate a SAP with a mirror-source";
          leaf sap-id {
            type string;
            description
                "Attribute sap-id for sap";
          } //sap-id

          leaf ingress {
            type boolean;
          } //ingress

          leaf egress {
            type boolean;
          } //egress

        } //container sap

        leaf shutdown {
          type boolean;
          description
              "Administratively enable/disable the mirror source";
        }

        list subscriber {
          key "sub-ident-string";
          description
              "Add hosts of a subscriber to mirroring service";
          leaf sap {
            type string;
            description
                "Attribute sap-id for subscriber";
          } //sap

          leaf ip {
            type inet:ip-address;
          } //ip

          leaf mac {
            type alu:ieee-address;
            description
                "xx:xx:xx:xx:xx:xx or xx-xx-xx-xx-xx-xx";
          } //mac

          leaf sla-profile {
            type string {
              length "1..32";
            }
          } //sla-profile

          leaf-list fc {
            type enumeration {
              enum be;
              enum l2;
              enum af;
              enum l1;
              enum h2;
              enum ef;
              enum h1;
              enum nc;
            }
            max-elements 8;
          } //fc

          leaf ingress {
            type boolean;
          } //ingress

          leaf egress {
            type boolean;
          } //egress

          leaf sub-ident-string {
            type string {
              length "1..32";
            }
          } //sub-ident-string

          leaf host-type {
            type enumeration {
              enum any;
              enum ipoe;
              enum ppp;
            }
          } //host-type

          leaf family {
            type enumeration {
              enum any;
              enum ipv4;
              enum ipv6;
            }
          } //family

        } //list subscriber

      } //list mirror-source

    } //container mirror

  } //grouping alu-conf-mirror-r13

} //module  alu-conf-mirror-r13
