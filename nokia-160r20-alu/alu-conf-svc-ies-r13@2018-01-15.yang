module alu-conf-svc-ies-r13 {
  yang-version "1";

  namespace "urn:alcatel-lucent.com:sros:ns:yang:conf-svc-ies-r13";

  prefix "conf-svc-ies-r13";

  import alu-conf-svc-ies-if-r13 {
    prefix "conf-svc-ies-if-r13";
  }
  import alu-conf-svc-ies-ipt-r13 {
    prefix "conf-svc-ies-ipt-r13";
  }
  import alu-conf-svc-ies-subif-r13 {
    prefix "conf-svc-ies-subif-r13";
  }
  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure Internet Enhanced Services on SR 
       OS based routers. 
       
       Copyright 2014-2015 Alcatel-Lucent, 2016 Nokia. All rights reserved. 
       Reproduction of this document is authorized on the condition that the 
       foregoing copyright notice is included. 
       
       This alu-conf-svc-ies-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-01-15";

  grouping alu-conf-svc-ies-r13 {
    list ies {
      key "service-id";
      description
          "Configure Internet Enhanced Services";
      leaf service-id {
        type string;
        description
            "Attribute service-id for ies";
      } //service-id

      leaf customer {
        type uint32 {
          range "1..2147483647";
        }
      } //customer

      leaf vpn {
        type uint32 {
          range "1..2147483647";
        }
      } //vpn

      leaf name {
        type string;
        description
            "64-char max";
      } //name

      list description {
        key "description-string";
        description
            "Description for the service";
        leaf description-string {
          type string {
            length "1..80";
          }
        } //description-string

      } //list description

      container service-name {
        status "obsolete";
        description
            "Configure a service name";
        leaf service-name {
          type string;
          description
              "64-char max";
        } //service-name

      } //container service-name

      leaf shutdown {
        type boolean;
        description
            "Administratively enable/disable the service";
      }

      list aa-interface {
        key "aa-if-name";
        description
            "Create/delete or configure an AA interface";
        leaf aa-if-name {
          type string {
            length "1..32";
          }
          description
              "[32 chars max] (must start with a letter)";
        } //aa-if-name

        list address {
          key "ip-address-mask";
          description
              "Assigns an IP address to the interface";
          leaf ip-address-mask {
            type string;
          } //ip-address-mask

        } //list address

        container description {
          description
              "Description for an AA interface";
          leaf description-string {
            type string {
              length "1..80";
            }
          } //description-string

        } //container description

        container ip-mtu {
          description
              "Configure the AA interface IP MTU";
          leaf octets {
            type uint32 {
              range "512..9000";
            }
          } //octets

        } //container ip-mtu

        leaf shutdown {
          type boolean;
          description
              "Administratively enable/disable the interface";
        }

        list sap {
          key "sap-id";
          description
              "Configure a SAP";
          leaf sap-id {
            type string;
            description
                "<sap-id>     : <slot>/<mda>/aa-svc:<vlan> 
                 <slot>     : iom slot (must be IOM3 or above) 
                 <mda>     : isa-aa mda 
                 aa-svc     : keyword 
                 <vlan>     : [1..4094]";
          } //sap-id

          container description {
            description
                "Description for the SAP";
            leaf long-description-string {
              type string {
                length "1..160";
              }
            } //long-description-string

          } //container description

          leaf shutdown {
            type boolean;
            description
                "Administratively enable/disable the SAP";
          }

          container egress {
            description
                "Configure egress parameter";
            list filter {
              key "ip";
              description
                  "Apply egress filter";
              leaf ip {
                type string;
                description
                    "[1..65535]|<name:64 char max>";
              } //ip

            } //list filter

            list qos {
              key "policy-id";
              description
                  "Apply egress qos policy";
              leaf policy-id {
                type string;
                description
                    "[1..65535] | <name : 64 char max>";
              } //policy-id

            } //list qos

          } //container egress

          container ingress {
            description
                "Configure ingress parameter";
            list qos {
              key "policy-id";
              description
                  "Apply ingress qos policy";
              leaf policy-id {
                type string;
                description
                    "[1..65535] | <name : 64 char max>";
              } //policy-id

            } //list qos

          } //container ingress

        } //list sap

      } //list aa-interface

      list aarp-interface {
        key "aarp-int-name";
        description
            "Create/delete or configure an AARP interface";
        leaf aarp-int-name {
          type string {
            length "1..32";
          }
          description
              "[32 chars max] (must start with a letter)";
        } //aarp-int-name

        container description {
          description
              "Description for an AARP interface";
          leaf long-description-string {
            type string {
              length "1..160";
            }
          } //long-description-string

        } //container description

        container ip-mtu {
          description
              "Configure the interface IP MTU";
          leaf octets {
            type uint32 {
              range "512..9000";
            }
          } //octets

        } //container ip-mtu

        leaf shutdown {
          type boolean;
          description
              "Administratively enable/disable the interface";
        }

        list spoke-sdp {
          key "sdp-id-vc-id";
          description
              "Provision a spoke SDP binding";
          leaf sdp-id-vc-id {
            type string;
            description
                "sdp-id - [1..32767] 
                 vc-id - [1..4294967295]";
          } //sdp-id-vc-id

          container aarp {
            description
                "Configure AARP instance id";
            leaf aarpId {
              type uint32 {
                range "1..65535";
              }
            } //aarpId

            leaf type {
              type enumeration {
                enum subscriber-side-shunt;
                enum network-side-shunt;
              }
            } //type

          } //container aarp

          container description {
            description
                "Set description for spoke-sdp";
            leaf description-string {
              type string {
                length "1..80";
              }
            } //description-string

          } //container description

          leaf shutdown {
            type boolean;
            description
                "Administratively enable/disable the spoke SDP binding";
          }

          container egress {
            description
                "Spoke SDP egress configuration";
            container filter {
              description
                  "Apply egress filter";
              leaf ip {
                type string;
                description
                    "[1..65535]|<name:64 char max>";
              } //ip

            } //container filter

            list vc-label {
              key "egress-vc-label";
              description
                  "Configure egress VC label";
              leaf egress-vc-label {
                type int32 {
                  range "16..1048575";
                }
              } //egress-vc-label

            } //list vc-label

          } //container egress

          container ingress {
            description
                "Spoke SDP ingress configuration";
            container filter {
              description
                  "Apply ingress filter";
              leaf ip {
                type string;
                description
                    "[1..65535]|<name:64 char max>";
              } //ip

            } //container filter

            list vc-label {
              key "ingress-vc-label";
              description
                  "Configure ingress VC label";
              leaf ingress-vc-label {
                type string;
                description
                    "Attribute ingress-vc-label for vc-label";
              } //ingress-vc-label

            } //list vc-label

          } //container ingress

        } //list spoke-sdp

      } //list aarp-interface

      container eth-cfm {
        description
            "Configure CFM parameters";
        container tunnel-fault {
          description
              "Accept/Ignore tunnel fault notification";
          leaf tunnel-fault-id {
            type enumeration {
              enum accept;
              enum ignore;
            }
          } //tunnel-fault-id

        } //container tunnel-fault

      } //container eth-cfm

      container igmp-host-tracking {
        description
            "Configure IGMP host tracking";
        container expiry-time {
          description
              "Configure the time that the system continues to track inactive hosts";
          leaf expiry-time {
            type uint32 {
              range "1..65535";
            }
            description
                "[1..65535] seconds";
          } //expiry-time

        } //container expiry-time

        leaf shutdown {
          type boolean;
          description
              "Administratively enable/disable IGMP host tracking";
        }

      } //container igmp-host-tracking

      uses "conf-svc-ies-if-r13:alu-conf-svc-ies-if-r13";
      uses "conf-svc-ies-ipt-r13:alu-conf-svc-ies-ipt-r13";
      list redundant-interface {
        key "ip-int-name";
        description
            "Create/delete or configure a redundant interface";
        leaf ip-int-name {
          type string {
            length "1..32";
          }
          description
              "[32 chars max] (must start with a letter)";
        } //ip-int-name

        container address {
          description
              "Assigns an IP address/IP subnet format and a remote IP to the interface";
          leaf ip-address-mask {
            type string;
            description
                "ip-address a.b.c.d (no multicast address) 
                 mask [0..32]";
          } //ip-address-mask

          leaf netmask {
            type string;
            description
                "a.b.c.d (network bits all 1 and host bits all 0)";
          } //netmask

          leaf remote-ip {
            type inet:ip-address;
          } //remote-ip

        } //container address

        container delayed-enable {
          status "obsolete";
          leaf seconds {
            type uint32 {
              range "1..65535";
            }
          } //seconds

          leaf init-only {
            type boolean;
          } //init-only

        } //container delayed-enable

        list description {
          key "long-description-string";
          description
              "Description for redundant interface";
          leaf long-description-string {
            type string {
              length "1..160";
            }
          } //long-description-string

        } //list description

        container ip-mtu {
          description
              "Configure the interface IP MTU";
          leaf octets {
            type uint32 {
              range "512..9000";
            }
          } //octets

        } //container ip-mtu

        leaf shutdown {
          type boolean;
          description
              "Administratively enable/disable the interface";
        }

        container hold-time {
          description
              "Configure the hold times (up/down) for the interface";
          list down {
            key "ip";
            description
                "Configure the hold time when the interface is coming up";
            leaf ip {
              type boolean;
            } //ip

            leaf seconds {
              type uint32 {
                range "1..1200";
              }
            } //seconds

            leaf init-only {
              type boolean;
            } //init-only

          } //list down

          list up {
            key "ip";
            description
                "Configure the hold time when the interface is going down";
            leaf ip {
              type boolean;
            } //ip

            leaf seconds {
              type uint32 {
                range "1..1200";
              }
            } //seconds

          } //list up

        } //container hold-time

        list spoke-sdp {
          key "sdp-id-vc-id";
          description
              "Provision a spoke SDP binding";
          leaf sdp-id-vc-id {
            type string;
            description
                "sdp-id - [1..32767] 
                 vc-id - [1..4294967295]";
          } //sdp-id-vc-id

          leaf control-word {
            type boolean;
            description
                "Enable/disable setting the CW bit in the label message";
          }

          container description {
            description
                "Set description for spoke-sdp";
            leaf description-string {
              type string {
                length "1..80";
              }
              description
                  "80 char max";
            } //description-string

          } //container description

          leaf shutdown {
            type boolean;
            description
                "Administratively enable/disable the spoke SDP binding";
          }

          container control-channel-status {
            description
                "Configure control channel status information";
            leaf acknowledgment {
              type boolean;
              description
                  "Enable/disable acknowledgment";
            }

            container refresh-timer {
              description
                  "Configure refresh timer";
              leaf seconds {
                type uint32 {
                  range "10..65535";
                }
              } //seconds

            } //container refresh-timer

            container request-timer {
              description
                  "Configure request-timer for the control channel status";
              leaf request-timer-secs {
                type uint32 {
                  range "10..65535";
                }
              } //request-timer-secs

              leaf retry-timer {
                type uint32 {
                  range "3..60";
                }
              } //retry-timer

              leaf timeout-multiplier {
                type uint32 {
                  range "3..15";
                }
              } //timeout-multiplier

            } //container request-timer

            leaf shutdown {
              type boolean;
              description
                  "Administratively enable/disable the control channel status";
            }

          } //container control-channel-status

          container egress {
            description
                "Spoke SDP egress configuration";
            container filter {
              description
                  "Apply egress filter";
              leaf ip {
                type string;
                description
                    "[1..65535]|<name:64 char max>";
              } //ip

            } //container filter

            list vc-label {
              key "egress-vc-label";
              description
                  "Configure egress VC label";
              leaf egress-vc-label {
                type int32 {
                  range "16..1048575";
                }
              } //egress-vc-label

            } //list vc-label

          } //container egress

          container ingress {
            description
                "Spoke SDP ingress configuration";
            container filter {
              description
                  "Apply ingress filter";
              leaf ip {
                type string;
                description
                    "[1..65535]|<name:64 char max>";
              } //ip

            } //container filter

            list vc-label {
              key "ingress-vc-label";
              description
                  "Configure ingress VC label";
              leaf ingress-vc-label {
                type string;
                description
                    "Attribute ingress-vc-label for vc-label";
              } //ingress-vc-label

            } //list vc-label

          } //container ingress

          container pw-path-id {
            presence
                "Configure PW path identifier information";
            container agi {
              description
                  "Configure Attachment Group Identifier";
              leaf attachment-group-identifier {
                type string {
                }
                description
                    "<0..4294967295>:<0..4294967295>";
              } //attachment-group-identifier

            } //container agi

            container saii-type2 {
              description
                  "Configure Source Attachment Individual Identifier (SAII)";
              leaf global-id-node-id-ac-id {
                type string {
                }
                description
                    "Attribute global-id:node-id:ac-id for saii-type2";
              } //global-id-node-id-ac-id

            } //container saii-type2

            container taii-type2 {
              description
                  "Configure Target Attachment Individual Identifier (TAII)";
              leaf global-id-node-id-ac-id {
                type string {
                }
                description
                    "Attribute global-id:node-id:ac-id for taii-type2";
              } //global-id-node-id-ac-id

            } //container taii-type2

          } //container pw-path-id

        } //list spoke-sdp

      } //list redundant-interface

      uses "conf-svc-ies-subif-r13:alu-conf-svc-ies-subif-r13";
      list video-interface {
        key "ip-int-name";
        description
            "Configure a video interface";
        leaf ip-int-name {
          type string {
            length "1..30";
          }
          description
              "[29 chars max] (must start with a letter)";
        } //ip-int-name

        container accounting-policy {
          description
              "Configure Accounting Policy";
          leaf acct-policy-id {
            type uint32 {
              range "1..99";
            }
          } //acct-policy-id

        } //container accounting-policy

        list address {
          key "ip-address-mask";
          description
              "Configure an IP address to the interface";
          leaf ip-address-mask {
            type inet:ip-prefix;
            description
                "ip-address a.b.c.d 
                 mask [1..32]";
          } //ip-address-mask

        } //list address

        container cpu-protection {
          description
              "Configure a CPU protection policy";
          leaf policy-id {
            type uint32 {
              range "1..255";
            }
          } //policy-id

        } //container cpu-protection

        container description {
          description
              "Description for video interface";
          leaf description-string {
            type string {
              length "1..80";
            }
          } //description-string

        } //container description

        container multicast-service {
          description
              "Configure service ID of the associated multicast service";
          leaf service-id {
            type string;
            description
                "Attribute service-id for multicast-service";
          } //service-id

        } //container multicast-service

        container output-format {
          description
              "Configure the output format";
          leaf udp-rtp-udp {
            type enumeration {
              enum udp;
              enum rtp-udp;
            }
            description
                "keywords";
          } //udp-rtp-udp

        } //container output-format

        container rt-client-src-address {
          description
              "Configure an IP address for the RT client";
          leaf ip-address {
            type inet:ip-address;
          } //ip-address

        } //container rt-client-src-address

        leaf shutdown {
          type boolean;
          description
              "Administratively enable/disable the video interface";
        }

        container adi {
          description
              "Configure Ad-Insertion for the video interface";
          container scte30 {
            description
                "Configure scte30 parameters";
            list ad-server {
              key "ip-address";
              description
                  "Configure ad server address";
              leaf ip-address {
                type inet:ip-address;
              } //ip-address

            } //list ad-server

            container local-address {
              description
                  "Configure local address for scte 30 control and data streams";
              leaf control {
                type inet:ip-address;
              } //control

              leaf data {
                type inet:ip-address;
              } //data

            } //container local-address

          } //container scte30

        } //container adi

        list channel {
          key "mcast-address source";
          description
              "Configure channel";
          leaf mcast-address {
            type inet:ip-address;
            description
                "a.b.c.d - multicast channel address";
          } //mcast-address

          leaf source {
            type inet:ip-address;
            description
                "a.b.c.d - unicast source address";
          } //source

          leaf channel-name {
            type string {
              length "1..32";
            }
            description
                "max 32 chars";
          } //channel-name

          container description {
            description
                "Add/remove description for channel";
            leaf description-string {
              type string {
                length "1..80";
              }
              description
                  "[Max 80 chars]";
            } //description-string

          } //container description

          container scte35-action {
            description
                "Enable/disable forwarding scte 35 cue avails";
            leaf forward-drop {
              type enumeration {
                enum forward;
                enum drop;
              }
              description
                  "keywords";
            } //forward-drop

          } //container scte35-action

          list zone-channel {
            key "mcast-address source";
            description
                "Configure zone-channel";
            leaf mcast-address {
              type inet:ip-address;
            } //mcast-address

            leaf source {
              type inet:ip-address;
            } //source

            leaf adi-channel-name {
              type string {
                length "1..32";
              }
            } //adi-channel-name

          } //list zone-channel

        } //list channel

        container video-sap {
          description
              "Configure group id for the video interface";
          leaf video-group-id {
            type uint32 {
              range "1..4";
            }
          } //video-group-id

          container egress {
            description
                "Configure egress parameters";
            container filter {
              description
                  "Configure an egress filter";
              leaf ip {
                type string;
                description
                    "[1..65535]|<name:64 char max>";
              } //ip

            } //container filter

            container qos {
              description
                  "Configure qos policy";
              leaf policy-id {
                type string;
                description
                    "[1..65535]|<name:64 char max>";
              } //policy-id

            } //container qos

          } //container egress

          container ingress {
            description
                "Configure ingress parameters";
            container filter {
              description
                  "Configure an ingress filter";
              leaf ip {
                type string;
                description
                    "[1..65535]|<name:64 char max>";
              } //ip

            } //container filter

            container qos {
              description
                  "Configure qos policy";
              leaf policy-id {
                type string;
                description
                    "[1..65535]|<name:64 char max>";
              } //policy-id

            } //container qos

          } //container ingress

        } //container video-sap

      } //list video-interface

    } //list ies

  } //grouping alu-conf-svc-ies-r13

} //module  alu-conf-svc-ies-r13
