module alu-conf-router-policy-r13 {
  yang-version "1";

  namespace "urn:alcatel-lucent.com:sros:ns:yang:conf-router-policy-r13";

  prefix "conf-router-policy-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure route policies on SR OS based 
       routers. 
       
       Copyright 2014-2015 Alcatel-Lucent, 2016 Nokia. All rights reserved. 
       Reproduction of this document is authorized on the condition that the 
       foregoing copyright notice is included. 
       
       This alu-conf-router-policy-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-10-10";

  grouping alu-conf-router-policy-r13 {
    container policy-options {
      presence
          "Configure route policies";
      leaf abort {
        type boolean;
        description
            "Discard the changes that have been made to route policies during a session";
      }

      container begin {
        description
            "Switch to edit mode for route policies - use commit to save or abort to 
             discard the changes made in a session";
        leaf exclusive {
          type boolean;
          description
              "keyword";
        } //exclusive

      } //container begin

      leaf commit {
        type boolean;
        description
            "Save the changes made to route policies during a session";
      }

      container exclusive-lock-time {
        description
            "Configure the inactivity timer for the exclusive lock time for policy editing";
        leaf seconds {
          type uint32 {
            range "1..3600";
          }
          description
              "[1..3600] - Idle time before aborting configuration changes";
        } //seconds

      } //container exclusive-lock-time

      list as-path {
        key "name";
        description
            "Create/delete AS Path regular expressions for use in route policy entries";
        leaf name {
          type string {
            length "1..32";
          }
        } //name

        container expression {
          description
              "Create/delete regular expressions for use in route policy entries";
          leaf regular-expression {
            type string;
            description
                "[255 chars max] - regular expression string 
                 null - empty regular expression string";
          } //regular-expression

        } //container expression

      } //list as-path

      list as-path-group {
        key "name";
        description
            "Configure a group of AS Path entries";
        leaf name {
          type string {
            length "1..32";
          }
        } //name

        list entry {
          key "entry-id";
          description
              "Configure an entry in this AS Path group";
          leaf entry-id {
            type uint32 {
              range "1..128";
            }
          } //entry-id

          leaf expression {
            type string;
            description
                "[255 chars max] - regular expression string 
                 null - empty regular expression string";
          } //expression

        } //list entry

      } //list as-path-group

      list community {
        key "name";
        description
            "Create/delete a community list for use in route policy entries";
        leaf name {
          type string {
            length "1..64";
          }
          description
              "Attribute name for community";
        } //name

        container expression {
          description
              "Configure the expression";
          leaf expression {
            type string {
              length "1..900";
            }
            description
                "Attribute expression for expression";
          } //expression

          leaf exact {
            type boolean;
            description
                "keyword";
          } //exact

        } //container expression

        container members {
          description
              "Configure the members";
          leaf-list comm-id {
            type string;
            max-elements 15;
            description
                "Attribute comm-id for members";
          } //comm-id

        } //container members

      } //list community

      list damping {
        key "name";
        description
            "Configure a damping profile for use in route policy entries";
        leaf name {
          type string {
            length "1..32";
          }
        } //name

        container half-life {
          description
              "The time in minutes after which the accumulated figure-of-merit value is 
               reduced by half if the route remains stable.";
          leaf minutes {
            type uint32 {
              range "1..45";
            }
          } //minutes

        } //container half-life

        container max-suppress {
          description
              "The maximum time in minutes that a route can be suppressed no matter how 
               unstable it has been.";
          leaf minutes {
            type uint32 {
              range "1..720";
            }
          } //minutes

        } //container max-suppress

        container reuse {
          description
              "The figure-of-merit value below which a suppressed route can be used again.";
          leaf integer {
            type uint32 {
              range "1..20000";
            }
          } //integer

        } //container reuse

        container suppress {
          description
              "The figure-of-merit value above which a route is suppressed for use or 
               inclusion in route advertisements.";
          leaf integer {
            type uint32 {
              range "1..20000";
            }
          } //integer

        } //container suppress

      } //list damping

      container global-variables {
        presence
            "Configure global policy variables used as a match criterion";
        list name {
          key "name-string";
          description
              "Configure a mapping of a variable name to a value, a number or an address";
          leaf name-string {
            type string {
              length "1..32";
            }
            description
                "[32 chars max] - Must start and end with an at-sign (@)";
          } //name-string

          leaf value {
            type string {
              length "1..32";
            }
          } //value

          leaf number {
            type uint32;
          } //number

          leaf address {
            type string;
            description
                "Attribute ip-address for name";
          } //address

        } //list name

      } //container global-variables

      list policy-statement {
        key "name";
        description
            "Configuring a route policy statement";
        leaf name {
          type string;
          description
              "Attribute name for policy-statement";
        } //name

        container description {
          description
              "Textual description for the policy statement";
          leaf description-string {
            type string {
              length "1..80";
            }
          } //description-string

        } //container description

        container renumber {
          description
              "Renumber an entry";
          leaf from {
            type uint32 {
              range "1..4294967295";
            }
          } //from

          leaf to {
            type uint32 {
              range "1..4294967295";
            }
          } //to

        } //container renumber

        container default-action {
          description
              "Configuring actions for routes that do not match any policy entries";
          leaf default-action-id {
            type enumeration {
              enum accept;
              enum next-entry;
              enum next-policy;
              enum drop;
              enum reject;
            }
          } //default-action-id

          container add-paths-send-limit {
            description
                "Assign a BGP ADD-PATHS send limit to routes matching the entry";
            leaf send-limit {
              type enumeration {
                enum 1;
                enum 2;
                enum 3;
                enum 4;
                enum 5;
                enum 6;
                enum 7;
                enum 8;
                enum 9;
                enum 10;
                enum 11;
                enum 12;
                enum 13;
                enum 14;
                enum 15;
                enum 16;
              }
              description
                  "[1..16]";
            } //send-limit

          } //container add-paths-send-limit

          container admin-tag-policy {
            description
                "Configure an admininistrative tag policy to be used for BGP routes that do not 
                 match any entry";
            leaf name {
              type string;
            } //name

          } //container admin-tag-policy

          container advertise-label {
            description
                "Set the advertise label mode for BGP routes that do not match any entry";
            leaf per-prefix {
              type boolean;
            } //per-prefix

            leaf advertise-label-id {
              type enumeration {
                enum per-prefix;
                enum pop;
              }
            } //advertise-label-id

          } //container advertise-label

          container aigp-metric {
            description
                "Assign a BGP AIGP metric to routes matching the entry";
            leaf metric {
              type string;
              description
                  "Attribute metric for aigp-metric";
            } //metric

            leaf igp {
              type boolean;
            } //igp

            leaf add {
              type boolean;
            } //add

          } //container aigp-metric

          container as-path {
            description
                "Assign a BGP AS Path list to routes that do not match any entry";
            leaf add-replace {
              type enumeration {
                enum add;
                enum replace;
              }
              description
                  "keywords";
            } //add-replace

            leaf name {
              type string {
                length "1..32";
              }
            } //name

          } //container as-path

          container as-path-prepend {
            description
                "Prepending a BGP AS number to the AS Path attribute of routes that do not 
                 match any entry";
            leaf as-path {
              type string;
              description
                  "Attribute as-path for as-path-prepend";
            } //as-path

            leaf most-recent {
              type boolean;
            } //most-recent

            leaf repeat {
              type string;
              description
                  "Attribute repeat for as-path-prepend";
            } //repeat

          } //container as-path-prepend

          leaf bgp-leak {
            type boolean;
            description
                "Enable/disable leaking for BGP routes that do not match any entry";
          }

          container community {
            description
                "Apply a BGP community list to routes that do not match any entry";
            leaf-list add {
              type string;
              max-elements 28;
              description
                  "Attribute name for community";
            } //add

            leaf-list remove {
              type string;
              max-elements 28;
              description
                  "name";
            } //remove

            leaf-list replace {
              type string;
              max-elements 28;
              description
                  "name";
            } //replace

          } //container community

          leaf create-udp-tunnel {
            type boolean;
            description
                "Enable/disable creation of UDP tunnels for BGP routes that do not match any 
                 entry";
          }

          container damping {
            description
                "Configure a damping profile to be used for routes that do not match any entry";
            leaf name {
              type string {
                length "1..32";
              }
            } //name

            leaf none {
              type boolean;
            } //none

          } //container damping

          container dest-class {
            description
                "Default dest-class for this policy-statement";
            leaf dest-class-id {
              type uint32 {
                range "1..255";
              }
            } //dest-class-id

          } //container dest-class

          leaf install-backup-path {
            type boolean;
            description
                "Set the backup-path-desired flag for BGP routes that do not match any entry";
          }

          container local-preference {
            description
                "Assign a BGP Local Preference to routes that do not match any entry";
            leaf local-pref {
              type string;
              description
                  "Attribute local-pref for local-preference";
            } //local-pref

          } //container local-preference

          container metric {
            description
                "Assign a metric to routes that do not match any entry";
            leaf add-subtract {
              type enumeration {
                enum add;
                enum subtract;
              }
              description
                  "keywords";
            } //add-subtract

            leaf metric {
              type string;
              description
                  "Attribute metric for metric";
            } //metric

            leaf set {
              type boolean;
              description
                  "keyword";
            } //set

            leaf igp-metric {
              type string;
              description
                  "Attribute igp|metric for metric";
            } //igp-metric

          } //container metric

          container multicast-redirection {
            description
                "Configure the interface where to redirect IGMP multicast traffic to";
            leaf fwd-service {
              type string;
              description
                  "Attribute service-id for multicast-redirection";
            } //fwd-service

            leaf ip-int-name {
              type string {
                length "1..32";
              }
            } //ip-int-name

          } //container multicast-redirection

          container next-hop {
            description
                "Assign a next hop IP address to routes that do not match any entry";
            leaf ip-address {
              type string;
              description
                  "Attribute ip-address for next-hop";
            } //ip-address

          } //container next-hop

          leaf next-hop-self {
            type boolean;
            description
                "Advertising a next hop IP address belonging to this router to routes that do 
                 not match any entry";
          }

          container origin {
            description
                "Set the BGP origin assigned to routes exported into BGP that do not match any 
                 entry";
            leaf param-name {
              type string;
              description
                  "[32 chars max] - Must start and end with an at-sign (@)";
            } //param-name

            leaf igp-egp-incomplete {
              type enumeration {
                enum igp;
                enum egp;
                enum incomplete;
              }
              description
                  "keywords";
            } //igp-egp-incomplete

          } //container origin

          container origin-validation-state {
            description
                "Configure origin validation state to routes that do not match any entry";
            leaf param-name {
              type string;
              description
                  "[32 chars max] - Must start and end with an at-sign (@)";
            } //param-name

            leaf state {
              type enumeration {
                enum valid;
                enum notFound;
                enum invalid;
              }
            } //state

          } //container origin-validation-state

          container preference {
            description
                "Assign a route preference to routes that do not match any entry";
            leaf preference {
              type string;
              description
                  "Attribute preference for preference";
            } //preference

          } //container preference

          leaf resolve-static {
            type boolean;
            description
                "Enable/disable resolved next-hop of static route for BGP routes that do not 
                 match any entry";
          }

          container source-class {
            description
                "Default source-class for this policy-statement";
            leaf source-class-id {
              type uint32 {
                range "1..255";
              }
            } //source-class-id

          } //container source-class

          leaf sticky-ecmp {
            type boolean;
            description
                "Set the sticky-ecmp flag for BGP ECMP routes that do not match any entry";
          }

          container tag {
            description
                "Assign an OSPF RIP or ISIS tag to routes that do not match any entry";
            leaf tag {
              type string;
              description
                  "Attribute tag for tag";
            } //tag

          } //container tag

          container type {
            description
                "Assign an OSPF type metric to routes that do not match any entry";
            leaf param-name {
              type string;
              description
                  "[32 chars max] - Must start and end with an at-sign (@)";
            } //param-name

            leaf type {
              type enumeration {
                enum 1;
                enum 2;
              }
            } //type

          } //container type

        } //container default-action

        list entry {
          key "entry-id";
          description
              "Configure a route policy entry within the policy statement";
          leaf entry-id {
            type uint32 {
              range "1..4294967295";
            }
          } //entry-id

          container description {
            description
                "Textual description for the policy statement entry";
            leaf description-string {
              type string {
                length "1..80";
              }
            } //description-string

          } //container description

          container action {
            description
                "Configure actions to take for routes matching a policy entry";
            leaf action-id {
              type enumeration {
                enum accept;
                enum next-entry;
                enum next-policy;
                enum drop;
                enum reject;
              }
            } //action-id

            container add-paths-send-limit {
              description
                  "Assign a BGP ADD-PATHS send limit to routes matching the entry";
              leaf send-limit {
                type enumeration {
                  enum 1;
                  enum 2;
                  enum 3;
                  enum 4;
                  enum 5;
                  enum 6;
                  enum 7;
                  enum 8;
                  enum 9;
                  enum 10;
                  enum 11;
                  enum 12;
                  enum 13;
                  enum 14;
                  enum 15;
                  enum 16;
                }
                description
                    "[1..16]";
              } //send-limit

            } //container add-paths-send-limit

            container admin-tag-policy {
              description
                  "Configure an admininistrative tag policy to be used for BGP routes matching 
                   the entry";
              leaf name {
                type string;
              } //name

            } //container admin-tag-policy

            container advertise-label {
              description
                  "Set the advertise label mode for BGP routes matching the entry";
              leaf per-prefix {
                type boolean;
              } //per-prefix

              leaf advertise-label-id {
                type enumeration {
                  enum per-prefix;
                  enum pop;
                }
              } //advertise-label-id

            } //container advertise-label

            container aigp-metric {
              description
                  "Assign a BGP AIGP metric to routes matching the entry";
              leaf metric {
                type string;
                description
                    "Attribute metric for aigp-metric";
              } //metric

              leaf igp {
                type boolean;
              } //igp

              leaf add {
                type boolean;
              } //add

            } //container aigp-metric

            container as-path {
              description
                  "Assign a BGP AS Path list to routes matching the entry";
              leaf add-replace {
                type enumeration {
                  enum add;
                  enum replace;
                }
                description
                    "keywords";
              } //add-replace

              leaf name {
                type string {
                  length "1..32";
                }
              } //name

            } //container as-path

            container as-path-prepend {
              description
                  "Prepending a BGP AS number to the AS Path attribute of routes that match the 
                   entry";
              leaf as-path {
                type string;
                description
                    "Attribute as-path for as-path-prepend";
              } //as-path

              leaf most-recent {
                type boolean;
              } //most-recent

              leaf repeat {
                type string;
                description
                    "Attribute repeat for as-path-prepend";
              } //repeat

            } //container as-path-prepend

            leaf bgp-leak {
              type boolean;
              description
                  "Enable/disable leaking for BGP routes matching the entry";
            }

            container community {
              description
                  "Apply a BGP community list to routes matching the entry";
              leaf-list add {
                type string;
                max-elements 28;
                description
                    "Attribute name for community";
              } //add

              leaf-list remove {
                type string;
                max-elements 28;
                description
                    "name";
              } //remove

              leaf-list replace {
                type string;
                max-elements 28;
                description
                    "name";
              } //replace

            } //container community

            leaf create-udp-tunnel {
              type boolean;
              description
                  "Enable/disable creation of UDP tunnels for BGP routes matching the entry";
            }

            container damping {
              description
                  "Configure a damping profile to be used for routes matching the entry";
              leaf name {
                type string {
                  length "1..32";
                }
              } //name

              leaf none {
                type boolean;
              } //none

            } //container damping

            container dest-class {
              description
                  "Dest-class for this policy-statement";
              leaf dest-class-id {
                type uint32 {
                  range "1..255";
                }
              } //dest-class-id

            } //container dest-class

            container fc {
              description
                  "Configure forwarding-class to routes matching the entry";
              leaf fc {
                type enumeration {
                  enum be;
                  enum l2;
                  enum af;
                  enum l1;
                  enum h2;
                  enum ef;
                  enum h1;
                  enum nc;
                }
                description
                    "be|l2|af|l1|h2|ef|h1|nc";
              } //fc

              leaf priority {
                type enumeration {
                  enum low;
                  enum high;
                }
                description
                    "low|high";
              } //priority

            } //container fc

            leaf install-backup-path {
              type boolean;
              description
                  "Set the backup-path-desired flag for BGP routes matching the entry";
            }

            container local-preference {
              description
                  "Assign a BGP Local Preference to routes matching the entry";
              leaf local-pref {
                type string;
                description
                    "Attribute local-pref for local-preference";
              } //local-pref

            } //container local-preference

            container metric {
              description
                  "Assign a metric to routes matching the entry";
              leaf add-subtract {
                type enumeration {
                  enum add;
                  enum subtract;
                }
                description
                    "keywords";
              } //add-subtract

              leaf set {
                type boolean;
                description
                    "keyword";
              } //set

              leaf metric {
                type string;
                description
                    "Attribute metric for metric";
              } //metric

              leaf igp-metric {
                type string;
                description
                    "Attribute igp|metric for metric";
              } //igp-metric

            } //container metric

            container multicast-redirection {
              description
                  "Configure the interface where to redirect IGMP multicast traffic to";
              leaf fwd-service {
                type string;
                description
                    "Attribute service-id for multicast-redirection";
              } //fwd-service

              leaf ip-int-name {
                type string {
                  length "1..32";
                }
              } //ip-int-name

            } //container multicast-redirection

            container next-hop {
              description
                  "Assign a next hop IP address to routes matching the entry";
              leaf ip-address {
                type string;
                description
                    "Attribute ip-address for next-hop";
              } //ip-address

            } //container next-hop

            leaf next-hop-self {
              type boolean;
              description
                  "Advertising a next hop IP address belonging to this router to routes matching 
                   the entry";
            }

            container origin {
              description
                  "Set the BGP origin assigned to routes exported into BGP that match the entry";
              leaf param-name {
                type string;
                description
                    "[32 chars max] - Must start and end with an at-sign (@)";
              } //param-name

              leaf igp-egp-incomplete {
                type enumeration {
                  enum igp;
                  enum egp;
                  enum incomplete;
                }
                description
                    "keywords";
              } //igp-egp-incomplete

            } //container origin

            container origin-validation-state {
              description
                  "Configure origin validation state to routes matching the entry";
              leaf param-name {
                type string;
                description
                    "[32 chars max] - Must start and end with an at-sign (@)";
              } //param-name

              leaf state {
                type enumeration {
                  enum valid;
                  enum notFound;
                  enum invalid;
                }
              } //state

            } //container origin-validation-state

            container preference {
              description
                  "Assign a route preference to routes matching the entry";
              leaf preference {
                type string;
                description
                    "Attribute preference for preference";
              } //preference

            } //container preference

            leaf resolve-static {
              type boolean;
              description
                  "Enable/disable resolved next-hop of static route for BGP routes matching the 
                   entry";
            }

            container source-class {
              description
                  "Source-class for this policy-statement";
              leaf source-class-id {
                type uint32 {
                  range "1..255";
                }
              } //source-class-id

            } //container source-class

            leaf sticky-ecmp {
              type boolean;
              description
                  "Set the sticky-ecmp flag for BGP ECMP routes matching the entry";
            }

            container tag {
              description
                  "Assign an OSPF RIP ISIS or BGP tag to routes matching the entry";
              leaf tag {
                type string;
                description
                    "Attribute tag for tag";
              } //tag

            } //container tag

            container type {
              description
                  "Assign an OSPF type metric to routes matching the entry";
              leaf param-name {
                type string;
                description
                    "[32 chars max] - Must start and end with an at-sign (@)";
              } //param-name

              leaf type {
                type enumeration {
                  enum 1;
                  enum 2;
                }
              } //type

            } //container type

          } //container action

          container conditional-expression {
            presence
                "Configure conditional expressions to decide whether the entry should be 
                 evaluated";
            container route-exists {
              description
                  "Configure a conditional expression to test route existence";
              leaf expression {
                type string {
                  length "1..50";
                }
                description
                    "Attribute expression for route-exists";
              } //expression

            } //container route-exists

          } //container conditional-expression

          container from {
            presence
                "Configure policy match criteria based on source of routes or protocol from 
                 which it is received";
            container area {
              description
                  "Configure an OSPF area as a match criterion for the entry";
              leaf area-id {
                type string;
                description
                    "<ip-address> | [0..4294967295]";
              } //area-id

            } //container area

            container as-path {
              description
                  "Configures an AS Path regular expression statement as a match criterion for 
                   the entry";
              leaf name {
                type string {
                  length "1..32";
                }
              } //name

            } //container as-path

            container as-path-group {
              description
                  "Configures an AS Path Group as a match criterion for the entry";
              leaf name {
                type string {
                  length "1..32";
                }
              } //name

            } //container as-path-group

            container as-path-length {
              description
                  "Configures an AS Path length as a match criterion for the entry";
              leaf length {
                type string;
                description
                    "Attribute length for as-path-length";
              } //length

              leaf as-path-length-id {
                type enumeration {
                  enum equal;
                  enum or-higher;
                  enum or-lower;
                }
              } //as-path-length-id

              leaf unique {
                type boolean;
              } //unique

            } //container as-path-length

            container cluster-id {
              description
                  "Configures a cluster id as a match criterion for the entry";
              leaf-list ip-address-mask {
                type inet:ip-prefix;
                max-elements 5;
                description
                    "ip-address - a.b.c.d 
                     mask - [1..32]";
              } //ip-address-mask

              leaf none {
                type boolean;
              } //none

            } //container cluster-id

            container community {
              description
                  "Configure a community list as a match criterion for the entry";
              leaf comm-name {
                type string;
                description
                    "Attribute comm-name for community";
              } //comm-name

              leaf expression {
                type string {
                  length "1..900";
                }
                description
                    "[900 chars max] - <expression> is one of the following: 
                     <expression> {AND|OR} <expression> 
                     [NOT] ( <expression> ) 
                     [NOT] \"[\"<comm-name>\"]\"";
              } //expression

            } //container community

            container community-count {
              description
                  "Configures a number of communities as a match criterion for the entry";
              leaf count {
                type string;
                description
                    "Attribute count for community-count";
              } //count

              leaf community-count-id {
                type enumeration {
                  enum equal;
                  enum or-higher;
                  enum or-lower;
                }
              } //community-count-id

              leaf community-count-id-2 {
                type enumeration {
                  enum standard;
                  enum extended;
                }
              } //community-count-id-2

              leaf community-count-id-3 {
                type enumeration {
                  enum standard;
                  enum extended;
                  enum large;
                }
              } //community-count-id-3

            } //container community-count

            container evpn-type {
              description
                  "Configure a EVPN type as match criterion for the entry";
              leaf type {
                type enumeration {
                  enum 1;
                  enum 2;
                  enum 3;
                  enum 4;
                  enum 5;
                }
              } //type

            } //container evpn-type

            leaf external {
              type boolean;
              description
                  "Configure external ISIS route matching criterion for the entry";
            }

            container family {
              description
                  "Configure the address families that this condition would match against";
              leaf ipv4 {
                type boolean;
                description
                    "keyword - provision support of the specific family";
              } //ipv4

              leaf ipv6 {
                type boolean;
                description
                    "keyword - provision support of the specific family";
              } //ipv6

              leaf mcast-ipv4 {
                type boolean;
                description
                    "keyword - provision support of the specific family";
              } //mcast-ipv4

              leaf mcast-ipv6 {
                type boolean;
                description
                    "keyword - provision support of the specific family";
              } //mcast-ipv6

              leaf vpn-ipv4 {
                type boolean;
                description
                    "keyword - provision support of the specific family";
              } //vpn-ipv4

              leaf vpn-ipv6 {
                type boolean;
                description
                    "keyword - provision support of the specific family";
              } //vpn-ipv6

              leaf l2-vpn {
                type boolean;
                description
                    "keyword - provision support of the specific family";
              } //l2-vpn

              leaf mvpn-ipv4 {
                type boolean;
                description
                    "keyword - provision support of the specific family";
              } //mvpn-ipv4

              leaf flow-ipv4 {
                type boolean;
                description
                    "keyword - provision support of the specific family";
              } //flow-ipv4

              leaf ms-pw {
                type boolean;
                description
                    "keyword - provision support of the specific family";
              } //ms-pw

              leaf mdt-safi {
                type boolean;
                description
                    "keyword - provision support of the specific family";
              } //mdt-safi

              leaf route-target {
                type boolean;
                description
                    "keyword - provision support of the specific family";
              } //route-target

              leaf mcast-vpn-ipv4 {
                type boolean;
                description
                    "keyword - provision support of the specific family";
              } //mcast-vpn-ipv4

              leaf mvpn-ipv6 {
                type boolean;
                description
                    "keyword - provision support of the specific family";
              } //mvpn-ipv6

              leaf flow-ipv6 {
                type boolean;
                description
                    "keyword - provision support of the specific family";
              } //flow-ipv6

              leaf evpn {
                type boolean;
                description
                    "keyword - provision support of the specific family";
              } //evpn

              leaf label-ipv4 {
                type boolean;
                description
                    "keyword - provision support of the specific family";
              } //label-ipv4

              leaf label-ipv6 {
                type boolean;
                description
                    "keyword - provision support of the specific family";
              } //label-ipv6

              leaf bgp-ls {
                type boolean;
                description
                    "keyword - provision support of the specific family";
              } //bgp-ls

              leaf mcast-vpn-ipv6 {
                type boolean;
                description
                    "keyword - provision support of the specific family";
              } //mcast-vpn-ipv6

              leaf sr-policy-ipv4 {
                type boolean;
                description
                    "keyword - provision support of the specific family";
              } //sr-policy-ipv4

            } //container family

            container flow-spec-dest {
              description
                  "Configure a prefix list of flow-spec destination addresses as a match 
                   criterion for the entry";
              leaf prefix-list-name {
                type string;
              } //prefix-list-name

            } //container flow-spec-dest

            container flow-spec-source {
              description
                  "Configure a prefix list of flow-spec source addresses as a match criterion for 
                   the entry";
              leaf prefix-list-name {
                type string;
              } //prefix-list-name

            } //container flow-spec-source

            container group-address {
              description
                  "Configure a prefix list of multicast group addresses as a match criterion for 
                   the entry";
              leaf prefix-list-name {
                type string {
                  length "1..32";
                }
              } //prefix-list-name

            } //container group-address

            container host-ip {
              description
                  "Configure a prefix list of IGMP host ip addresses as a match criterion for 
                   this entry";
              leaf prefix-list-name {
                type string {
                  length "1..32";
                }
              } //prefix-list-name

            } //container host-ip

            container interface {
              description
                  "Configure the name of the interface as a match criterion for this entry";
              leaf interface-name {
                type string {
                  length "1..32";
                }
              } //interface-name

            } //container interface

            container level {
              description
                  "Configure ISIS route level as a match criterion for the entry";
              leaf t1-2 {
                type enumeration {
                  enum 1;
                  enum 2;
                }
                description
                    "ISIS route levels";
              } //t1-2

            } //container level

            container local-preference {
              description
                  "Configure a local preference as match criterion for the entry";
              leaf preference {
                type string;
                description
                    "Attribute preference for local-preference";
              } //preference

              leaf local-preference-id {
                type enumeration {
                  enum equal;
                  enum or-higher;
                  enum or-lower;
                }
              } //local-preference-id

            } //container local-preference

            container metric {
              description
                  "Configure a BGP MED metric as match criterion for the entry";
              leaf metric {
                type string;
                description
                    "Attribute metric for metric";
              } //metric

              leaf metric-id {
                type enumeration {
                  enum equal;
                  enum or-higher;
                  enum or-lower;
                }
              } //metric-id

            } //container metric

            container mvpn-type {
              description
                  "Configure a MVPN type as match criterion for the entry";
              leaf type {
                type enumeration {
                  enum 1;
                  enum 2;
                  enum 3;
                  enum 4;
                  enum 5;
                  enum 6;
                  enum 7;
                }
              } //type

            } //container mvpn-type

            container neighbor {
              description
                  "Configure a neighbor or prefix list as match criterion for the entry";
              leaf ip-address {
                type string;
                description
                    "Attribute ip-address for neighbor";
              } //ip-address

              leaf prefix-list {
                type string {
                  length "1..32";
                }
              } //prefix-list

            } //container neighbor

            container next-hop {
              description
                  "Configures a next-hop as a match criterion for the entry";
              leaf ip-address {
                type string;
                description
                    "Attribute ip-address for next-hop";
              } //ip-address

              leaf prefix-list {
                type string {
                  length "1..32";
                }
              } //prefix-list

            } //container next-hop

            container origin {
              description
                  "Configure an origin attribute as a match criterion for the entry";
              leaf origin {
                type enumeration {
                  enum igp;
                  enum egp;
                  enum incomplete;
                  enum any;
                  enum aaa;
                  enum dynamic;
                  enum static;
                  enum bonding;
                }
              } //origin

              leaf ludb {
                type boolean;
                status "obsolete";
              } //ludb

              leaf dhcp {
                type boolean;
                status "obsolete";
              } //dhcp

              leaf origin-1 {
                type enumeration {
                  enum igp;
                  enum egp;
                  enum incomplete;
                  enum any;
                  enum aaa;
                  enum dynamic;
                  enum static;
                }
              } //origin-1

            } //container origin

            container origin-validation-state {
              description
                  "Configure origin validation state as a match criterion for the entry";
              leaf state {
                type enumeration {
                  enum valid;
                  enum notFound;
                  enum invalid;
                }
              } //state

            } //container origin-validation-state

            container path-type {
              description
                  "Configure a path type as a match criterion for the entry";
              leaf path-type-id {
                type enumeration {
                  enum ibgp;
                  enum ebgp;
                }
              } //path-type-id

            } //container path-type

            container policy {
              description
                  "Configures a policy statement as a match criterion for the entry";
              leaf policy-name {
                type string;
                description
                    "Attribute policy-name for policy";
              } //policy-name

              leaf plcy-or-long-expr {
                type string {
                  length "1..255";
                }
                description
                    "Attribute plcy-or-long-expr for policy";
              } //plcy-or-long-expr

            } //container policy

            container prefix-list {
              description
                  "Configure a prefix list as a match criterion for the entry";
              leaf-list name {
                type string {
                  length "1..32";
                }
                max-elements 5;
              } //name

              leaf-list name-1 {
                type string {
                  length "1..32";
                }
                max-elements 28;
              } //name-1

            } //container prefix-list

            container protocol {
              description
                  "Configure a routing protocol as a match criterion for the entry";
              leaf protocol {
                type enumeration {
                  enum direct;
                  enum static;
                  enum isis;
                  enum ospf;
                  enum rip;
                  enum aggregate;
                  enum bgp-vpn;
                  enum igmp;
                  enum pim;
                  enum ospf3;
                  enum ldp;
                  enum sub-mgmt;
                  enum mld;
                  enum managed;
                  enum vpn-leak;
                  enum tms;
                  enum nat;
                  enum periodic;
                  enum ipsec;
                  enum dhcpv6-pd;
                  enum dhcpv6-pd-excl;
                  enum dhcpv6-na;
                  enum dhcpv6-ta;
                  enum ripng;
                  enum direct-interface;
                  enum arp-nd;
                  enum rib-api;
                }
                description
                    "Attribute protocol for protocol";
              } //protocol

              leaf instance {
                type string;
                description
                    "Attribute instance for protocol";
              } //instance

              leaf all {
                type boolean;
                description
                    "Attribute all for protocol";
              } //all

              leaf bgp {
                type boolean;
              } //bgp

              leaf bgp-label {
                type boolean;
              } //bgp-label

            } //container protocol

            container source-address {
              description
                  "Configure a multicast data source address or prefix list as a match criterion 
                   for this entry";
              leaf ip-address {
                type string;
                description
                    "Attribute ip-address for source-address";
              } //ip-address

              leaf prefix-list {
                type string {
                  length "1..32";
                }
              } //prefix-list

            } //container source-address

            container state {
              description
                  "Configure a state as a match criterion for the entry";
              leaf state {
                type enumeration {
                  enum srrp-master;
                  enum srrp-non-master;
                  enum ipsec-master-with-peer;
                  enum ipsec-non-master;
                  enum ipsec-master-without-peer;
                }
              } //state

            } //container state

            container tag {
              description
                  "Configure a route tag as a match criterion for the entry";
              leaf tag {
                type string;
                description
                    "accepts in decimal or hex 
                     [0x1..0xFFFFFFFF]H (for OSPF and ISIS) 
                     [0x1..0xFFFF]H (for RIP) 
                     [0x1..0xFF]H (for BGP)";
              } //tag

              leaf no-tag {
                type boolean;
              } //no-tag

            } //container tag

            container type {
              description
                  "Configure an OSPF type metric as a match criterion for the entry";
              leaf type {
                type enumeration {
                  enum 1;
                  enum 2;
                }
              } //type

            } //container type

            container policy-variables {
              presence
                  "Configure policy variables for the policy statement used as a match criterion 
                   for this entry";
              list name {
                key "name-string";
                description
                    "Configure a mapping of a variable name to a value, a number or an address";
                leaf name-string {
                  type string {
                    length "1..32";
                  }
                  description
                      "[32 chars max] - Must start and end with an at-sign (@)";
                } //name-string

                leaf value {
                  type string {
                    length "1..32";
                  }
                } //value

                leaf number {
                  type uint32;
                } //number

                leaf address {
                  type string;
                  description
                      "Attribute ip-address for name";
                } //address

              } //list name

            } //container policy-variables

          } //container from

          container to {
            presence
                "Configure policy match criteria based on destination of routes or protocol 
                 into which it is advertised";
            container level {
              description
                  "Configure ISIS route level as a match criterion for the entry";
              leaf t1-2 {
                type enumeration {
                  enum 1;
                  enum 2;
                }
                description
                    "ISIS route level";
              } //t1-2

            } //container level

            container neighbor {
              description
                  "Configure a neighbor or prefix list as match criterion for the entry";
              leaf ip-address {
                type string;
                description
                    "Attribute ip-address for neighbor";
              } //ip-address

              leaf prefix-list {
                type string {
                  length "1..32";
                }
              } //prefix-list

            } //container neighbor

            container prefix-list {
              description
                  "Configure a prefix list as a match criterion for the entry";
              leaf-list name {
                type string {
                  length "1..32";
                }
                max-elements 5;
              } //name

              leaf-list name-1 {
                type string {
                  length "1..32";
                }
                max-elements 28;
              } //name-1

            } //container prefix-list

            container protocol {
              description
                  "Configure a routing protocol as a match criterion for the entry";
              leaf protocol {
                type enumeration {
                  enum isis;
                  enum ospf;
                  enum rip;
                  enum bgp-vpn;
                  enum ospf3;
                  enum vpn-leak;
                  enum ldp;
                  enum ripng;
                }
                description
                    "Attribute protocol for protocol";
              } //protocol

              leaf instance {
                type string;
                description
                    "Attribute instance for protocol";
              } //instance

              leaf all {
                type boolean;
                description
                    "keyword [only used with isis and ospf]";
              } //all

              leaf bgp {
                type boolean;
              } //bgp

              leaf bgp-label {
                type boolean;
              } //bgp-label

            } //container protocol

          } //container to

        } //list entry

      } //list policy-statement

      list prefix-list {
        key "name";
        description
            "Configure a prefix list for use in route policy entries";
        leaf name {
          type string {
            length "1..32";
          }
        } //name

        list prefix {
          key "ip-prefix-prefix-length";
          description
              "Create/delete a prefix entry in the prefix list";
          leaf ip-prefix-prefix-length {
            type string;
            description
                "Attribute ip-prefix/prefix-length for prefix";
          } //ip-prefix-prefix-length

          leaf exact-longer-through-prefix-length-range {
            type enumeration {
              enum exact;
              enum longer;
            }
            description
                "keywords";
          } //exact-longer-through-prefix-length-range

          leaf through {
            type uint16 {
              range "0..128";
            }
            description
                "Attribute length for prefix";
          } //through

          leaf prefix-length-range {
            type string {
              length "1..7";
            }
            description
                "Attribute length1-length2 for prefix";
          } //prefix-length-range

        } //list prefix

      } //list prefix-list

    } //container policy-options

  } //grouping alu-conf-router-policy-r13

} //module  alu-conf-router-policy-r13
