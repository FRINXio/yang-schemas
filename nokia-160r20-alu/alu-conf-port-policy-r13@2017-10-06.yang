module alu-conf-port-policy-r13 {
  yang-version "1";

  namespace "urn:alcatel-lucent.com:sros:ns:yang:conf-port-policy-r13";

  prefix "conf-port-policy-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure port policies on SR OS based 
       routers. 
       
       Copyright 2014-2015 Alcatel-Lucent, 2016 Nokia. All rights reserved. 
       Reproduction of this document is authorized on the condition that the 
       foregoing copyright notice is included. 
       
       This alu-conf-port-policy-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-10-06";

  grouping alu-conf-port-policy-r13 {
    list port-policy {
      key "policy-name";
      description
          "Configure port policies";
      leaf policy-name {
        type string {
          length "1..32";
        }
      } //policy-name

      container description {
        description
            "Configure the description";
        leaf description-string {
          type string {
            length "1..80";
          }
        } //description-string

      } //container description

      container egress-scheduler-policy {
        description
            "Configure the egress scheduler policy";
        leaf port-sched-plcy {
          type string {
            length "1..32";
          }
        } //port-sched-plcy

      } //container egress-scheduler-policy

    } //list port-policy

  } //grouping alu-conf-port-policy-r13

} //module  alu-conf-port-policy-r13
