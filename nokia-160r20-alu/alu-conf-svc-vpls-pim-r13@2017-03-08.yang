module alu-conf-svc-vpls-pim-r13 {
  yang-version "1";

  namespace "urn:alcatel-lucent.com:sros:ns:yang:conf-svc-vpls-pim-r13";

  prefix "conf-svc-vpls-pim-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure PIM snooping on SR OS based 
       routers. 
       
       Copyright 2014-2015 Alcatel-Lucent, 2016 Nokia. All rights reserved. 
       Reproduction of this document is authorized on the condition that the 
       foregoing copyright notice is included. 
       
       This alu-conf-svc-vpls-pim-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-03-08";

  grouping alu-conf-svc-vpls-pim-r13 {
    container pim-snooping {
      presence
          "Configure PIM snooping";
      container group-policy {
        description
            "Enable/Disable PIM snooping group policy";
        leaf-list grp-policy-name {
          type string {
            length "1..32";
          }
          max-elements 5;
          description
              "[max 32 chars] - maximum 5 policies";
        } //grp-policy-name

      } //container group-policy

      container hold-time {
        description
            "Configure PIM snooping hold time";
        leaf seconds {
          type uint32 {
            range "0..300";
          }
        } //seconds

      } //container hold-time

      leaf ipv4-multicast-disable {
        type boolean;
        description
            "Administratively disable/enable PIM operation for IPv4";
      }

      leaf ipv6-multicast-disable {
        type boolean;
        description
            "Administratively disable/enable PIM operation for IPv6";
      }

      container mode {
        description
            "Administratively enable/disable PIM Snooping mode";
        leaf mode {
          type enumeration {
            enum snoop;
            enum proxy;
          }
        } //mode

      } //container mode

      leaf shutdown {
        type boolean;
        description
            "Administratively enable or disable PIM snooping";
      }

    } //container pim-snooping

  } //grouping alu-conf-svc-vpls-pim-r13

} //module  alu-conf-svc-vpls-pim-r13
