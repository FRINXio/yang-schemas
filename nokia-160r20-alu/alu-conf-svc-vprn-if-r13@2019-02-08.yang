module alu-conf-svc-vprn-if-r13 {
  yang-version "1";

  namespace "urn:alcatel-lucent.com:sros:ns:yang:conf-svc-vprn-if-r13";

  prefix "conf-svc-vprn-if-r13";

  import alu-types {
    prefix "alu";
  }
  import ietf-inet-types {
    prefix "inet";
  }
  import ietf-yang-types {
    prefix "yang";
  }

  alu:alu-major-release "rel16";

  organization "Alcatel-Lucent";

  contact
      "Alcatel-Lucent SR OS Support 
       Web: <http://www.alcatel-lucent.com>";

  description
      "Alcatel-Lucent YANG Data model to configure IP interfaces for VPRN services on 
       SR OS based routers. 
       
       Copyright 2014-2015 Alcatel-Lucent, 2016 Nokia. All rights reserved. 
       Reproduction of this document is authorized on the condition that the 
       foregoing copyright notice is included. 
       
       This alu-conf-svc-vprn-if-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-02-08";

  grouping alu-conf-svc-vprn-if-r13 {
    list interface {
      key "ip-int-name";
      description
          "Configure IP interfaces for VPRN services";
      leaf ip-int-name {
        type string {
          length "1..32";
        }
        description
            "[32 chars max] (must start with a letter)";
      } //ip-int-name

      leaf tunnel {
        type boolean;
      } //tunnel

      list address {
        key "ip-address-mask netmask broadcast";
        description
            "Assigns an IP address/IP subnet/broadcast address format to the interface";
        leaf ip-address-mask {
          type string;
          description
              "ip-address a.b.c.d (no multicast/broadcast address) 
               mask [0..32]";
        } //ip-address-mask

        leaf netmask {
          type string;
          description
              "a.b.c.d (network bits all 1 and host bits all 0)";
        } //netmask

        leaf broadcast {
          type enumeration {
            enum all-ones;
            enum host-ones;
          }
          description
              "keywords - specify broadcast format";
        } //broadcast

        leaf track-srrp {
          type uint32 {
            range "1..4294967295";
          }
        } //track-srrp

      } //list address

      leaf allow-directed-broadcasts {
        type boolean;
        description
            "Enable/disable forwarding of directed broadcasts on the interface";
      }

      leaf arp-learn-unsolicited {
        type boolean;
        description
            "Configure ARP learn unsolicited";
      }

      container arp-limit {
        description
            "Configures the maximum amount of IPv4 ARP entries";
        leaf limit {
          type int32 {
            range "0..524288";
          }
          description
              "[0..524288] entries - default = disabled";
        } //limit

        leaf log-only {
          type boolean;
        } //log-only

        leaf threshold {
          type uint32 {
            range "1..100";
          }
        } //threshold

      } //container arp-limit

      leaf arp-populate {
        type boolean;
        description
            "Configures the ARP populate option";
      }

      leaf arp-populate-host-route {
        type boolean;
        description
            "Configure ARP populate host route";
      }

      leaf arp-proactive-refresh {
        type boolean;
        description
            "Configure ARP proactive refresh";
      }

      container arp-retry-timer {
        description
            "Configures ARP retry interval on the interface";
        leaf t100s-of-milliseconds {
          type uint32 {
            range "1..300";
          }
          default 50;
          description
              "[1..300] Default: 50";
        } //t100s-of-milliseconds

        leaf t0 {
          type boolean;
          status "obsolete";
        } //t0

      } //container arp-retry-timer

      container arp-route-tag {
        description
            "Configure ARP route tag";
        leaf arp-route-tag-string {
          type string;
        } //arp-route-tag-string

      } //container arp-route-tag

      list arp-timeout {
        key "seconds";
        description
            "Configures timeout for an ARP entry learned on the interface";
        leaf seconds {
          type uint32 {
            range "0..65535";
          }
        } //seconds

      } //list arp-timeout

      container authentication-policy {
        description
            "Configures the authentication policy for this interface";
        leaf-list name {
          type string {
            length "1..32";
          }
          max-elements 5;
          description
              "[32 chars max]";
        } //name

      } //container authentication-policy

      container bfd {
        description
            "Configure BFD parameters";
        leaf transmit-interval {
          type uint32 {
            range "10..100000";
          }
          description
              "[10..100000] in milliseconds";
        } //transmit-interval

        leaf receive {
          type uint32 {
            range "10..100000";
          }
          description
              "[10..100000] in milliseconds";
        } //receive

        leaf multiplier {
          type string;
          description
              "[3..20]";
        } //multiplier

        leaf echo-receive {
          type uint32 {
            range "100..100000";
          }
          description
              "[100..100000] in milliseconds";
        } //echo-receive

        leaf type {
          type enumeration {
            enum cpm-np;
          }
          description
              "keyword - use CPM network processor";
        } //type

      } //container bfd

      container cpu-protection {
        description
            "Configure a CPU protection policy";
        leaf cpu-protection-policy-id {
          type uint32 {
            range "1..255";
          }
          default 254;
          description
              "[1..255] - Default: 254";
        } //cpu-protection-policy-id

      } //container cpu-protection

      container delayed-enable {
        status "obsolete";
        description
            "Delays making interface operational by the specified number of seconds";
        leaf seconds {
          type uint32 {
            range "1..65535";
          }
        } //seconds

        leaf init-only {
          type boolean;
        } //init-only

      } //container delayed-enable

      list description {
        key "long-description-string";
        description
            "Description for VPRN interface";
        leaf long-description-string {
          type string {
            length "1..160";
          }
        } //long-description-string

      } //list description

      container dynamic-tunnel-redundant-next-hop {
        description
            "Configure dynamic ISA tunnel redundant next-hop address";
        leaf ip-address {
          type inet:ip-address;
        } //ip-address

      } //container dynamic-tunnel-redundant-next-hop

      leaf enable-ingress-stats {
        type boolean;
        description
            "Enable/disable the gathering of ingress interface statistics";
      }

      leaf enable-mac-accounting {
        type boolean;
        description
            "Configure MAC Accounting functionality for the interface.";
      }

      container host-connectivity-verify {
        description
            "Enable/disable host connectivity verification for all hosts on this interface";
        leaf source {
          type enumeration {
            enum vrrp;
            enum interface;
          }
          description
              "keywords";
        } //source

        leaf interval {
          type uint64 {
            range "1..6000";
          }
          description
              "[1..6000] minutes";
        } //interval

        leaf action {
          type enumeration {
            enum remove;
            enum alarm;
          }
          description
              "keywords";
        } //action

        leaf timeout {
          type uint8 {
            range "10..60";
          }
          description
              "[10..60] seconds";
        } //timeout

        leaf retry-count {
          type uint8 {
            range "2..29";
          }
          description
              "[2..29]";
        } //retry-count

      } //container host-connectivity-verify

      container ip-helper-address {
        description
            "Configure the gateway address to forward UDP traffic sent to the local 
             broadcast address on the interface";
        leaf gateway-address {
          type inet:ip-address;
          description
              "expressed in dotted decimal format (a.b.c.d)";
        } //gateway-address

      } //container ip-helper-address

      container ip-mtu {
        description
            "Configure the interface IP MTU";
        leaf octets {
          type uint32 {
            range "512..9000";
          }
        } //octets

      } //container ip-mtu

      container local-dhcp-server {
        description
            "Assign a DHCP server to the interface";
        leaf local-server-name {
          type string {
            length "1..32";
          }
        } //local-server-name

      } //container local-dhcp-server

      leaf local-proxy-arp {
        type boolean;
        description
            "Enable/disable local proxy ARP on the interface";
      }

      leaf loopback {
        type boolean;
        description
            "Configure the interface as a loopback interface";
      }

      list mac {
        key "ieee-address";
        description
            "Assign a MAC address to the interface";
        leaf ieee-address {
          type string;
          description
              "xx:xx:xx:xx:xx:xx or xx-xx-xx-xx-xx-xx (cannot be all zeros)";
        } //ieee-address

      } //list mac

      container monitor-oper-group {
        description
            "Configure operational group to monitor";
        leaf name {
          type string {
            length "1..32";
          }
        } //name

      } //container monitor-oper-group

      container proxy-arp-policy {
        description
            "Configure a proxy ARP policy for the interface";
        leaf-list policy-name {
          type string {
            length "1..32";
          }
          max-elements 5;
          description
              "[32 chars max]";
        } //policy-name

      } //container proxy-arp-policy

      leaf ptp-hw-assist {
        type boolean;
        description
            "Enable/Disable time stamping Precision Timing Protocol (PTP) packets at the 
             physical interface.";
      }

      container qos-route-lookup {
        description
            "Configure Qos route lookup for the interface";
        leaf source-destination {
          type enumeration {
            enum source;
            enum destination;
          }
        } //source-destination

      } //container qos-route-lookup

      leaf remote-proxy-arp {
        type boolean;
        description
            "Enable/disable remote proxy ARP on the interface";
      }

      list secondary {
        key "ip-address-mask";
        description
            "Assigns a secondary IP address/IP subnet/broadcast address format to the 
             interface";
        leaf ip-address-mask {
          type string;
          description
              "ip-address a.b.c.d 
               mask [0..32]";
        } //ip-address-mask

        leaf netmask {
          type string;
          description
              "a.b.c.d (network bits all 1 and host bits all 0)";
        } //netmask

        leaf broadcast {
          type enumeration {
            enum all-ones;
            enum host-ones;
          }
          description
              "keywords";
        } //broadcast

        leaf igp-inhibit {
          type boolean;
          description
              "secondary ip-address should not be recognized as a local interface by the 
               running IGP";
        } //igp-inhibit

        leaf track-srrp {
          type uint32 {
            range "1..4294967295";
          }
        } //track-srrp

      } //list secondary

      container shcv-policy-ipv4 {
        description
            "Configure the Subscriber Host Connectivity Verification policy for IPv4";
        leaf policy-name {
          type string;
        } //policy-name

      } //container shcv-policy-ipv4

      leaf shutdown {
        type boolean;
        description
            "Administratively enable/disable the interface";
      }

      list static-arp {
        key "ieee-address";
        description
            "Configure a static ARP entry for the interface";
        leaf ip-address {
          type inet:ip-address;
        } //ip-address

        leaf ieee-address {
          type string;
          description
              "xx:xx:xx:xx:xx:xx or xx-xx-xx-xx-xx-xx (cannot be all zeros)";
        } //ieee-address

        leaf unnumbered {
          type boolean;
        } //unnumbered

      } //list static-arp

      container static-tunnel-redundant-next-hop {
        description
            "Configure static ISA tunnel redundant next-hop address";
        leaf ip-address {
          type inet:ip-address;
        } //ip-address

      } //container static-tunnel-redundant-next-hop

      container tcp-mss {
        description
            "Configure TCP maximum segment size for the interface";
        leaf mss-value {
          type uint32 {
            range "384..9158";
          }
        } //mss-value

      } //container tcp-mss

      container tos-marking-state {
        description
            "Specify TOS marking state";
        leaf trusted-untrusted {
          type enumeration {
            enum trusted;
            enum untrusted;
          }
          description
              "keywords";
        } //trusted-untrusted

      } //container tos-marking-state

      container unnumbered {
        description
            "Configure the interface as an unnumbered interface";
        leaf ip-int-name-ip-address {
          type string;
          description
              "Attribute ip-int-name|ip-address for unnumbered";
        } //ip-int-name-ip-address

      } //container unnumbered

      container vas-if-type {
        description
            "Specifies VAS interface type";
        leaf vas-if-type-id {
          type enumeration {
            enum to-from-access;
            enum to-from-network;
            enum to-from-both;
          }
        } //vas-if-type-id

      } //container vas-if-type

      container cflowd-parameters {
        description
            "Configure Cflowd parameters on the interface";
        list sampling {
          key "sampling-id";
          description
              "Configure the Cflowd sampling parameters";
          leaf sampling-id {
            type enumeration {
              enum unicast;
              enum multicast;
            }
          } //sampling-id

          leaf type {
            type enumeration {
              enum acl;
              enum interface;
            }
          } //type

          leaf direction {
            type enumeration {
              enum ingress-only;
              enum egress-only;
              enum both;
            }
            default "ingress-only";
            description
                "keywords - Default: ingress-only";
          } //direction

        } //list sampling

      } //container cflowd-parameters

      container dhcp {
        description
            "Configure DHCP parameters";
        container description {
          description
              "Add/remove a text description for DHCP";
          leaf description-string {
            type string {
              length "1..80";
            }
          } //description-string

        } //container description

        container gi-address {
          description
              "Configure the gateway interface address for the DHCP relay";
          leaf ip-address {
            type inet:ip-address;
          } //ip-address

          leaf src-ip-addr {
            type boolean;
            description
                "keyword - use the gi-address as src-ip";
          } //src-ip-addr

        } //container gi-address

        container lease-populate {
          description
              "Configure the maximum number of DHCPv4 leases";
          leaf nbr-of-leases {
            type int32 {
              range "1..131071";
            }
            description
                "Attribute nbr-of-leases for lease-populate";
          } //nbr-of-leases

        } //container lease-populate

        container python-policy {
          description
              "Configure the Python policy";
          leaf name {
            type string {
              length "1..32";
            }
          } //name

        } //container python-policy

        leaf relay-plain-bootp {
          type boolean;
          description
              "Enable/disable relaying of plain BOOTP packets";
        }

        container relay-proxy {
          description
              "Enable/disable relaying of unicast DHCP client messages and optional DHCP 
               server ip address hiding";
          leaf release-update-src-ip {
            type boolean;
          } //release-update-src-ip

          leaf siaddr-override {
            type inet:ip-address;
          } //siaddr-override

        } //container relay-proxy

        container server {
          description
              "Configure the DHCP server IP address";
          leaf-list server-ip-address {
            type inet:ip-address;
            max-elements 8;
            description
                "DHCP server IP address";
          } //server-ip-address

        } //container server

        leaf shutdown {
          type boolean;
          description
              "Administratively enable/disable DHCP on this interface";
        }

        leaf trusted {
          type boolean;
          description
              "Enable/disable relaying of untrusted packets";
        }

        leaf use-arp {
          type boolean;
          description
              "enable/disable the use of ARP to determine the destination Hw address";
        }

        container option {
          presence
              "Configure the DHCP Relay information options";
          container action {
            description
                "Configure the DHCP Relay reforwarding policy action";
            leaf replace-drop-keep {
              type enumeration {
                enum replace;
                enum drop;
                enum keep;
              }
              description
                  "keywords";
            } //replace-drop-keep

          } //container action

          container circuit-id {
            description
                "Configure the circuit-id suboption of the DHCP Relay packet";
            leaf ifindex {
              type boolean;
            } //ifindex

            leaf ascii-tuple {
              type boolean;
            } //ascii-tuple

            leaf sap-id {
              type boolean;
            } //sap-id

            leaf vlan-ascii-tuple {
              type boolean;
            } //vlan-ascii-tuple

          } //container circuit-id

          container remote-id {
            description
                "Configure the remote-id suboption of the DHCP Relay packet";
            leaf mac {
              type boolean;
            } //mac

            leaf string {
              type string {
                length "1..32";
              }
              description
                  "Max 32 chars";
            } //string

          } //container remote-id

          container vendor-specific-option {
            presence
                "Configure the Nokia vendor specific suboption of the DHCP Relay packet";
            leaf client-mac-address {
              type boolean;
              description
                  "Enable/disable sending of the MAC address in the Nokia vendor specific 
                   suboption of the DHCP Relay packet";
            }

            leaf pool-name {
              type boolean;
              description
                  "Enable/disable sending of the pool name in the Nokia vendor specific suboption 
                   of the DHCP Relay packet";
            }

            leaf sap-id {
              type boolean;
              description
                  "Enable/disable sending of the SAP-id in the Nokia vendor specific suboption of 
                   the DHCP Relay packet";
            }

            leaf service-id {
              type boolean;
              description
                  "Enable/disable sending of the service-id in the Nokia vendor specific 
                   suboption of the DHCP Relay packet";
            }

            container string {
              description
                  "Specifies the string in the Nokia vendor specific suboption of the DHCP Relay 
                   packet";
              leaf text {
                type string {
                  length "1..32";
                }
              } //text

            } //container string

            leaf system-id {
              type boolean;
              description
                  "Enable/disable sending of the system-id in the Nokia vendor specific suboption 
                   of the DHCP Relay packet";
            }

          } //container vendor-specific-option

        } //container option

        container proxy-server {
          description
              "Configure the DHCP proxy server";
          container emulated-server {
            description
                "Specify the emulated server address";
            leaf ip-address {
              type inet:ip-address;
            } //ip-address

          } //container emulated-server

          container lease-time {
            description
                "Configure the DHCP lease time";
            leaf days {
              type int32 {
                range "0..3650";
              }
            } //days

            leaf hrs {
              type int32 {
                range "0..23";
              }
            } //hrs

            leaf min {
              type int32 {
                range "0..59";
              }
            } //min

            leaf sec {
              type int32 {
                range "0..59";
              }
            } //sec

            leaf override {
              type boolean;
            } //override

          } //container lease-time

          leaf shutdown {
            type boolean;
            description
                "Administratively enable/disable DHCP proxy on this interface";
          }

        } //container proxy-server

      } //container dhcp

      container hold-time {
        description
            "Configure the hold times (up/down) for the interface";
        container down {
          description
              "Configure the hold time when the interface is coming up";
          leaf ip {
            type boolean;
          } //ip

          leaf ipv6 {
            type boolean;
          } //ipv6

          leaf seconds {
            type uint32 {
              range "1..1200";
            }
          } //seconds

          leaf init-only {
            type boolean;
          } //init-only

        } //container down

        container up {
          description
              "Configure the hold time when the interface is going down";
          leaf ip {
            type boolean;
          } //ip

          leaf ipv6 {
            type boolean;
          } //ipv6

          leaf seconds {
            type uint32 {
              range "1..1200";
            }
          } //seconds

        } //container up

      } //container hold-time

      container icmp {
        description
            "Configure ICMP parameters for the interface";
        leaf mask-reply {
          type boolean;
          description
              "Enable/disable responses to ICMP mask requests";
        }

        container param-problem {
          description
              "Configures rate for ICMP param-problem messages";
          leaf-list number-seconds {
            type uint16 {
              range "1..1000";
            }
            max-elements 2;
            description
                "number [10..1000] 
                 seconds [1..60]";
          } //number-seconds

        } //container param-problem

        container redirects {
          description
              "Configures rate for ICMP redirect messages";
          leaf-list number-seconds {
            type uint16 {
              range "1..1000";
            }
            max-elements 2;
            description
                "number [10..1000] 
                 seconds [1..60]";
          } //number-seconds

        } //container redirects

        container ttl-expired {
          description
              "Configures rate for ICMP TTL expired messages";
          leaf-list number-seconds {
            type uint16 {
              range "1..2000";
            }
            max-elements 2;
            description
                "number [10..2000] 
                 seconds [1..60]";
          } //number-seconds

        } //container ttl-expired

        container unreachables {
          description
              "Configures rate for ICMP unreachable messages";
          leaf-list number-seconds {
            type uint16 {
              range "1..2000";
            }
            max-elements 2;
            description
                "number [10..2000] 
                 seconds [1..60]";
          } //number-seconds

        } //container unreachables

      } //container icmp

      container if-attribute {
        description
            "Add/Remove interface attributes";
        container admin-group {
          description
              "Configure interface Admin Group memberships for this interface";
          leaf-list group-name {
            type string {
              length "1..32";
            }
            max-elements 5;
          } //group-name

        } //container admin-group

        container srlg-group {
          description
              "Configure interface SRLG Group memberships for this interface";
          leaf-list group-name {
            type string {
              length "1..32";
            }
            max-elements 5;
          } //group-name

        } //container srlg-group

      } //container if-attribute

      container ingress {
        description
            "Configure ingress network filter policies for the interface.";
        container policy-accounting {
          description
              "Enable/Disable policy accounting template";
          leaf template-name {
            type string {
              length "1..32";
            }
          } //template-name

        } //container policy-accounting

      } //container ingress

      container ipcp {
        description
            "Configure IPCP parameters";
        list dns {
          key "secondary";
          description
              "Configure the Peer's Primary and Secondary DNS Addresses";
          leaf ip-address {
            type inet:ip-address;
            description
                "a.b.c.d (unicast only)";
          } //ip-address

          leaf secondary {
            type inet:ip-address;
            description
                "a.b.c.d (unicast only)";
          } //secondary

        } //list dns

        container peer-ip-address {
          description
              "Configure the Peer's IP Address";
          leaf ip-address {
            type inet:ip-address;
            description
                "a.b.c.d (unicast only)";
          } //ip-address

        } //container peer-ip-address

      } //container ipcp

      container ipv6 {
        presence
            "Enables/Configures IPv6 for a VPRN interface";
        list address {
          key "ipv6-address-prefix-length";
          description
              "Assigns an IPv6 address to the VPRN interface.";
          leaf ipv6-address-prefix-length {
            type string;
            description
                "ipv6-address x:x:x:x:x:x:x:x (eight 16-bit pieces) 
                 x:x:x:x:x:x:d.d.d.d 
                 x [0..FFFF]H 
                 d [0..255]D 
                 (no multicast address) 
                 prefix-length [1..128]";
          } //ipv6-address-prefix-length

          leaf eui-64 {
            type boolean;
          } //eui-64

          leaf preferred {
            type boolean;
            status "obsolete";
          } //preferred

          leaf track-srrp {
            type uint32 {
              range "1..4294967295";
            }
          } //track-srrp

          leaf modifier {
            type string {
              length "1..34";
            }
            description
                "[0x0..0xFFFFFFFF...(32 hex nibbles)]";
          } //modifier

          leaf dad-disable {
            type boolean;
          } //dad-disable

          leaf primary-preference {
            type uint32 {
              range "1..4294967295";
            }
          } //primary-preference

        } //list address

        container bfd {
          description
              "Configure BFD parameters";
          leaf transmit-interval {
            type uint32 {
              range "10..100000";
            }
            description
                "[10..100000] in milliseconds";
          } //transmit-interval

          leaf receive {
            type uint32 {
              range "10..100000";
            }
            description
                "[10..100000] in milliseconds";
          } //receive

          leaf multiplier {
            type string;
            description
                "[3..20]";
          } //multiplier

          leaf echo-receive {
            type uint32 {
              range "100..100000";
            }
            description
                "[100..100000] in milliseconds";
          } //echo-receive

          leaf type {
            type enumeration {
              enum cpm-np;
            }
            description
                "keyword - use CPM network processor";
          } //type

        } //container bfd

        leaf dad-disable {
          type boolean;
          description
              "Disable Duplicate Address Detection";
        }

        container link-local-address {
          description
              "Configure link-local address";
          leaf ipv6-address {
            type string;
            description
                "Attribute ipv6-address for link-local-address";
          } //ipv6-address

          leaf preferred {
            type boolean;
            status "obsolete";
          } //preferred

          leaf dad-disable {
            type boolean;
          } //dad-disable

        } //container link-local-address

        container local-dhcp-server {
          description
              "Assign a DHCP server to the interface";
          leaf local-server-name {
            type string {
              length "1..32";
            }
          } //local-server-name

        } //container local-dhcp-server

        leaf local-proxy-nd {
          type boolean;
          description
              "Enable/disable local proxy Neighbor Discovery on the VPRN interface";
        }

        container nd-learn-unsolicited {
          description
              "Configure neighbor discover learn unsolicited";
          leaf nd-learn-unsolicited-id {
            type enumeration {
              enum global;
              enum link-local;
              enum both;
            }
          } //nd-learn-unsolicited-id

        } //container nd-learn-unsolicited

        leaf nd-populate-host-route {
          type boolean;
          description
              "Configure neighbor discovery populate host route";
        }

        container nd-proactive-refresh {
          description
              "Configure neighbor discovery proactive refresh";
          leaf nd-proactive-refresh-id {
            type enumeration {
              enum global;
              enum link-local;
              enum both;
            }
          } //nd-proactive-refresh-id

        } //container nd-proactive-refresh

        container nd-route-tag {
          description
              "Configure neighbor discovery route tag";
          leaf nd-route-tag-string {
            type string;
          } //nd-route-tag-string

        } //container nd-route-tag

        list neighbor {
          key "ipv6-address";
          description
              "Configure IPv6-to-MAC address mapping on the VPRN interface";
          leaf ipv6-address {
            type inet:ipv6-address;
            description
                "x:x:x:x:x:x:x:x (eight 16-bit pieces) 
                 x:x:x:x:x:x:d.d.d.d 
                 x [0..FFFF]H 
                 d [0..255]D 
                 prefix-length [1..128]";
          } //ipv6-address

          leaf mac-address {
            type alu:ieee-address;
            description
                "xx:xx:xx:xx:xx:xx or xx-xx-xx-xx-xx-xx";
          } //mac-address

        } //list neighbor

        container neighbor-limit {
          description
              "Configures the maximum amount of IPv6 neighbor entries";
          leaf limit {
            type int32 {
              range "0..102400";
            }
            description
                "[0..102400] entries - default = disabled";
          } //limit

          leaf log-only {
            type boolean;
          } //log-only

          leaf threshold {
            type uint32 {
              range "1..100";
            }
          } //threshold

        } //container neighbor-limit

        container proxy-nd-policy {
          description
              "Configure a proxy Neighbor Discovery policy for the VPRN interface";
          leaf-list policy-name {
            type string {
              length "1..32";
            }
            max-elements 5;
            description
                "[32 chars max]";
          } //policy-name

        } //container proxy-nd-policy

        container qos-route-lookup {
          description
              "Enable/Disable Qos route lookup for the interface";
          leaf source-destination {
            type enumeration {
              enum source;
              enum destination;
            }
          } //source-destination

        } //container qos-route-lookup

        container reachable-time {
          description
              "Configure neighbor reachability detection timer";
          leaf seconds {
            type uint32 {
              range "30..3600";
            }
          } //seconds

        } //container reachable-time

        container stale-time {
          description
              "Configure the time a neighbor discovery cache entry can remain stale before 
               being removed";
          leaf seconds {
            type uint32 {
              range "60..65535";
            }
          } //seconds

        } //container stale-time

        container tcp-mss {
          description
              "Configure TCP maximum segment size for the interface";
          leaf mss-value {
            type uint32 {
              range "1220..9138";
            }
          } //mss-value

        } //container tcp-mss

        container dhcp6-relay {
          presence
              "Configure DHCPv6 relay parameters for the VPRN interface";
          container description {
            description
                "Description for VPRN interface DHCPv6 relay";
            leaf description-string {
              type string {
                length "1..80";
              }
            } //description-string

          } //container description

          container lease-populate {
            description
                "Configures the amount of DHCPv6 leases allowed";
            leaf nbr-of-leases {
              type int32 {
                range "1..131071";
              }
              description
                  "Attribute nbr-of-leases for lease-populate";
            } //nbr-of-leases

            leaf route-populate {
              type boolean;
            } //route-populate

            leaf pd {
              type boolean;
            } //pd

            leaf na {
              type boolean;
            } //na

            leaf ta {
              type boolean;
            } //ta

            leaf exclude {
              type boolean;
            } //exclude

          } //container lease-populate

          container link-address {
            description
                "Configure the link address of the DHCPv6 relay messages";
            leaf ipv6-address {
              type inet:ipv6-address;
            } //ipv6-address

          } //container link-address

          leaf neighbor-resolution {
            type boolean;
            description
                "Enable/disable neighbor resolution via DHCPv6 Relay";
          }

          container python-policy {
            description
                "Configure the Python policy";
            leaf policy-name {
              type string;
            } //policy-name

          } //container python-policy

          container server {
            description
                "Configure the DHCPv6 server IPv6 address";
            leaf-list ipv6z-address {
              type string;
              max-elements 8;
              description
                  "Attribute ipv6z-address for server";
            } //ipv6z-address

          } //container server

          leaf shutdown {
            type boolean;
            description
                "Administratively enable/disable DHCPv6 relay on this interface";
          }

          container source-address {
            description
                "Configure the source IPv6 address of the DHCPv6 relay messages";
            leaf ipv6-address {
              type inet:ipv6-address;
              description
                  "ipv6-address x:x:x:x:x:x:x:x (eight 16-bit pieces) 
                   x:x:x:x:x:x:d.d.d.d 
                   x [0..FFFF]H 
                   d [0..255]D 
                   ";
            } //ipv6-address

          } //container source-address

          container user-db {
            description
                "Configure the local user database to use for authentication";
            leaf local-user-db-name {
              type string {
                length "1..32";
              }
            } //local-user-db-name

          } //container user-db

          container option {
            presence
                "Configure the DHCPv6 Relay information options";
            container interface-id {
              description
                  "Enable/disable sending of interface-id option in the DHCPv6 Relay packet";
              leaf ifindex {
                type boolean;
              } //ifindex

              leaf ascii-tuple {
                type boolean;
              } //ascii-tuple

              leaf sap-id {
                type boolean;
              } //sap-id

              leaf string {
                type string {
                  length "1..80";
                }
              } //string

            } //container interface-id

            leaf remote-id {
              type boolean;
              description
                  "Enable/disable sending of remote-id option in the DHCPv6 Relay packet";
            }

          } //container option

        } //container dhcp6-relay

        container dhcp6-server {
          presence
              "Configure DHCPv6 server parameters for the VPRN interface";
          container max-nbr-of-leases {
            description
                "Configures the amount of DHCPv6 leases allowed";
            leaf max-nbr-of-leases {
              type int32 {
                range "0..8000";
              }
            } //max-nbr-of-leases

          } //container max-nbr-of-leases

          container prefix-delegation {
            presence
                "Configure the DHCPv6 Prefix Delegation options";
            leaf shutdown {
              type boolean;
              description
                  "Administratively enable/disable prefix delegation on this interface";
            }

            list prefix {
              key "ipv6-address-prefix-length";
              description
                  "Configure the IPv6 prefix/mask for DHCPv6 clients";
              leaf ipv6-address-prefix-length {
                type string;
                description
                    "ipv6-address x:x:x:x:x:x:x:x (eight 16-bit pieces) 
                     x:x:x:x:x:x:d.d.d.d 
                     x [0..FFFF]H 
                     d [0..255]D 
                     prefix-length [1..128]";
              } //ipv6-address-prefix-length

              container duid {
                description
                    "Configure the DUID of the DHCP client";
                leaf duid {
                  type string {
                    length "1..130";
                  }
                  description
                      "[128 hex values max]";
                } //duid

                leaf iaid {
                  type uint32 {
                    range "1..4294967295";
                  }
                } //iaid

              } //container duid

              container preferred-lifetime {
                description
                    "Configure the IPv6 prefix/mask preferred life time";
                leaf seconds {
                  type uint32 {
                    range "1..4294967294";
                  }
                } //seconds

                leaf infinite {
                  type boolean;
                } //infinite

              } //container preferred-lifetime

              container valid-lifetime {
                description
                    "Configure the IPv6 prefix/mask valid life time";
                leaf seconds {
                  type uint32 {
                    range "1..4294967294";
                  }
                } //seconds

                leaf infinite {
                  type boolean;
                } //infinite

              } //container valid-lifetime

            } //list prefix

          } //container prefix-delegation

        } //container dhcp6-server

        container icmp6 {
          description
              "Configure ICMPv6 parameters for the VPRN interface";
          container packet-too-big {
            description
                "Configures rate for ICMPv6 packet-too-big messages";
            leaf-list number-seconds {
              type uint16 {
                range "1..1000";
              }
              max-elements 2;
              description
                  "number [10..1000] 
                   seconds [1..60]";
            } //number-seconds

          } //container packet-too-big

          container param-problem {
            description
                "Configures rate for ICMPv6 param-problem messages";
            leaf-list number-seconds {
              type uint16 {
                range "1..1000";
              }
              max-elements 2;
              description
                  "number [10..1000] 
                   seconds [1..60]";
            } //number-seconds

          } //container param-problem

          container redirects {
            description
                "Configures rate for ICMPv6 redirect messages";
            leaf-list number-seconds {
              type uint16 {
                range "1..1000";
              }
              max-elements 2;
              description
                  "number [10..1000] 
                   seconds [1..60]";
            } //number-seconds

          } //container redirects

          container time-exceeded {
            description
                "Configures rate for ICMPv6 time-exceeded messages";
            leaf-list number-seconds {
              type uint16 {
                range "1..2000";
              }
              max-elements 2;
              description
                  "number [10..2000] 
                   seconds [1..60]";
            } //number-seconds

          } //container time-exceeded

          container unreachables {
            description
                "Configures rate for ICMPv6 unreachable messages";
            leaf-list number-seconds {
              type uint16 {
                range "1..2000";
              }
              max-elements 2;
              description
                  "number [10..2000] 
                   seconds [1..60]";
            } //number-seconds

          } //container unreachables

        } //container icmp6

        container secure-nd {
          presence
              "Configure Secure Neighbor Discovery (SEND) parameters for the interface";
          leaf allow-unsecured-msgs {
            type boolean;
            description
                "Specify whether unsecured messages are accepted";
          }

          container link-local-modifier {
            description
                "Configure the CGA modifier for link-local addresses";
            leaf link-local-modifier-string {
              type string {
                length "1..34";
              }
              description
                  "[0x0..0xFFFFFFFF...(32 hex nibbles)]";
            } //link-local-modifier-string

          } //container link-local-modifier

          container public-key-min-bits {
            description
                "Configure the minimum acceptable key length for public keys used in the 
                 generation of a CGA";
            leaf bits {
              type uint32 {
                range "512..1024";
              }
            } //bits

          } //container public-key-min-bits

          container security-parameter {
            description
                "Configure the security parameter used in the generation of a CGA";
            leaf sec {
              type uint32 {
                range "0..1";
              }
            } //sec

          } //container security-parameter

          leaf shutdown {
            type boolean;
            description
                "Administratively enable/disable SEND on this interface";
          }

        } //container secure-nd

        container urpf-check {
          presence
              "Enables/Configures unicast RPF check for an interface";
          leaf ignore-default {
            type boolean;
            description
                "Enable/Disable default route when performing a uRPF check.";
          }

          container mode {
            description
                "Configure unicast RPF check mode";
            leaf strict-loose-strict-no-ecmp {
              type enumeration {
                enum strict;
                enum loose;
                enum strict-no-ecmp;
              }
              description
                  "keywords";
            } //strict-loose-strict-no-ecmp

          } //container mode

        } //container urpf-check

        list vrrp {
          key "virtual-router-id";
          description
              "Context to create and configure VRRP virtual router instance on the interface";
          leaf virtual-router-id {
            type uint16 {
              range "1..255";
            }
          } //virtual-router-id

          leaf owner {
            type boolean;
          } //owner

          leaf passive {
            type boolean;
          } //passive

          list backup {
            key "ipv6-address";
            description
                "Configure virtual router IP addresses for the interface";
            leaf ipv6-address {
              type inet:ipv6-address;
              description
                  "x:x:x:x:x:x:x:x (eight 16-bit pieces) 
                   ";
            } //ipv6-address

          } //list backup

          list bfd-enable {
            key "interface dst-ip";
            description
                "Configure a BFD interface";
            leaf service-id {
              type string;
              description
                  "Attribute service-id for bfd-enable";
            } //service-id

            leaf interface {
              type string {
                length "1..32";
              }
              description
                  "[32 chars max] (must start with a letter)";
            } //interface

            leaf dst-ip {
              type string;
              description
                  "Attribute ip-address for bfd-enable";
            } //dst-ip

            leaf name {
              type string;
              description
                  "64-char max (ies/vprn service-name)";
            } //name

          } //list bfd-enable

          container init-delay {
            description
                "Configure VRRP initialization delay timer";
            leaf seconds {
              type uint32 {
                range "1..65535";
              }
            } //seconds

          } //container init-delay

          container mac {
            description
                "Configure a Virtual MAC address to use in Neighbor Discovery";
            leaf mac-address {
              type string;
              description
                  "xx:xx:xx:xx:xx:xx or xx-xx-xx-xx-xx-xx";
            } //mac-address

          } //container mac

          leaf master-int-inherit {
            type boolean;
            description
                "Allow/disallow the master instance to dictate the master down timer (non-owner 
                 context only)";
          }

          container message-interval {
            description
                "Configure the interval for sending VRRP Advertisement messages";
            leaf seconds {
              type uint32 {
                range "1..40";
              }
            } //seconds

            leaf milliseconds {
              type uint32 {
                range "10..990";
              }
            } //milliseconds

          } //container message-interval

          container oper-group {
            description
                "Associate group-name to VRRP";
            leaf group-name {
              type string {
                length "1..32";
              }
            } //group-name

          } //container oper-group

          leaf ping-reply {
            type boolean;
            description
                "Allow/disallow non-owner master to reply to ICMP Echo requests (non-owner 
                 context only)";
          }

          container policy {
            description
                "Associate a VRRP Priority Control Policy with the virtual router instance 
                 (non-owner context only)";
            leaf vrrp-policy-id {
              type uint32 {
                range "1..9999";
              }
            } //vrrp-policy-id

          } //container policy

          leaf preempt {
            type boolean;
            description
                "Allow/disallow the virtual router instance to override an existing non-owner 
                 master (non-owner context only)";
          }

          container priority {
            description
                "Configure the base priority for the virtual router instance (non-owner context 
                 only)";
            leaf priority {
              type uint16 {
                range "1..254";
              }
            } //priority

          } //container priority

          leaf shutdown {
            type boolean;
            description
                "Administratively enable/disable the virtual router instance (non-owner context 
                 only)";
          }

          leaf standby-forwarding {
            type boolean;
            description
                "Allow/disallow the forwarding of packets by a standby router";
          }

          leaf telnet-reply {
            type boolean;
            description
                "Allow/disallow non-owner master to reply to Telnet requests (non-owner context 
                 only)";
          }

          leaf traceroute-reply {
            type boolean;
            description
                "Allow/disallow non-owner master to reply to traceroute requests (non-owner 
                 context only)";
          }

        } //list vrrp

      } //container ipv6

      container load-balancing {
        description
            "Context to configure hashing commands";
        container egr-ip-load-balancing {
          description
              "Configure egr-ip-load-balancing for the interface";
          leaf algorithm {
            type enumeration {
              enum source;
              enum destination;
              enum inner-ip;
            }
          } //algorithm

        } //container egr-ip-load-balancing

        leaf spi-load-balancing {
          type boolean;
          description
              "Enable/disable SPI use in hashing for the interface";
        }

        leaf teid-load-balancing {
          type boolean;
          description
              "Enable/disable TEID load balancing for the interface";
        }

      } //container load-balancing

      list sap {
        key "sap-id";
        description
            "Provision a SAP";
        leaf sap-id {
          type string;
          description
              "Attribute sap-id for sap";
        } //sap-id

        container aarp {
          description
              "Configure AARP instance id";
          leaf aarpId {
            type uint32 {
              range "1..65535";
            }
          } //aarpId

          leaf type {
            type enumeration {
              enum dual-homed;
              enum dual-homed-secondary;
            }
          } //type

        } //container aarp

        list accounting-policy {
          key "acct-policy-id";
          description
              "Configure accounting-policy to be used";
          leaf acct-policy-id {
            type uint64 {
              range "1..99";
            }
          } //acct-policy-id

        } //list accounting-policy

        container anti-spoof {
          description
              "Configures anti-spoof filtering for this SAP";
          leaf type {
            type enumeration {
              enum ip;
              enum ip-mac;
              enum mac;
              enum nh-mac;
            }
            description
                "Attribute type for anti-spoof";
          } //type

        } //container anti-spoof

        container app-profile {
          description
              "Configure the application profile name";
          leaf app-profile-name {
            type string {
              length "1..32";
            }
          } //app-profile-name

        } //container app-profile

        container bandwidth {
          description
              "Configure SAP Bandwidth";
          leaf bandwidth {
            type uint32 {
              range "1..3200000000";
            }
            description
                "[1..3200000000] Kbps";
          } //bandwidth

        } //container bandwidth

        container calling-station-id {
          description
              "Configure the RADIUS calling-station-id to include in auth/acct requests";
          leaf calling-station-id {
            type string {
              length "1..64";
            }
          } //calling-station-id

        } //container calling-station-id

        leaf collect-stats {
          type boolean;
          description
              "Enable/disable statistics collection";
        }

        container cpu-protection {
          description
              "Configure CPU protection";
          leaf policy-id {
            type uint32 {
              range "1..255";
            }
            default 254;
            description
                "[1..255] - Default: 254";
          } //policy-id

          leaf mac-monitoring {
            type boolean;
            description
                "keyword - enable MAC monitoring";
          } //mac-monitoring

          leaf eth-cfm-monitoring {
            type boolean;
            description
                "keyword - enable Ethernet Connectivity Fault Management monitoring";
          } //eth-cfm-monitoring

          leaf aggregate {
            type boolean;
            description
                "keyword - apply the rate limit to the sum of the per peer packet rates";
          } //aggregate

          leaf car {
            type boolean;
            description
                "keyword - Committed Access Rate - ignore Eth-CFM packets when enforcing 
                 overall-rate";
          } //car

          leaf ip-src-monitoring {
            type boolean;
            description
                "keyword - enable monitoring per IP source address";
          } //ip-src-monitoring

        } //container cpu-protection

        list description {
          key "long-description-string";
          description
              "Description for the SAP";
          leaf long-description-string {
            type string {
              length "1..160";
            }
          } //long-description-string

        } //list description

        container dist-cpu-protection {
          description
              "Assign Distributed CPU protection policy for the SAP";
          leaf policy-name {
            type string;
          } //policy-name

        } //container dist-cpu-protection

        container host-lockout-policy {
          description
              "Configure host lockout policy";
          leaf policy-name {
            type string {
              length "1..32";
            }
          } //policy-name

        } //container host-lockout-policy

        leaf host-shutdown {
          type boolean;
          description
              "Administratively enable/disable host creation on this SAP";
        }

        container lag-link-map-profile {
          description
              "Configure lag link profile";
          leaf link-map-profile-id {
            type string;
            description
                "Attribute link-map-profile-id for lag-link-map-profile";
          } //link-map-profile-id

        } //container lag-link-map-profile

        container lag-per-link-hash {
          description
              "Configure per-link-hash information";
          leaf class {
            type enumeration {
              enum 1;
              enum 2;
              enum 3;
            }
          } //class

          leaf weight {
            type uint32 {
              range "1..1024";
            }
          } //weight

        } //container lag-per-link-hash

        container multi-service-site {
          description
              "Specify the multi-service-site to which this SAP belongs";
          leaf customer-site-name {
            type string {
              length "1..32";
            }
          } //customer-site-name

        } //container multi-service-site

        leaf shutdown {
          type boolean;
          description
              "Administratively enable/disable the SAP";
        }

        container tod-suite {
          status "obsolete";
          description
              "Configure a time-of-day suite for this SAP";
          leaf tod-suite-name {
            type string {
              length "1..32";
            }
          } //tod-suite-name

        } //container tod-suite

        container transit-policy {
          description
              "Configure transit policy id";
          leaf ip {
            type uint32 {
              range "1..65535";
            }
          } //ip

          leaf prefix {
            type uint32 {
              range "1..65535";
            }
          } //prefix

        } //container transit-policy

        container atm {
          description
              "Configure ATM properties";
          container encapsulation {
            description
                "Configure the ATM encap-type";
            leaf atm-encap-type {
              type enumeration {
                enum aal5snap-routed;
                enum aal5mux-ip;
                enum aal5snap-bridged;
                enum aal5mux-bridged-eth-nofcs;
              }
              description
                  "keywords - aal5snap-routed|aal5mux-ip| 
                   aal5snap-bridged|aal5mux-bridged-eth-nofcs";
            } //atm-encap-type

          } //container encapsulation

          container egress {
            description
                "Configure egress parameters";
            container traffic-desc {
              description
                  "Assign ATM traffic descriptor profile";
              leaf traffic-desc-profile-id {
                type int32 {
                  range "1..1000";
                }
              } //traffic-desc-profile-id

            } //container traffic-desc

          } //container egress

          container ingress {
            description
                "Configure ingress parameters";
            container traffic-desc {
              description
                  "Assign ATM traffic descriptor profile";
              leaf traffic-desc-profile-id {
                type int32 {
                  range "1..1000";
                }
              } //traffic-desc-profile-id

            } //container traffic-desc

          } //container ingress

          container oam {
            description
                "Configure OAM properties";
            leaf alarm-cells {
              type boolean;
              description
                  "Disable/enable handling and generation of AIS/RDI";
            }

            leaf periodic-loopback {
              type boolean;
              description
                  "Disable/enable periodic loopback cells";
            }

          } //container oam

        } //container atm

        container egress {
          description
              "Configure egress policy";
          container filter {
            description
                "Apply egress filter";
            leaf ip {
              type string;
              description
                  "[1..65535]|<name:64 char max>";
            } //ip

            leaf ipv6 {
              type string;
              description
                  "[1..65535]|<name:64 char max>";
            } //ipv6

          } //container filter

          container policer-control-policy {
            description
                "Specify policer control policy";
            leaf policy-name {
              type string {
                length "1..32";
              }
            } //policy-name

          } //container policer-control-policy

          leaf qinq-mark-top-only {
            type boolean;
            description
                "Mark p-bits on top q-tag only";
          }

          list qos {
            key "policy-id";
            description
                "Apply egress qos policy";
            leaf policy-id {
              type string;
              description
                  "[1..65535]|<name:64 char max>";
            } //policy-id

            leaf port-redirect-group {
              type string {
                length "1..32";
              }
            } //port-redirect-group

            leaf instance {
              type uint16 {
                range "1..65535";
              }
            } //instance

          } //list qos

          container queue-group-redirect-list {
            description
                "Assign queue-group redirect list";
            leaf redirect-list-name {
              type string;
            } //redirect-list-name

          } //container queue-group-redirect-list

          container scheduler-policy {
            description
                "Specify a scheduler-policy";
            leaf scheduler-policy-name {
              type string {
                length "1..32";
              }
            } //scheduler-policy-name

          } //container scheduler-policy

          container agg-rate {
            presence
                "Configure aggregate rate limit";
            leaf limit-unused-bandwidth {
              type boolean;
              description
                  "Specify whether to enable limit unused bandwidth";
            }

            leaf queue-frame-based-accounting {
              type boolean;
              description
                  "Specify whether to enable queue frame based accounting";
            }

            container rate {
              description
                  "Specify rate limit for agg-rate";
              leaf kilobits-per-second {
                type string;
                description
                    "[1..3200000000|max] Kbps";
              } //kilobits-per-second

            } //container rate

          } //container agg-rate

          container hsmda-queue-override {
            presence
                "Configure HSMDA egress queue overrides";
            container packet-byte-offset {
              description
                  "Specify a packet offset for HSMDA queue accounting";
              leaf add {
                type uint32 {
                  range "0..31";
                }
              } //add

              leaf subtract {
                type string;
                description
                    "Attribute sub-bytes for packet-byte-offset";
              } //subtract

            } //container packet-byte-offset

            container secondary-shaper {
              description
                  "Configure a HSMDA egress secondary shaper";
              leaf secondary-shaper-name {
                type string {
                  length "1..32";
                }
              } //secondary-shaper-name

            } //container secondary-shaper

            container wrr-policy {
              description
                  "Configure a HSMDA egress wrr policy";
              leaf policy-name {
                type string {
                  length "1..32";
                }
              } //policy-name

            } //container wrr-policy

            list queue {
              key "queue-id";
              description
                  "Configure overrides for a HSMDA egress queue";
              leaf queue-id {
                type uint32 {
                  range "1..8";
                }
              } //queue-id

              container mbs {
                description
                    "Specify MBS rate";
                leaf mbs-string {
                  type string;
                } //mbs-string

                leaf mbs-id-2 {
                  type enumeration {
                    enum bytes;
                    enum kilobytes;
                  }
                } //mbs-id-2

              } //container mbs

              container rate {
                description
                    "Specify rates (CIR and PIR)";
                leaf pir-rate {
                  type string;
                  description
                      "[1..100000000|max]";
                } //pir-rate

              } //container rate

              container slope-policy {
                description
                    "Specify slope policy";
                leaf hsmda-slope-policy-name {
                  type string {
                    length "1..32";
                  }
                } //hsmda-slope-policy-name

              } //container slope-policy

              container wrr-weight {
                description
                    "Specify wrr-weight";
                leaf weight {
                  type int32 {
                    range "1..32";
                  }
                  description
                      "[1..32]";
                } //weight

              } //container wrr-weight

            } //list queue

          } //container hsmda-queue-override

          container policer-control-override {
            description
                "Configure policer control overrides";
            container max-rate {
              description
                  "Configure Max Rate override in kilobits-per-second";
              leaf rate {
                type string;
                description
                    "[1..2000000000|max] Kbps";
              } //rate

            } //container max-rate

            container priority-mbs-thresholds {
              description
                  "Configure priority mbs thresholds overrides";
              container min-thresh-separation {
                description
                    "configure min threshold separation override";
                leaf size {
                  type string;
                  description
                      "[0..16777216 default]";
                } //size

                leaf bytes-kilobytes {
                  type enumeration {
                    enum bytes;
                    enum kilobytes;
                  }
                } //bytes-kilobytes

              } //container min-thresh-separation

              list priority {
                key "level";
                description
                    "Configure Priority Levels overrides";
                leaf level {
                  type uint32 {
                    range "1..8";
                  }
                } //level

                container mbs-contribution {
                  description
                      "Configure mbs size override";
                  leaf size {
                    type string;
                    description
                        "[0..16777216 default]";
                  } //size

                  leaf bytes-kilobytes {
                    type enumeration {
                      enum bytes;
                      enum kilobytes;
                    }
                  } //bytes-kilobytes

                } //container mbs-contribution

              } //list priority

            } //container priority-mbs-thresholds

          } //container policer-control-override

          container policer-override {
            presence
                "Configure policer overrides";
            list policer {
              key "policer-id";
              description
                  "Configure overrides for the policer";
              leaf policer-id {
                type uint32 {
                  range "1..63";
                }
              } //policer-id

              container cbs {
                description
                    "Specify Cbs override";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs override";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "Specify packet byte offset";
                leaf add {
                  type uint32 {
                    range "0..31";
                  }
                } //add

                leaf subtract {
                  type string;
                  description
                      "Attribute sub-bytes for packet-byte-offset";
                } //subtract

              } //container packet-byte-offset

              container percent-rate {
                description
                    "Specify percent rates (CIR and PIR) override";
                leaf pir-percent {
                  type string;
                  description
                      "[0.01..100.00]";
                } //pir-percent

                leaf cir {
                  type string;
                  description
                      "[0.00..100.00]";
                } //cir

              } //container percent-rate

              container rate {
                description
                    "Specify rates (CIR and PIR) override";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-profile-cir;
                    enum offered-total-cir;
                    enum offered-limited-capped-cir;
                    enum offered-profile-capped-cir;
                    enum offered-total-cir-exceed;
                    enum offered-four-profile-no-cir;
                    enum offered-total-cir-four-profile;
                  }
                } //stat-mode

              } //container stat-mode

            } //list policer

          } //container policer-override

          container queue-override {
            presence
                "Apply queue override";
            container hs-secondary-shaper {
              description
                  "Specify HS Secondary Shaper";
              leaf policy-name {
                type string;
              } //policy-name

            } //container hs-secondary-shaper

            list hs-wrr-group {
              key "group-id";
              description
                  "Configure HS WRR Group";
              leaf group-id {
                type uint16 {
                  range "1..2";
                }
                description
                    "[1..2]";
              } //group-id

              container class-weight {
                description
                    "Specify class weight";
                leaf weight {
                  type enumeration {
                    enum 1;
                    enum 2;
                    enum 4;
                    enum 8;
                  }
                } //weight

              } //container class-weight

              container percent-rate {
                description
                    "Specify percent rate";
                leaf percent {
                  type string;
                  description
                      "[0.01..100.00]";
                } //percent

              } //container percent-rate

              container rate {
                description
                    "Specify rates (PIR)";
                leaf rate {
                  type string;
                  description
                      "Attribute rate for rate";
                } //rate

              } //container rate

            } //list hs-wrr-group

            list queue {
              key "queue-id";
              description
                  "Configure a queue override";
              leaf queue-id {
                type int32 {
                  range "1..8";
                }
              } //queue-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container avg-frame-overhead {
                description
                    "Specify the average frame overhead";
                leaf percentage {
                  type string;
                  description
                      "[0.00..100.00]";
                } //percentage

              } //container avg-frame-overhead

              container burst-limit {
                description
                    "Specify burst limit";
                leaf size {
                  type string;
                  description
                      "Attribute size for burst-limit";
                } //size

                leaf bytes-kilobytes {
                  type enumeration {
                    enum bytes;
                    enum kilobytes;
                  }
                } //bytes-kilobytes

              } //container burst-limit

              container cbs {
                description
                    "Specify CBS";
                leaf size-in-kbytes {
                  type string;
                  description
                      "Attribute size-in-kbytes for cbs";
                } //size-in-kbytes

              } //container cbs

              container high-prio-only {
                status "obsolete";
                description
                    "Specify high priority only burst size";
                leaf percent {
                  type string;
                  description
                      "[0..100 | default]";
                } //percent

              } //container high-prio-only

              container hs-class-weight {
                description
                    "Specify HS class weight";
                leaf weight {
                  type enumeration {
                    enum 1;
                    enum 2;
                    enum 4;
                    enum 8;
                  }
                } //weight

              } //container hs-class-weight

              container hs-wred-queue {
                description
                    "Configure HS WRED queue";
                leaf policy {
                  type string {
                    length "1..32";
                  }
                } //policy

              } //container hs-wred-queue

              container hs-wrr-weight {
                description
                    "Specify HS WRR weight";
                leaf weight {
                  type uint16 {
                    range "1..127";
                  }
                  description
                      "[1..127]";
                } //weight

              } //container hs-wrr-weight

              container mbs {
                description
                    "Specify MBS";
                leaf size {
                  type string;
                  description
                      "Attribute size for mbs";
                } //size

                leaf bytes-kilobytes {
                  type enumeration {
                    enum bytes;
                    enum kilobytes;
                  }
                } //bytes-kilobytes

              } //container mbs

              leaf monitor-depth {
                type boolean;
                description
                    "Enable/Disable queue-depth monitoring";
              }

              container parent {
                description
                    "Specify the override weights for the queue within its parental scheduling 
                     context";
                leaf weight {
                  type uint32 {
                    range "0..100";
                  }
                } //weight

                leaf cir-weight {
                  type uint32 {
                    range "0..100";
                  }
                } //cir-weight

              } //container parent

              container percent-rate {
                description
                    "Specify percent rates (CIR and PIR)";
                leaf pir-percent {
                  type string;
                  description
                      "[0.01..100.00]";
                } //pir-percent

                leaf cir {
                  type string;
                  description
                      "[0.00..100.00]";
                } //cir

              } //container percent-rate

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container drop-tail {
                description
                    "Specify drop tail";
                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

            } //list queue

          } //container queue-override

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..3200000000|max] Kbps";
                } //pir-rate

                leaf cir {
                  type string;
                  description
                      "[0..3200000000|sum|max] Kbps";
                } //cir

              } //container rate

            } //list scheduler

          } //container scheduler-override

        } //container egress

        container eth-cfm {
          description
              "Configure CFM parameters";
          leaf collect-lmm-stats {
            type boolean;
            description
                "Enable/Disable the collection of statistics for OAM-PM Loss Measurement 
                 Message (LMM) tests";
          }

          container squelch-ingress-levels {
            description
                "Configure the level(s) of the ETH-CFM PDUs that will be silently discarded";
            leaf t0 {
              type boolean;
              description
                  "[0..7]";
            } //t0

            leaf t1 {
              type boolean;
            } //t1

            leaf t2 {
              type boolean;
            } //t2

            leaf t3 {
              type boolean;
            } //t3

            leaf t4 {
              type boolean;
            } //t4

            leaf t5 {
              type boolean;
            } //t5

            leaf t6 {
              type boolean;
            } //t6

            leaf t7 {
              type boolean;
            } //t7

          } //container squelch-ingress-levels

          container tunnel-fault {
            description
                "Accept/Ignore tunnel fault notification";
            leaf tunnel-fault-id {
              type enumeration {
                enum accept;
                enum ignore;
              }
            } //tunnel-fault-id

          } //container tunnel-fault

          container collect-lmm-fc-stats {
            description
                "Configure the collection of Forwarding Class (FC) aware statistics for OAM-PM 
                 Loss Measurement Message (LMM) tests";
            container fc {
              description
                  "Configure Forwarding Class (FC) counters without regard for profile";
              leaf-list fc-name {
                type enumeration {
                  enum be;
                  enum l2;
                  enum af;
                  enum l1;
                  enum h2;
                  enum ef;
                  enum h1;
                  enum nc;
                }
                max-elements 8;
              } //fc-name

            } //container fc

            container fc-in-profile {
              description
                  "Configure only in profile Forwarding Class (FC) counters";
              leaf-list fc-name {
                type enumeration {
                  enum be;
                  enum l2;
                  enum af;
                  enum l1;
                  enum h2;
                  enum ef;
                  enum h1;
                  enum nc;
                }
                max-elements 8;
              } //fc-name

            } //container fc-in-profile

          } //container collect-lmm-fc-stats

          list mep {
            key "mep-id domain association";
            description
                "Configure a CFM Maintenance Endpoint";
            leaf mep-id {
              type int16 {
                range "1..8191";
              }
            } //mep-id

            leaf domain {
              type uint32 {
                range "1..4294967295";
              }
            } //domain

            leaf association {
              type uint32 {
                range "1..4294967295";
              }
            } //association

            leaf direction {
              type enumeration {
                enum up;
                enum down;
              }
              description
                  "keywords";
            } //direction

            leaf ccm-enable {
              type boolean;
              description
                  "Enable/Disable Generation of CCM messages";
            }

            container ccm-ltm-priority {
              description
                  "Configure the priority of CCM and LTM messages";
              leaf priority {
                type uint16 {
                  range "0..7";
                }
                description
                    "[0..7] - Default highest priority on bridge-port";
              } //priority

            } //container ccm-ltm-priority

            container ccm-padding-size {
              description
                  "Insert additional padding in the CCM packets";
              leaf ccm-padding {
                type uint32 {
                  range "3..1500";
                }
                description
                    "3..1500 octets";
              } //ccm-padding

            } //container ccm-padding-size

            container description {
              description
                  "Add/remove a text description for the MEP";
              leaf description-string {
                type string {
                }
                description
                    "[80 chars max]";
              } //description-string

            } //container description

            container fault-propagation-enable {
              description
                  "Configure the Fault Propagation for the MEP";
              leaf use-if-tlv-suspend-ccm {
                type enumeration {
                  enum use-if-tlv;
                  enum suspend-ccm;
                }
                description
                    "keywords - use interface TLV, or suspend Continuity Check Messages";
              } //use-if-tlv-suspend-ccm

            } //container fault-propagation-enable

            container low-priority-defect {
              description
                  "Configure the low-priority defect for the MEP";
              leaf allDef-macRemErrXcon-remErrXcon-errXcon-xcon-noXcon {
                type enumeration {
                  enum allDef;
                  enum macRemErrXcon;
                  enum remErrXcon;
                  enum errXcon;
                  enum xcon;
                  enum noXcon;
                }
                description
                    "keywords";
              } //allDef-macRemErrXcon-remErrXcon-errXcon-xcon-noXcon

            } //container low-priority-defect

            container mac-address {
              description
                  "Configure the mac-address for the MEP";
              leaf mac-address {
                type yang:mac-address;
              } //mac-address

            } //container mac-address

            container one-way-delay-threshold {
              description
                  "Configure the one-way-delay test threshold";
              leaf seconds {
                type uint32 {
                  range "0..600";
                }
                default 3;
                description
                    "[0..600] Default: 3";
              } //seconds

            } //container one-way-delay-threshold

            leaf shutdown {
              type boolean;
              description
                  "Administratively enable/disable the MEP";
            }

            container ais-enable {
              presence
                  "Configure the generation and reception of Alarm Indication Signal (AIS) 
                   message parameters";
              leaf fake-node {
                type boolean;
              }

              leaf interface-support-enable {
                type boolean;
                description
                    "Enable/disable the generation of AIS PDUs based on the associated endpoint 
                     state";
              }

            } //container ais-enable

            container alarm-notification {
              description
                  "Configure the MEP alarm notification parameters";
              container fng-alarm-time {
                description
                    "Configure the Fault Notification Generation (FNG) alarm time";
                leaf time {
                  type enumeration {
                    enum 0;
                    enum 250;
                    enum 500;
                    enum 1000;
                  }
                  default 0;
                  description
                      "[0,250,500,1000] centi-seconds - Default: 0";
                } //time

              } //container fng-alarm-time

              container fng-reset-time {
                description
                    "Configure the Fault Notification Generation (FNG) reset time";
                leaf time {
                  type enumeration {
                    enum 0;
                    enum 250;
                    enum 500;
                    enum 1000;
                  }
                  default 0;
                  description
                      "[0,250,500,1000] centi-seconds - Default: 0";
                } //time

              } //container fng-reset-time

            } //container alarm-notification

            container csf-enable {
              presence
                  "Configure the reception of Client Signal Fail (CSF) message parameters";
              container multiplier {
                description
                    "Configure the multiplier used for timing out CSF";
                leaf multiplier-value {
                  type string;
                  description
                      "[0.0|2.0 .. 30.0] - Default: 3.5";
                } //multiplier-value

              } //container multiplier

            } //container csf-enable

            container eth-test-enable {
              presence
                  "Enable/Disable eth-test functionality on MEP";
              container bit-error-threshold {
                description
                    "Configure the bit error trap threshold";
                leaf bit-errors {
                  type uint32 {
                    range "0..11840";
                  }
                  default 1;
                  description
                      "[0..11840] Default: 1";
                } //bit-errors

              } //container bit-error-threshold

              container test-pattern {
                description
                    "Configure the test pattern for eth-test frames";
                leaf all-zeros-all-ones {
                  type enumeration {
                    enum all-zeros;
                    enum all-ones;
                  }
                  default "all-zeros";
                  description
                      "keywords - Test pattern - default: all-zeros";
                } //all-zeros-all-ones

                leaf crc-enable {
                  type boolean;
                  description
                      "keyword - Generate CRC checksum";
                } //crc-enable

              } //container test-pattern

            } //container eth-test-enable

            container grace {
              description
                  "Configure the generation and reception of grace period parameters";
              container eth-ed {
                description
                    "Configure the generation and reception of eth-ed grace period parameters";
                container max-rx-defect-window {
                  description
                      "Configure/Disable an upper maximum defect window length; when disabled the 
                       advertised value from the peer will be used; when enabled the lower of the 
                       configured value or the advertised value from the peer will be used";
                  leaf seconds {
                    type uint32 {
                      range "1..86400";
                    }
                    description
                        "[1..86400] - Default: no max-rx-defect-window";
                  } //seconds

                } //container max-rx-defect-window

                container priority {
                  description
                      "Configure/Disable the transmission priority value for ETH-ED PDUs; when 
                       disabled the priority value of ccm-ltm-priority associated with this MEP will 
                       be used";
                  leaf priority {
                    type int32 {
                      range "0..7";
                    }
                    default 0;
                    description
                        "[0..7] - Default: no priority";
                  } //priority

                } //container priority

                leaf rx-eth-ed {
                  type boolean;
                  description
                      "Enable/Disable the receiving and processing of ETH-ED PDUs";
                }

                leaf tx-eth-ed {
                  type boolean;
                  description
                      "Enable/Disable the transmission of ETH-ED PDUs";
                }

              } //container eth-ed

              container eth-vsm-grace {
                description
                    "Configure the generation and reception of sros vendor specific message (vsm) 
                     grace period parameters";
                leaf rx-eth-vsm-grace {
                  type boolean;
                  description
                      "Enable/Disable the receiving and processing of vendor specific message (vsm) 
                       grace period notifications";
                }

                leaf tx-eth-vsm-grace {
                  type boolean;
                  description
                      "Enable/Disable the transmission of vsm grace period notifications";
                }

              } //container eth-vsm-grace

            } //container grace

          } //list mep

        } //container eth-cfm

        container frame-relay {
          description
              "Configure frame-relay parameters";
          container scheduling-class {
            description
                "Configure frf.12 scheduling class";
            leaf class-id {
              type uint32 {
                range "0..3";
              }
            } //class-id

          } //container scheduling-class

          container frf-12 {
            presence
                "Enable/Disable FRF12 Headers";
            container ete-fragment-threshold {
              description
                  "Configure frf.12 fragmentation threshold";
              leaf threshold {
                type uint32 {
                  range "128..512";
                }
              } //threshold

            } //container ete-fragment-threshold

            leaf interleave {
              type boolean;
              description
                  "Enable/Disable frf-12 interleave";
            }

          } //container frf-12

        } //container frame-relay

        container fwd-wholesale {
          description
              "Configure Foward wholesale information";
          container pppoe {
            description
                "Configure EPIPE service id";
            leaf service-id {
              type string;
              description
                  "Attribute service-id for pppoe";
            } //service-id

          } //container pppoe

        } //container fwd-wholesale

        container ingress {
          description
              "Configure ingress policy";
          container filter {
            description
                "Apply ingress filter";
            leaf ip {
              type string;
              description
                  "[1..65535]|<name:64 char max>";
            } //ip

            leaf ipv6 {
              type string;
              description
                  "[1..65535]|<name:64 char max>";
            } //ipv6

          } //container filter

          leaf flowspec {
            type boolean;
            status "obsolete";
            description
                "Enable/disable IPv4 Flowspec on the sap";
          }

          leaf flowspec-ipv6 {
            type boolean;
            status "obsolete";
            description
                "Enable/disable IPv6 Flowspec on the sap";
          }

          container match-qinq-dot1p {
            description
                "Define 802.1P bits to match in QinQ SAP's";
            leaf top-bottom {
              type enumeration {
                enum top;
                enum bottom;
              }
            } //top-bottom

          } //container match-qinq-dot1p

          container policer-control-policy {
            description
                "Specify policer control policy";
            leaf policy-name {
              type string {
                length "1..32";
              }
            } //policy-name

          } //container policer-control-policy

          list qos {
            key "policy-id";
            description
                "Apply ingress qos policy";
            leaf policy-id {
              type string;
              description
                  "[1..65535]|<name:64 char max>";
            } //policy-id

            leaf shared-queuing-multipoint-shared {
              type enumeration {
                enum shared-queuing;
                enum multipoint-shared;
              }
              description
                  "keywords";
            } //shared-queuing-multipoint-shared

            leaf fp-redirect-group {
              type string {
                length "1..32";
              }
            } //fp-redirect-group

            leaf instance {
              type uint16 {
                range "1..65535";
              }
            } //instance

          } //list qos

          container queue-group-redirect-list {
            description
                "Assign queue-group redirect list";
            leaf redirect-list-name {
              type string;
            } //redirect-list-name

          } //container queue-group-redirect-list

          container scheduler-policy {
            description
                "Specify a scheduler-policy";
            leaf scheduler-policy-name {
              type string {
                length "1..32";
              }
            } //scheduler-policy-name

          } //container scheduler-policy

          container policer-control-override {
            description
                "Configure policer control overrides";
            container max-rate {
              description
                  "Configure Max Rate override in kilobits-per-second";
              leaf rate {
                type string;
                description
                    "[1..2000000000|max] Kbps";
              } //rate

            } //container max-rate

            container priority-mbs-thresholds {
              description
                  "Configure priority mbs thresholds overrides";
              container min-thresh-separation {
                description
                    "configure min threshold separation override";
                leaf size {
                  type string;
                  description
                      "[0..16777216 default]";
                } //size

                leaf bytes-kilobytes {
                  type enumeration {
                    enum bytes;
                    enum kilobytes;
                  }
                } //bytes-kilobytes

              } //container min-thresh-separation

              list priority {
                key "level";
                description
                    "Configure Priority Levels overrides";
                leaf level {
                  type uint32 {
                    range "1..8";
                  }
                } //level

                container mbs-contribution {
                  description
                      "Configure mbs size override";
                  leaf size {
                    type string;
                    description
                        "[0..16777216 default]";
                  } //size

                  leaf bytes-kilobytes {
                    type enumeration {
                      enum bytes;
                      enum kilobytes;
                    }
                  } //bytes-kilobytes

                } //container mbs-contribution

              } //list priority

            } //container priority-mbs-thresholds

          } //container policer-control-override

          container policer-override {
            presence
                "Configure policer overrides";
            list policer {
              key "policer-id";
              description
                  "Configure overrides for the policer";
              leaf policer-id {
                type uint32 {
                  range "1..63";
                }
              } //policer-id

              container cbs {
                description
                    "Specify Cbs override";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs override";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "specify packet byte offset";
                leaf add {
                  type uint32 {
                    range "0..31";
                  }
                } //add

                leaf subtract {
                  type uint32 {
                    range "1..32";
                  }
                } //subtract

              } //container packet-byte-offset

              container percent-rate {
                description
                    "Specify percent rates (CIR and PIR) override";
                leaf pir-percent {
                  type string;
                  description
                      "[0.01..100.00]";
                } //pir-percent

                leaf cir {
                  type string;
                  description
                      "[0.00..100.00]";
                } //cir

              } //container percent-rate

              container rate {
                description
                    "Specify rates (CIR and PIR) override";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-priority-no-cir;
                    enum offered-profile-cir;
                    enum offered-priority-cir;
                    enum offered-total-cir;
                    enum offered-limited-profile-cir;
                    enum offered-profile-capped-cir;
                    enum offered-limited-capped-cir;
                  }
                } //stat-mode

              } //container stat-mode

            } //list policer

          } //container policer-override

          container queue-override {
            presence
                "Apply queue override";
            list queue {
              key "queue-id";
              description
                  "Configure a queue override";
              leaf queue-id {
                type int32 {
                  range "1..32";
                }
              } //queue-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container cbs {
                description
                    "Specify CBS";
                leaf size-in-kbytes {
                  type string;
                  description
                      "Attribute size-in-kbytes for cbs";
                } //size-in-kbytes

              } //container cbs

              container high-prio-only {
                status "obsolete";
                description
                    "Specify high priority only burst size";
                leaf percent {
                  type string;
                  description
                      "[0..100 | default]";
                } //percent

              } //container high-prio-only

              container mbs {
                description
                    "Specify MBS";
                leaf size {
                  type string;
                  description
                      "Attribute size for mbs";
                } //size

                leaf bytes-kilobytes {
                  type enumeration {
                    enum bytes;
                    enum kilobytes;
                  }
                } //bytes-kilobytes

              } //container mbs

              leaf monitor-depth {
                type boolean;
                description
                    "Enable/Disable queue-depth monitoring";
              }

              container parent {
                description
                    "Specify the override weights for the queue within its parental scheduling 
                     context";
                leaf weight {
                  type uint32 {
                    range "0..100";
                  }
                } //weight

                leaf cir-weight {
                  type uint32 {
                    range "0..100";
                  }
                } //cir-weight

              } //container parent

              container percent-rate {
                description
                    "Specify percent rates (CIR and PIR)";
                leaf pir-percent {
                  type string;
                  description
                      "[0.01..100.00]";
                } //pir-percent

                leaf cir {
                  type string;
                  description
                      "[0.00..100.00]";
                } //cir

              } //container percent-rate

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container drop-tail {
                description
                    "Specify drop tail";
                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

            } //list queue

          } //container queue-override

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..3200000000|max] Kbps";
                } //pir-rate

                leaf cir {
                  type string;
                  description
                      "[0..3200000000|sum|max] Kbps";
                } //cir

              } //container rate

            } //list scheduler

          } //container scheduler-override

        } //container ingress

        list ip-tunnel {
          key "name";
          description
              "Configure an IP tunnel";
          leaf name {
            type string;
            description
                "[32 chars max] (must start with a letter)";
          } //name

          container backup-remote-ip {
            description
                "Configure a backup remote IP address";
            leaf ip-address {
              type string;
              description
                  "Attribute ip-address for backup-remote-ip";
            } //ip-address

          } //container backup-remote-ip

          leaf clear-df-bit {
            type boolean;
            description
                "Enable/disable clearing of Do-not-Fragment bit";
          }

          container delivery-service {
            description
                "Configure delivery service";
            leaf service-id {
              type string;
              description
                  "Attribute service-id for delivery-service";
            } //service-id

            leaf name {
              type string;
            } //name

          } //container delivery-service

          container description {
            description
                "Description of the tunnel";
            leaf description-string {
              type string {
                length "1..80";
              }
            } //description-string

          } //container description

          list dest-ip {
            key "ip-address";
            description
                "Configure destination IP address of the tunnel";
            leaf ip-address {
              type string;
              description
                  "Attribute ip-address for dest-ip";
            } //ip-address

          } //list dest-ip

          container dscp {
            description
                "Configure a DSCP value";
            leaf dscp-name {
              type string {
                length "1..32";
              }
              description
                  "Attribute dscp-name for dscp";
            } //dscp-name

          } //container dscp

          container encapsulated-ip-mtu {
            description
                "Configure the tunnel encapsulated IP MTU";
            leaf octets {
              type uint32 {
                range "512..9000";
              }
            } //octets

          } //container encapsulated-ip-mtu

          container gre-header {
            description
                "Configure GRE header in the tunnel";
            leaf send-key {
              type uint32;
            } //send-key

            leaf receive-key {
              type uint32;
            } //receive-key

          } //container gre-header

          container ip-mtu {
            description
                "Configure the tunnel IP MTU";
            leaf octets {
              type uint32 {
                range "512..9000";
              }
            } //octets

          } //container ip-mtu

          container private-tcp-mss-adjust {
            description
                "Configure the TCP maximum segment size (MSS) on private network";
            leaf octets {
              type uint32 {
                range "512..9000";
              }
            } //octets

          } //container private-tcp-mss-adjust

          container public-tcp-mss-adjust {
            description
                "Configure the TCP maximum segment size (MSS) on public network";
            leaf octets {
              type uint32 {
                range "512..9000";
              }
            } //octets

            leaf auto {
              type boolean;
            } //auto

          } //container public-tcp-mss-adjust

          container reassembly {
            description
                "Configure reassembly wait time";
            leaf wait-msecs {
              type int32 {
                range "1..5000";
              }
              description
                  "[1..5000] milli-secs in 100 increments";
            } //wait-msecs

          } //container reassembly

          container remote-ip {
            description
                "Configure remote IP address";
            leaf ip-address {
              type string;
              description
                  "Attribute ip-address for remote-ip";
            } //ip-address

          } //container remote-ip

          leaf shutdown {
            type boolean;
            description
                "Administratively enable/disable tunnel";
          }

          container source {
            description
                "Configure source IP address";
            leaf ip-address {
              type string;
              description
                  "Attribute ip-address for source";
            } //ip-address

          } //container source

          container icmp6-generation {
            description
                "Configure ICMPv6 generation information";
            container packet-too-big {
              description
                  "Configures rate for ICMPv6 packet-too-big messages";
              leaf number {
                type uint32 {
                  range "10..1000";
                }
              } //number

              leaf seconds {
                type uint32 {
                  range "1..60";
                }
              } //seconds

            } //container packet-too-big

          } //container icmp6-generation

        } //list ip-tunnel

        container ipsec-gw {
          description
              "Configure IPSec gateway";
          leaf name {
            type string {
              length "1..32";
            }
            description
                "32 char max";
          } //name

          container client-db {
            description
                "Configure the IPsec client database";
            leaf name {
              type string;
            } //name

            leaf fallback {
              type boolean;
              description
                  "keyword - falling back to the default IPsec tunnel request authentication 
                   policy if IPsec database client matching has failed";
            } //fallback

            leaf no-fallback {
              type boolean;
              description
                  "keyword - do not falling back to the default IPsec tunnel request 
                   authentication policy if IPsec database client matching has failed";
            } //no-fallback

          } //container client-db

          container default-secure-service {
            description
                "Configure default secure service";
            leaf service-id {
              type string;
              description
                  "Attribute service-id for default-secure-service";
            } //service-id

            leaf default-secure-service-string {
              type string {
              }
            } //default-secure-service-string

            leaf default-secure-service-string-2 {
              type string {
                length "1..32";
              }
            } //default-secure-service-string-2

            leaf name {
              type string;
            } //name

            leaf interface {
              type string {
                length "1..32";
              }
              description
                  "[32 chars max] (must start with a letter)";
            } //interface

          } //container default-secure-service

          container default-tunnel-template {
            description
                "Configure default tunnel policy template for the gateway";
            leaf ipsec-template-identifier {
              type uint32 {
                range "1..2048";
              }
            } //ipsec-template-identifier

          } //container default-tunnel-template

          container ike-policy {
            description
                "Configure IKE policy for the gateway";
            leaf ike-policy-id {
              type uint32 {
                range "1..2048";
              }
            } //ike-policy-id

          } //container ike-policy

          container local-gateway-address {
            description
                "Configure ipsec-gateway local address";
            leaf ip-address {
              type string;
              description
                  "Attribute ip-address for local-gateway-address";
            } //ip-address

          } //container local-gateway-address

          container local-id {
            description
                "Configure local ID type for CA profile";
            leaf type {
              type enumeration {
                enum ipv4;
                enum fqdn;
                enum ipv6;
              }
              description
                  "Attribute type for local-id";
            } //type

            leaf value {
              type string {
                length "1..255";
              }
            } //value

          } //container local-id

          container max-history-esp-key-records {
            description
                "Configure the maximum number of historical ESP keys which can be recorded by 
                 the system";
            leaf max-history-esp-key-records-id {
              type uint32 {
                range "1..48";
              }
            } //max-history-esp-key-records-id

          } //container max-history-esp-key-records

          container max-history-ike-key-records {
            description
                "Configure the maximum number of historical IKE keys which can be recorded by 
                 the system";
            leaf max-history-ike-key-records-id {
              type uint32 {
                range "1..3";
              }
            } //max-history-ike-key-records-id

          } //container max-history-ike-key-records

          container pre-shared-key {
            description
                "Configure pre-shared-key for dynamic-keying";
            leaf key {
              type string {
                length "1..500";
              }
              description
                  "64 chars max";
            } //key

            leaf hash-hash2-custom {
              type enumeration {
                enum hash;
                enum hash2;
                enum custom;
              }
              description
                  "keyword - hashing scheme used in the hashed key";
            } //hash-hash2-custom

          } //container pre-shared-key

          container radius-accounting-policy {
            description
                "Configure radius accounting policy";
            leaf policy-name {
              type string;
            } //policy-name

          } //container radius-accounting-policy

          container radius-authentication-policy {
            description
                "Configure IPsec radius authentication-policy";
            leaf name {
              type string;
            } //name

          } //container radius-authentication-policy

          leaf shutdown {
            type boolean;
            description
                "Shutdown this ipsec-gateway";
          }

          container ts-negotiation {
            description
                "Configure traffic-selector negotiation parameters";
            leaf ts-list {
              type string;
            } //ts-list

          } //container ts-negotiation

          container cert {
            description
                "Configure certificate parameters";
            container cert {
              status "obsolete";
              description
                  "Configure cert with local file URL";
              leaf filename {
                type string {
                  length "1..95";
                }
              } //filename

            } //container cert

            container cert-profile {
              description
                  "Configure certificate profile name";
              leaf name {
                type string;
              } //name

            } //container cert-profile

            container key {
              status "obsolete";
              description
                  "Configure a key with the CA profile";
              leaf filename {
                type string {
                  length "1..95";
                }
              } //filename

            } //container key

            list trust-anchor {
              key "ca-profile-name";
              status "obsolete";
              description
                  "Configure trust anchor with a CA profile";
              leaf ca-profile-name {
                type string {
                  length "1..32";
                }
              } //ca-profile-name

            } //list trust-anchor

            container trust-anchor-profile {
              description
                  "Configure Trust Anchor profile";
              leaf name {
                type string;
              } //name

            } //container trust-anchor-profile

            container status-verify {
              description
                  "Configure certificate status verification parameters";
              container default-result {
                description
                    "Configure default result of certificate status verification";
                leaf revoked-good {
                  type enumeration {
                    enum revoked;
                    enum good;
                  }
                } //revoked-good

              } //container default-result

              container primary {
                description
                    "Configure primary and secondary certificate status verification method";
                leaf primary {
                  type enumeration {
                    enum ocsp;
                    enum crl;
                  }
                  default "crl";
                  description
                      "ocsp|crl - default: crl";
                } //primary

                leaf secondary {
                  type enumeration {
                    enum ocsp;
                    enum crl;
                    enum none;
                  }
                  default "none";
                  description
                      "ocsp|crl|none - default: none";
                } //secondary

              } //container primary

              container secondary {
                status "obsolete";
                description
                    "Configure secondary certificate status verification method";
                leaf ocsp-crl {
                  type enumeration {
                    enum ocsp;
                    enum crl;
                  }
                } //ocsp-crl

              } //container secondary

            } //container status-verify

          } //container cert

          container dhcp {
            presence
                "Configure DHCP server information";
            container gi-address {
              description
                  "Configure gateway interface address";
              leaf ip-address {
                type inet:ip-address;
              } //ip-address

            } //container gi-address

            leaf send-release {
              type boolean;
              description
                  "Enable/disable sending of DHCP release message";
            }

            container server {
              description
                  "Configure DHCP server information";
              leaf-list ip-address {
                type inet:ip-address;
                max-elements 8;
              } //ip-address

              leaf router {
                type string {
                  length "1..32";
                }
                default "Base";
                description
                    "Attribute router-instance for server";
              } //router

              leaf service-name {
                type string;
              } //service-name

            } //container server

            leaf shutdown {
              type boolean;
              description
                  "Shutdown this ipsec-gateway DHCP configuration";
            }

          } //container dhcp

          container dhcp6 {
            presence
                "Configure DHCP6 server information";
            container link-address {
              description
                  "Configure gateway interface address";
              leaf ipv6-address {
                type inet:ipv6-address;
                description
                    "Attribute ipv6-address for link-address";
              } //ipv6-address

            } //container link-address

            leaf send-release {
              type boolean;
              description
                  "Enable/disable sending of DHCP6 release message";
            }

            container server {
              description
                  "Configure DHCP6 server information";
              leaf-list ipv6-address {
                type inet:ipv6-address;
                max-elements 8;
                description
                    "Attribute ipv6-address for server";
              } //ipv6-address

              leaf router {
                type string {
                  length "1..32";
                }
                default "Base";
                description
                    "Attribute router-instance for server";
              } //router

              leaf service-name {
                type string;
              } //service-name

            } //container server

            leaf shutdown {
              type boolean;
              description
                  "Shutdown this ipsec-gateway DHCP6 configuration";
            }

          } //container dhcp6

          container local-address-assignment {
            presence
                "Configure local address assignment information";
            leaf shutdown {
              type boolean;
              description
                  "Shutdown local-address-assignment configuration";
            }

            container ipv4 {
              description
                  "Configure local address assignment IPv4 information";
              container address-source {
                description
                    "Configure DHCP server/pool information";
                leaf router {
                  type string {
                    length "1..32";
                  }
                  default "Base";
                } //router

                leaf service-name {
                  type string;
                } //service-name

                leaf dhcp-server {
                  type string {
                    length "1..32";
                  }
                } //dhcp-server

                leaf pool {
                  type string {
                    length "1..32";
                  }
                } //pool

                leaf secondary-pool {
                  type string {
                    length "1..32";
                  }
                } //secondary-pool

              } //container address-source

            } //container ipv4

            container ipv6 {
              description
                  "Configure local address assignment IPv6 information";
              container address-source {
                description
                    "Configure DHCP server/pool information";
                leaf router {
                  type string {
                    length "1..32";
                  }
                  default "Base";
                } //router

                leaf service-name {
                  type string;
                } //service-name

                leaf dhcp-server {
                  type string {
                    length "1..32";
                  }
                } //dhcp-server

                leaf pool {
                  type string {
                    length "1..32";
                  }
                } //pool

              } //container address-source

            } //container ipv6

          } //container local-address-assignment

        } //container ipsec-gw

        list ipsec-tunnel {
          key "ipsec-tunnel-name";
          description
              "Configure IPsec tunnel";
          leaf ipsec-tunnel-name {
            type string {
              length "1..32";
            }
            description
                "[32 chars max] (must start with a letter)";
          } //ipsec-tunnel-name

          leaf bfd-designate {
            type boolean;
            description
                "Configure BFD designation for the tunnel";
          }

          container bfd-enable {
            description
                "Configure BFD parameter";
            leaf service {
              type string;
              description
                  "Attribute service-id for bfd-enable";
            } //service

            leaf service-name {
              type string;
            } //service-name

            leaf interface {
              type string {
                length "1..32";
              }
            } //interface

            leaf dst-ip {
              type inet:ip-address;
              description
                  "ipv4-address - a.b.c.d";
            } //dst-ip

          } //container bfd-enable

          leaf clear-df-bit {
            type boolean;
            description
                "Enable/disable clearing of Do-not-Fragment bit";
          }

          container description {
            description
                "Configure IPsec tunnel description";
            leaf description-string {
              type string {
                length "1..80";
              }
            } //description-string

          } //container description

          list dest-ip {
            key "ip-address";
            description
                "Configure destination IP address of the tunnel";
            leaf ip-address {
              type string;
              description
                  "Attribute ip-address for dest-ip";
            } //ip-address

          } //list dest-ip

          container encapsulated-ip-mtu {
            description
                "Configure the interface encapsulated IP MTU";
            leaf octets {
              type uint32 {
                range "512..9000";
              }
            } //octets

          } //container encapsulated-ip-mtu

          container ip-mtu {
            description
                "Configure the interface IP MTU";
            leaf octets {
              type uint32 {
                range "512..9000";
              }
            } //octets

          } //container ip-mtu

          container local-gateway-address {
            description
                "Configure local gateway address";
            leaf ip-address {
              type string;
              description
                  "Attribute ip-address for local-gateway-address";
            } //ip-address

            leaf peer {
              type string;
            } //peer

            leaf delivery-service {
              type string;
              description
                  "Attribute service-id for local-gateway-address";
            } //delivery-service

            leaf delivery-service-name {
              type string;
            } //delivery-service-name

          } //container local-gateway-address

          container max-history-esp-key-records {
            description
                "Configure the maximum number of historical ESP keys which can be recorded by 
                 the system";
            leaf max-history-esp-key-records-id {
              type uint32 {
                range "1..48";
              }
            } //max-history-esp-key-records-id

          } //container max-history-esp-key-records

          container max-history-ike-key-records {
            description
                "Configure the maximum number of historical IKE keys which can be recorded by 
                 the system";
            leaf max-history-ike-key-records-id {
              type uint32 {
                range "1..3";
              }
            } //max-history-ike-key-records-id

          } //container max-history-ike-key-records

          container private-tcp-mss-adjust {
            description
                "Configure the TCP MSS on private network";
            leaf octets {
              type uint32 {
                range "512..9000";
              }
            } //octets

          } //container private-tcp-mss-adjust

          container public-tcp-mss-adjust {
            description
                "Configure the TCP MSS on public network";
            leaf octets {
              type uint32 {
                range "512..9000";
              }
            } //octets

            leaf auto {
              type boolean;
            } //auto

          } //container public-tcp-mss-adjust

          container replay-window {
            description
                "Configure Anti replay window for the tunnel";
            leaf replay-window-size {
              type enumeration {
                enum 32;
                enum 64;
                enum 128;
                enum 256;
                enum 512;
              }
            } //replay-window-size

          } //container replay-window

          container security-policy {
            description
                "Configure security policy id for the tunnel";
            leaf security-policy-id {
              type uint32;
              description
                  "Attribute security-policy-id for security-policy";
            } //security-policy-id

            leaf strict-match {
              type boolean;
            } //strict-match

          } //container security-policy

          leaf shutdown {
            type boolean;
            description
                "Administratively enable/disable the IPsec tunnel";
          }

          container dynamic-keying {
            presence
                "Configure dynamic keying for the IPsec tunnel";
            leaf auto-establish {
              type boolean;
              description
                  "Enable/Disable auto-establish";
            }

            container ike-policy {
              description
                  "Configure IKE policy for the dynamic keying";
              leaf ike-policy-id {
                type uint32 {
                  range "1..2048";
                }
              } //ike-policy-id

            } //container ike-policy

            container local-id {
              description
                  "Configure local ID type for dynamic keying";
              leaf type {
                type enumeration {
                  enum ipv4;
                  enum fqdn;
                  enum ipv6;
                }
                description
                    "Attribute type for local-id";
              } //type

              leaf value {
                type string {
                  length "1..255";
                }
              } //value

            } //container local-id

            container pre-shared-key {
              description
                  "Configure key for dynamic keying";
              leaf key {
                type string {
                  length "1..500";
                }
                description
                    "64 chars max";
              } //key

              leaf hash-hash2-custom {
                type enumeration {
                  enum hash;
                  enum hash2;
                  enum custom;
                }
                description
                    "keyword - hashing scheme used in the hashed key";
              } //hash-hash2-custom

            } //container pre-shared-key

            container transform {
              description
                  "Configure transforms for dynamic keying";
              leaf-list transform-id {
                type uint32 {
                  range "1..2048";
                }
                max-elements 4;
                description
                    "[1..2048]";
              } //transform-id

            } //container transform

            container cert {
              description
                  "Configure certificate parameters";
              container cert {
                status "obsolete";
                description
                    "Configure cert with local file URL";
                leaf filename {
                  type string {
                    length "1..95";
                  }
                } //filename

              } //container cert

              container cert-profile {
                description
                    "Configure certificate profile name";
                leaf name {
                  type string;
                } //name

              } //container cert-profile

              container key {
                status "obsolete";
                description
                    "Configure a key with the CA profile";
                leaf filename {
                  type string {
                    length "1..95";
                  }
                } //filename

              } //container key

              list trust-anchor {
                key "ca-profile-name";
                status "obsolete";
                description
                    "Configure trust anchor with a CA profile";
                leaf ca-profile-name {
                  type string {
                    length "1..32";
                  }
                } //ca-profile-name

              } //list trust-anchor

              container trust-anchor-profile {
                description
                    "Configure Trust Anchor profile";
                leaf name {
                  type string;
                } //name

              } //container trust-anchor-profile

              container status-verify {
                description
                    "Configure certificate status verification parameters";
                container default-result {
                  description
                      "Configure default result of certificate status verification";
                  leaf revoked-good {
                    type enumeration {
                      enum revoked;
                      enum good;
                    }
                  } //revoked-good

                } //container default-result

                container primary {
                  description
                      "Configure primary and secondary certificate status verification methods";
                  leaf primary {
                    type enumeration {
                      enum ocsp;
                      enum crl;
                    }
                    default "crl";
                    description
                        "ocsp|crl - default: crl";
                  } //primary

                  leaf secondary {
                    type enumeration {
                      enum ocsp;
                      enum crl;
                      enum none;
                    }
                    default "none";
                    description
                        "ocsp|crl|none - default: none";
                  } //secondary

                } //container primary

                container secondary {
                  status "obsolete";
                  description
                      "Configure secondary certificate status verification method";
                  leaf ocsp-crl {
                    type enumeration {
                      enum ocsp;
                      enum crl;
                    }
                  } //ocsp-crl

                } //container secondary

              } //container status-verify

            } //container cert

          } //container dynamic-keying

          container icmp6-generation {
            description
                "Configure ICMPv6 generation information";
            container packet-too-big {
              status "obsolete";
              description
                  "Configures the rate for ICMPv6 packet-too-big messages";
              leaf number {
                type uint32 {
                  range "10..1000";
                }
              } //number

              leaf seconds {
                type uint32 {
                  range "1..60";
                }
              } //seconds

            } //container packet-too-big

            container pkt-too-big {
              presence
                  "Enable/disable the generation of the ICMPv6 packet too big messages";
              container interval {
                description
                    "Configure the maximum interval that the ICMPv6 messages can be sent";
                leaf seconds {
                  type uint32 {
                    range "1..60";
                  }
                  default 10;
                  description
                      "[1..60] - Default: 10";
                } //seconds

              } //container interval

              container message-count {
                description
                    "Configure the maximum number of ICMPv6 messages that can be sent during the 
                     period specified by 'interval'";
                leaf count {
                  type uint32 {
                    range "10..1000";
                  }
                  default 100;
                  description
                      "[10..1000] - Default: 100";
                } //count

              } //container message-count

            } //container pkt-too-big

          } //container icmp6-generation

          container manual-keying {
            presence
                "Configure manual keying for the IPsec tunnel";
            list security-association {
              key "security-entry-id direction";
              description
                  "Configure Security Association for manual keying";
              leaf security-entry-id {
                type uint32 {
                  range "1..16";
                }
              } //security-entry-id

              leaf authentication-key {
                type string;
                description
                    "none or [0x0..0xFFFFFFFF...(max 128 hex nibbles)]";
              } //authentication-key

              leaf encryption-key {
                type string;
                description
                    "none or [0x0..0xFFFFFFFF...(max 64 hex nibbles)]";
              } //encryption-key

              leaf spi {
                type uint32 {
                  range "256..16383";
                }
              } //spi

              leaf transform {
                type uint32 {
                  range "1..2048";
                }
              } //transform

              leaf direction {
                type enumeration {
                  enum inbound;
                  enum outbound;
                }
              } //direction

            } //list security-association

          } //container manual-keying

        } //list ipsec-tunnel

        container l2tpv3-session {
          description
              "Configure L2TPv3 session parameters";
          container pw-type {
            description
                "Configure pseudo-wire type";
            leaf ethernet {
              type boolean;
            } //ethernet

            leaf ethernet-vlan {
              type int32 {
                range "0..4095";
              }
            } //ethernet-vlan

          } //container pw-type

          container router {
            description
                "Configure L2TPv3 session router information";
            leaf router-instance {
              type string {
                length "1..32";
              }
              default "Base";
              description
                  "Attribute router-instance for router";
            } //router-instance

            leaf group {
              type string {
                length "1..32";
              }
            } //group

            leaf service-name {
              type string;
            } //service-name

          } //container router

          leaf shutdown {
            type boolean;
            description
                "Configure adminstrative state of the entry";
          }

          container vc-id {
            description
                "Configure VC identifier";
            leaf vc-id {
              type uint32 {
                range "1..4294967295";
              }
            } //vc-id

          } //container vc-id

        } //container l2tpv3-session

        container static-host {
          description
              "Configure a static host on this SAP";
          leaf ip {
            type inet:ip-address;
          } //ip

          leaf mac {
            type string;
            description
                "xx:xx:xx:xx:xx:xx or xx-xx-xx-xx-xx-xx (cannot be all zeros)";
          } //mac

          leaf all {
            type boolean;
          } //all

          leaf force {
            type boolean;
            description
                "keyword - force removal";
          } //force

          container ancp-string {
            description
                "Configure the ANCP string";
            leaf ancp-string {
              type string {
                length "1..63";
              }
            } //ancp-string

          } //container ancp-string

          container app-profile {
            description
                "Configure the application profile name";
            leaf app-profile-name {
              type string {
                length "1..32";
              }
            } //app-profile-name

          } //container app-profile

          container inter-dest-id {
            description
                "Configure the intermediate destination id";
            leaf intermediate-destination-id {
              type string {
                length "1..32";
              }
            } //intermediate-destination-id

          } //container inter-dest-id

          leaf shutdown {
            type boolean;
            description
                "Enable/disable the static host";
          }

          container sla-profile {
            description
                "Configure the SLA profile name";
            leaf sla-profile-name {
              type string {
                length "1..32";
              }
            } //sla-profile-name

          } //container sla-profile

          container sub-profile {
            description
                "Configure the sub-profile name";
            leaf sub-profile-name {
              type string {
                length "1..32";
              }
            } //sub-profile-name

          } //container sub-profile

          container subscriber {
            description
                "Configure the subscriber identification";
            leaf sub-ident {
              type string {
                length "1..32";
              }
            } //sub-ident

          } //container subscriber

          leaf subscriber-sap-id {
            type boolean;
            description
                "Enable/disable using the SAP id as subscriber id";
          }

        } //container static-host

      } //list sap

      list spoke-sdp {
        key "sdp-id-vc-id";
        description
            "Provision a spoke SDP binding";
        leaf sdp-id-vc-id {
          type string;
          description
              "sdp-id - [1..32767] 
               vc-id - [1..4294967295]";
        } //sdp-id-vc-id

        leaf vc-type {
          type enumeration {
            enum ether;
            enum ipipe;
          }
        } //vc-type

        container aarp {
          description
              "Configure AARP instance id";
          leaf aarpId {
            type uint32 {
              range "1..65535";
            }
          } //aarpId

          leaf type {
            type enumeration {
              enum dual-homed;
              enum dual-homed-secondary;
            }
          } //type

        } //container aarp

        container accounting-policy {
          description
              "Configure accounting-policy to be used";
          leaf acct-policy-id {
            type uint64 {
              range "1..99";
            }
          } //acct-policy-id

        } //container accounting-policy

        container app-profile {
          description
              "Configure the application profile name";
          leaf app-profile-name {
            type string {
              length "1..32";
            }
          } //app-profile-name

        } //container app-profile

        leaf bfd-enable {
          type boolean;
          description
              "Enable/disable BFD";
        }

        container bfd-template {
          description
              "Configure BFD template";
          leaf bfd-template-string {
            type string {
            }
          } //bfd-template-string

        } //container bfd-template

        leaf collect-stats {
          type boolean;
          description
              "Enable/disable statistics collection";
        }

        leaf control-word {
          type boolean;
          description
              "Enable/disable setting the CW bit in the label message";
        }

        container cpu-protection {
          description
              "Configure CPU protection";
          leaf policy-id {
            type uint32 {
              range "1..255";
            }
            default 255;
            description
                "[1..255] - Default: 255";
          } //policy-id

          leaf mac-monitoring {
            type boolean;
            description
                "keyword - enable MAC monitoring";
          } //mac-monitoring

          leaf eth-cfm-monitoring {
            type boolean;
            description
                "keyword - enable Ethernet Connectivity Fault Management monitoring";
          } //eth-cfm-monitoring

          leaf aggregate {
            type boolean;
            description
                "keyword - apply the rate limit to the sum of the per peer packet rates";
          } //aggregate

          leaf car {
            type boolean;
            description
                "keyword - Committed Access Rate - ignore Eth-CFM packets when enforcing 
                 overall-rate";
          } //car

          leaf ip-src-monitoring {
            type boolean;
            description
                "keyword - enable monitoring per IP source address";
          } //ip-src-monitoring

        } //container cpu-protection

        container description {
          description
              "Set description for spoke-sdp";
          leaf description-string {
            type string {
              length "1..80";
            }
            description
                "80 char max";
          } //description-string

        } //container description

        leaf entropy-label {
          type boolean;
          description
              "Enable/disable use of entropy-label";
        }

        container hash-label {
          description
              "Enable/disable use of hash-label";
          leaf signal-capability {
            type boolean;
          } //signal-capability

        } //container hash-label

        leaf shutdown {
          type boolean;
          description
              "Administratively enable/disable the spoke SDP binding";
        }

        container transit-policy {
          description
              "Configure transit policy id";
          leaf ip {
            type uint32 {
              range "1..65535";
            }
          } //ip

          leaf prefix {
            type uint32 {
              range "1..65535";
            }
          } //prefix

        } //container transit-policy

        container control-channel-status {
          description
              "Configure control channel status information";
          leaf acknowledgment {
            type boolean;
            description
                "Enable/disable acknowledgment";
          }

          container refresh-timer {
            description
                "Configure refresh timer";
            leaf seconds {
              type uint32 {
                range "10..65535";
              }
            } //seconds

          } //container refresh-timer

          container request-timer {
            description
                "Configure request-timer for the control channel status";
            leaf request-timer-secs {
              type uint32 {
                range "10..65535";
              }
            } //request-timer-secs

            leaf retry-timer {
              type uint32 {
                range "3..60";
              }
            } //retry-timer

            leaf timeout-multiplier {
              type uint32 {
                range "3..15";
              }
            } //timeout-multiplier

          } //container request-timer

          leaf shutdown {
            type boolean;
            description
                "Administratively enable/disable the control channel status";
          }

        } //container control-channel-status

        container egress {
          description
              "Spoke SDP egress configuration";
          container filter {
            description
                "Apply egress filter";
            leaf ip {
              type string;
              description
                  "[1..65535]|<name:64 char max>";
            } //ip

            leaf ipv6 {
              type string;
              description
                  "[1..65535]|<name:64 char max>";
            } //ipv6

          } //container filter

          list qos {
            key "network-policy-id";
            description
                "Configure egress qos";
            leaf network-policy-id {
              type uint32 {
                range "1..65535";
              }
            } //network-policy-id

            leaf port-redirect-group {
              type string {
                length "1..32";
              }
            } //port-redirect-group

            leaf instance {
              type uint16 {
                range "1..65535";
              }
            } //instance

          } //list qos

          list vc-label {
            key "egress-vc-label";
            description
                "Configure egress VC label";
            leaf egress-vc-label {
              type int32 {
                range "16..1048575";
              }
            } //egress-vc-label

          } //list vc-label

        } //container egress

        container eth-cfm {
          description
              "Configure CFM parameters";
          leaf collect-lmm-stats {
            type boolean;
            description
                "Enable/Disable the collection of statistics for OAM-PM Loss Measurement 
                 Message (LMM) tests";
          }

          container squelch-ingress-levels {
            description
                "Configure the level(s) of the ETH-CFM PDUs that will be silently discarded";
            leaf t0 {
              type boolean;
              description
                  "[0..7]";
            } //t0

            leaf t1 {
              type boolean;
            } //t1

            leaf t2 {
              type boolean;
            } //t2

            leaf t3 {
              type boolean;
            } //t3

            leaf t4 {
              type boolean;
            } //t4

            leaf t5 {
              type boolean;
            } //t5

            leaf t6 {
              type boolean;
            } //t6

            leaf t7 {
              type boolean;
            } //t7

          } //container squelch-ingress-levels

          container collect-lmm-fc-stats {
            description
                "Configure the collection of Forwarding Class (FC) aware statistics for OAM-PM 
                 Loss Measurement Message (LMM) tests";
            container fc {
              description
                  "Configure Forwarding Class (FC) counters without regard for profile";
              leaf-list fc-name {
                type enumeration {
                  enum be;
                  enum l2;
                  enum af;
                  enum l1;
                  enum h2;
                  enum ef;
                  enum h1;
                  enum nc;
                }
                max-elements 8;
              } //fc-name

            } //container fc

            container fc-in-profile {
              description
                  "Configure only in profile Forwarding Class (FC) counters";
              leaf-list fc-name {
                type enumeration {
                  enum be;
                  enum l2;
                  enum af;
                  enum l1;
                  enum h2;
                  enum ef;
                  enum h1;
                  enum nc;
                }
                max-elements 8;
              } //fc-name

            } //container fc-in-profile

          } //container collect-lmm-fc-stats

          list mep {
            key "mep-id domain association";
            description
                "Configure a CFM Maintenance Endpoint";
            leaf mep-id {
              type int16 {
                range "1..8191";
              }
            } //mep-id

            leaf domain {
              type uint32 {
                range "1..4294967295";
              }
            } //domain

            leaf association {
              type uint32 {
                range "1..4294967295";
              }
            } //association

            leaf direction {
              type enumeration {
                enum up;
                enum down;
              }
              description
                  "keywords";
            } //direction

            leaf ccm-enable {
              type boolean;
              description
                  "Enable/Disable Generation of CCM messages";
            }

            container ccm-ltm-priority {
              description
                  "Configure the priority of CCM and LTM messages";
              leaf priority {
                type uint16 {
                  range "0..7";
                }
                description
                    "[0..7] - Default highest priority on bridge-port";
              } //priority

            } //container ccm-ltm-priority

            container ccm-padding-size {
              description
                  "Insert additional padding in the CCM packets";
              leaf ccm-padding {
                type uint32 {
                  range "3..1500";
                }
                description
                    "3..1500 octets";
              } //ccm-padding

            } //container ccm-padding-size

            container description {
              description
                  "Add/remove a text description for the MEP";
              leaf description-string {
                type string {
                }
                description
                    "[80 chars max]";
              } //description-string

            } //container description

            container fault-propagation-enable {
              description
                  "Configure the Fault Propagation for the MEP";
              leaf use-if-tlv-suspend-ccm {
                type enumeration {
                  enum use-if-tlv;
                  enum suspend-ccm;
                }
                description
                    "keywords - use interface TLV, or suspend Continuity Check Messages";
              } //use-if-tlv-suspend-ccm

            } //container fault-propagation-enable

            container low-priority-defect {
              description
                  "Configure the low-priority defect for the MEP";
              leaf allDef-macRemErrXcon-remErrXcon-errXcon-xcon-noXcon {
                type enumeration {
                  enum allDef;
                  enum macRemErrXcon;
                  enum remErrXcon;
                  enum errXcon;
                  enum xcon;
                  enum noXcon;
                }
                description
                    "keywords";
              } //allDef-macRemErrXcon-remErrXcon-errXcon-xcon-noXcon

            } //container low-priority-defect

            container mac-address {
              description
                  "Configure the mac-address for the MEP";
              leaf mac-address {
                type yang:mac-address;
              } //mac-address

            } //container mac-address

            container one-way-delay-threshold {
              description
                  "Configure the one-way-delay test threshold";
              leaf seconds {
                type uint32 {
                  range "0..600";
                }
                default 3;
                description
                    "[0..600] Default: 3";
              } //seconds

            } //container one-way-delay-threshold

            leaf shutdown {
              type boolean;
              description
                  "Administratively enable/disable the MEP";
            }

            container ais-enable {
              presence
                  "Configure the generation and reception of Alarm Indication Signal (AIS) 
                   message parameters";
              leaf fake-node {
                type boolean;
              }

              leaf interface-support-enable {
                type boolean;
                description
                    "Enable/disable the generation of AIS PDUs based on the associated endpoint 
                     state";
              }

            } //container ais-enable

            container alarm-notification {
              description
                  "Configure the MEP alarm notification parameters";
              container fng-alarm-time {
                description
                    "Configure the Fault Notification Generation (FNG) alarm time";
                leaf time {
                  type enumeration {
                    enum 0;
                    enum 250;
                    enum 500;
                    enum 1000;
                  }
                  default 0;
                  description
                      "[0,250,500,1000] centi-seconds - Default: 0";
                } //time

              } //container fng-alarm-time

              container fng-reset-time {
                description
                    "Configure the Fault Notification Generation (FNG) reset time";
                leaf time {
                  type enumeration {
                    enum 0;
                    enum 250;
                    enum 500;
                    enum 1000;
                  }
                  default 0;
                  description
                      "[0,250,500,1000] centi-seconds - Default: 0";
                } //time

              } //container fng-reset-time

            } //container alarm-notification

            container csf-enable {
              presence
                  "Configure the reception of Client Signal Fail (CSF) message parameters";
              container multiplier {
                description
                    "Configure the multiplier used for timing out CSF";
                leaf multiplier-value {
                  type string;
                  description
                      "[0.0|2.0 .. 30.0] - Default: 3.5";
                } //multiplier-value

              } //container multiplier

            } //container csf-enable

            container eth-test-enable {
              presence
                  "Enable/Disable eth-test functionality on MEP";
              container bit-error-threshold {
                description
                    "Configure the bit error trap threshold";
                leaf bit-errors {
                  type uint32 {
                    range "0..11840";
                  }
                  default 1;
                  description
                      "[0..11840] Default: 1";
                } //bit-errors

              } //container bit-error-threshold

              container test-pattern {
                description
                    "Configure the test pattern for eth-test frames";
                leaf all-zeros-all-ones {
                  type enumeration {
                    enum all-zeros;
                    enum all-ones;
                  }
                  default "all-zeros";
                  description
                      "keywords - Test pattern - default: all-zeros";
                } //all-zeros-all-ones

                leaf crc-enable {
                  type boolean;
                  description
                      "keyword - Generate CRC checksum";
                } //crc-enable

              } //container test-pattern

            } //container eth-test-enable

            container grace {
              description
                  "Configure the generation and reception of grace period parameters";
              container eth-ed {
                description
                    "Configure the generation and reception of eth-ed grace period parameters";
                container max-rx-defect-window {
                  description
                      "Configure/Disable an upper maximum defect window length; when disabled the 
                       advertised value from the peer will be used; when enabled the lower of the 
                       configured value or the advertised value from the peer will be used";
                  leaf seconds {
                    type uint32 {
                      range "1..86400";
                    }
                    description
                        "[1..86400] - Default: no max-rx-defect-window";
                  } //seconds

                } //container max-rx-defect-window

                container priority {
                  description
                      "Configure/Disable the transmission priority value for ETH-ED PDUs; when 
                       disabled the priority value of ccm-ltm-priority associated with this MEP will 
                       be used";
                  leaf priority {
                    type int32 {
                      range "0..7";
                    }
                    default 0;
                    description
                        "[0..7] - Default: no priority";
                  } //priority

                } //container priority

                leaf rx-eth-ed {
                  type boolean;
                  description
                      "Enable/Disable the receiving and processing of ETH-ED PDUs";
                }

                leaf tx-eth-ed {
                  type boolean;
                  description
                      "Enable/Disable the transmission of ETH-ED PDUs";
                }

              } //container eth-ed

              container eth-vsm-grace {
                description
                    "Configure the generation and reception of sros vendor specific message (vsm) 
                     grace period parameters";
                leaf rx-eth-vsm-grace {
                  type boolean;
                  description
                      "Enable/Disable the receiving and processing of vendor specific message (vsm) 
                       grace period notifications";
                }

                leaf tx-eth-vsm-grace {
                  type boolean;
                  description
                      "Enable/Disable the transmission of vsm grace period notifications";
                }

              } //container eth-vsm-grace

            } //container grace

          } //list mep

        } //container eth-cfm

        container ingress {
          description
              "Spoke SDP ingress configuration";
          container filter {
            description
                "Apply ingress filter";
            leaf ip {
              type string;
              description
                  "[1..65535]|<name:64 char max>";
            } //ip

            leaf ipv6 {
              type string;
              description
                  "[1..65535]|<name:64 char max>";
            } //ipv6

          } //container filter

          leaf flowspec {
            type boolean;
            status "obsolete";
            description
                "Enable/disable IPv4 Flowspec on the spoke-sdp";
          }

          leaf flowspec-ipv6 {
            type boolean;
            status "obsolete";
            description
                "Enable/disable IPv6 Flowspec on the spoke-sdp";
          }

          list qos {
            key "network-policy-id";
            description
                "Configure ingress qos";
            leaf network-policy-id {
              type uint32 {
                range "1..65535";
              }
            } //network-policy-id

            leaf fp-redirect-group {
              type string {
                length "1..32";
              }
            } //fp-redirect-group

            leaf instance {
              type uint16 {
                range "1..65535";
              }
            } //instance

          } //list qos

          list vc-label {
            key "ingress-vc-label";
            description
                "Configure ingress VC label";
            leaf ingress-vc-label {
              type string;
              description
                  "Attribute ingress-vc-label for vc-label";
            } //ingress-vc-label

          } //list vc-label

        } //container ingress

        container pw-path-id {
          presence
              "Configure PW path identifier information";
          container agi {
            description
                "Configure Attachment Group Identifier";
            leaf attachment-group-identifier {
              type string {
              }
              description
                  "<0..4294967295>:<0..4294967295>";
            } //attachment-group-identifier

          } //container agi

          container saii-type2 {
            description
                "Configure Source Attachment Individual Identifier (SAII)";
            leaf global-id-node-id-ac-id {
              type string {
              }
              description
                  "Attribute global-id:node-id:ac-id for saii-type2";
            } //global-id-node-id-ac-id

          } //container saii-type2

          container taii-type2 {
            description
                "Configure Target Attachment Individual Identifier (TAII)";
            leaf global-id-node-id-ac-id {
              type string {
              }
              description
                  "Attribute global-id:node-id:ac-id for taii-type2";
            } //global-id-node-id-ac-id

          } //container taii-type2

        } //container pw-path-id

      } //list spoke-sdp

      container urpf-check {
        presence
            "Enables/Configures unicast RPF check for an interface";
        leaf ignore-default {
          type boolean;
          description
              "Enable/Disable default route when performing a uRPF check.";
        }

        container mode {
          description
              "Configure unicast RPF check mode";
          leaf strict-loose-strict-no-ecmp {
            type enumeration {
              enum strict;
              enum loose;
              enum strict-no-ecmp;
            }
            description
                "keywords";
          } //strict-loose-strict-no-ecmp

        } //container mode

      } //container urpf-check

      container vpls {
        description
            "Configure vpls service";
        leaf service-name {
          type string;
        } //service-name

        container evpn-tunnel {
          description
              "Configure interface as VPLS EVPN tunnel";
          leaf ipv6-gateway-address {
            type enumeration {
              enum ip;
              enum mac;
            }
          } //ipv6-gateway-address

        } //container evpn-tunnel

        container egress {
          description
              "Configure vpls egress parameters";
          container reclassify-using-qos {
            description
                "Apply egress QoS policy";
            leaf policy-id {
              type string;
              description
                  "[1..65535]|<name:64 char max>";
            } //policy-id

          } //container reclassify-using-qos

          container v4-routed-override-filter {
            description
                "Configure service egress override filter";
            leaf ip-filter-id {
              type string;
              description
                  "[1..65535]|<name:64 char max>";
            } //ip-filter-id

          } //container v4-routed-override-filter

          container v6-routed-override-filter {
            description
                "Configure service egress override filter";
            leaf ipv6-filter-id {
              type string;
              description
                  "[1..65535]|<name:64 char max>";
            } //ipv6-filter-id

          } //container v6-routed-override-filter

        } //container egress

        container ingress {
          description
              "Configure vpls ingress parameters";
          container v4-routed-override-filter {
            description
                "Configure service ingress override filter";
            leaf ip-filter-id {
              type string;
              description
                  "[1..65535]|<name:64 char max>";
            } //ip-filter-id

          } //container v4-routed-override-filter

          container v6-routed-override-filter {
            description
                "Configure service ingress override filter";
            leaf ipv6-filter-id {
              type string;
              description
                  "[1..65535]|<name:64 char max>";
            } //ipv6-filter-id

          } //container v6-routed-override-filter

        } //container ingress

      } //container vpls

      list vrrp {
        key "virtual-router-id";
        description
            "Context to create and configure VRRP virtual router instance on the interface";
        leaf virtual-router-id {
          type uint16 {
            range "1..255";
          }
        } //virtual-router-id

        leaf owner {
          type boolean;
        } //owner

        leaf passive {
          type boolean;
        } //passive

        container authentication-key {
          description
              "Configure password for simple text password authentication";
          leaf authentication-key-hash-key {
            type string {
              length "1..500";
            }
            description
                "authentication-key - [8 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        list backup {
          key "ip-address";
          description
              "Configure virtual router IP addresses for the interface";
          leaf ip-address {
            type inet:ip-address;
          } //ip-address

        } //list backup

        list bfd-enable {
          key "interface dst-ip";
          description
              "Configure a BFD interface";
          leaf svc-id {
            type uint32 {
              range "1..2147483647";
            }
          } //svc-id

          leaf interface {
            type string {
              length "1..32";
            }
            description
                "[32 chars max] (must start with a letter)";
          } //interface

          leaf dst-ip {
            type inet:ip-address;
            description
                "ip-address";
          } //dst-ip

          leaf name {
            type string;
            description
                "64-char max (ies/vprn service-name)";
          } //name

        } //list bfd-enable

        container init-delay {
          description
              "Configure VRRP initialization delay timer";
          leaf seconds {
            type uint32 {
              range "1..65535";
            }
          } //seconds

        } //container init-delay

        container mac {
          description
              "Configure a Virtual MAC address to use in ARP responses";
          leaf mac-address {
            type string;
            description
                "xx:xx:xx:xx:xx:xx or xx-xx-xx-xx-xx-xx";
          } //mac-address

        } //container mac

        leaf master-int-inherit {
          type boolean;
          description
              "Allow/disallow the master instance to dictate the master down timer (non-owner 
               context only)";
        }

        container message-interval {
          description
              "Configure the interval for sending VRRP Advertisement messages";
          leaf seconds {
            type uint32 {
              range "1..255";
            }
          } //seconds

          leaf milliseconds {
            type uint32 {
              range "100..900";
            }
          } //milliseconds

        } //container message-interval

        container oper-group {
          description
              "Associate group-name to VRRP";
          leaf group-name {
            type string {
              length "1..32";
            }
          } //group-name

        } //container oper-group

        leaf ping-reply {
          type boolean;
          description
              "Allow/disallow non-owner master to reply to ICMP Echo requests (non-owner 
               context only)";
        }

        container policy {
          description
              "Associate a VRRP Priority Control Policy with the virtual router instance 
               (non-owner context only)";
          leaf vrrp-policy-id {
            type uint32 {
              range "1..9999";
            }
          } //vrrp-policy-id

        } //container policy

        leaf preempt {
          type boolean;
          description
              "Allow/disallow the virtual router instance to override an existing non-owner 
               master (non-owner context only)";
        }

        container priority {
          description
              "Configure the base priority for the virtual router instance (non-owner context 
               only)";
          leaf priority {
            type uint16 {
              range "1..254";
            }
          } //priority

        } //container priority

        leaf shutdown {
          type boolean;
          description
              "Administratively enable/disable the virtual router instance (non-owner context 
               only)";
        }

        leaf ssh-reply {
          type boolean;
          description
              "Allow/disallow non-owner master to reply to SSH requests (non-owner context 
               only)";
        }

        leaf standby-forwarding {
          type boolean;
          description
              "Allow/disallow the forwarding of packets by a standby router";
        }

        leaf telnet-reply {
          type boolean;
          description
              "Allow/disallow non-owner master to reply to Telnet requests (non-owner context 
               only)";
        }

        leaf traceroute-reply {
          type boolean;
          description
              "Allow/disallow non-owner master to reply to traceroute requests (non-owner 
               context only)";
        }

      } //list vrrp

    } //list interface

  } //grouping alu-conf-svc-vprn-if-r13

} //module  alu-conf-svc-vprn-if-r13
