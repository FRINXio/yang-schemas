module alu-conf-port-r13 {
  yang-version "1";

  namespace "urn:alcatel-lucent.com:sros:ns:yang:conf-port-r13";

  prefix "conf-port-r13";

  import alu-conf-port-access-r13 {
    prefix "conf-port-access-r13";
  }
  import alu-conf-port-aps-r13 {
    prefix "conf-port-aps-r13";
  }
  import alu-conf-port-cellular-r13 {
    prefix "conf-port-cellular-r13";
  }
  import alu-conf-port-ethernet-r13 {
    prefix "conf-port-ethernet-r13";
  }
  import alu-conf-port-mbundle-r13 {
    prefix "conf-port-mbundle-r13";
  }
  import alu-conf-port-network-r13 {
    prefix "conf-port-network-r13";
  }
  import alu-conf-port-serial-r13 {
    prefix "conf-port-serial-r13";
  }
  import alu-conf-port-sonetsdh-r13 {
    prefix "conf-port-sonetsdh-r13";
  }
  import alu-conf-port-tdm-r13 {
    prefix "conf-port-tdm-r13";
  }
  import alu-conf-port-wlan-r13 {
    prefix "conf-port-wlan-r13";
  }
  import alu-types {
    prefix "alu";
  }

  alu:alu-major-release "rel16";

  organization "Alcatel-Lucent";

  contact
      "Alcatel-Lucent SR OS Support 
       Web: <http://www.alcatel-lucent.com>";

  description
      "Alcatel-Lucent YANG Data model to configure physical ports on SR OS based 
       routers. 
       
       Copyright 2014-2015 Alcatel-Lucent, 2016 Nokia. All rights reserved. 
       Reproduction of this document is authorized on the condition that the 
       foregoing copyright notice is included. 
       
       This alu-conf-port-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-09-28";

  grouping alu-conf-port-r13 {
    list port {
      key "port-id";
      description
          "Configure physical ports";
      leaf port-id {
        type string {
        }
        description
            "Attribute port-id for port";
      } //port-id

      leaf ddm-events {
        type boolean;
        description
            "Enable/Disable Digital Diagnostic Monitoring (DDM) events for the port";
      }

      container description {
        description
            "Add/remove a text description for the port";
        leaf long-description-string {
          type string {
            length "1..160";
          }
        } //long-description-string

      } //container description

      leaf monitor-agg-egress-queue-stats {
        type boolean;
        description
            "Enable/disable monitoring of Aggregate Queue Stats";
      }

      leaf shutdown {
        type boolean;
        description
            "Administratively enable/disable the port";
      }

      uses "conf-port-access-r13:alu-conf-port-access-r13";
      uses "conf-port-aps-r13:alu-conf-port-aps-r13";
      uses "conf-port-cellular-r13:alu-conf-port-cellular-r13";
      container connector {
        description
            "Configure connector port settings";
        container breakout {
          description
              "Configure the breakout for this connector port";
          leaf breakout {
            type string {
              length "1..32";
            }
            description
                "Attribute breakout for breakout";
          } //breakout

        } //container breakout

        container rs-fec-mode {
          description
              "Configure the RS FEC mode of the connector";
          leaf RS-FEC-mode {
            type enumeration {
              enum cl91-514-528;
              enum cl91-514-544;
            }
            description
                "cl91-514-528 | cl91-514-544";
          } //RS-FEC-mode

        } //container rs-fec-mode

      } //container connector

      container dwdm {
        description
            "Configure the Dense Wavelength Division Multiplexing parameters";
        container channel {
          description
              "Configure the DWDM channel number";
          leaf channel {
            type uint32;
            description
                "[0|17-61|175-605] 
                 - 17-61 used for 100GHz channels 
                 175, 185,...605 used for 50GHz channels 
                 0 only valid on shutdown ports";
          } //channel

        } //container channel

        leaf rxdtv-adjust {
          type boolean;
          description
              "Enable/Disable Rx Decision Threshold Voltage Adjustment feedback.";
        }

        container amplifier {
          status "obsolete";
          description
              "Configure the optical port amplifier parameters";
          container report-alarms {
            status "obsolete";
            description
                "Enable/disable logging of optical amplifier alarms on port";
            leaf ild {
              type boolean;
            } //ild

            leaf tmp {
              type boolean;
            } //tmp

            leaf mth {
              type boolean;
            } //mth

            leaf mtl {
              type boolean;
            } //mtl

            leaf los {
              type boolean;
            } //los

            leaf lop {
              type boolean;
            } //lop

            leaf com {
              type boolean;
            } //com

          } //container report-alarms

        } //container amplifier

        container coherent {
          description
              "Configure the coherent optical module parameters";
          container channel {
            description
                "Configure the received channel number";
            leaf channel {
              type uint32;
              description
                  "[0|17-61|175-605] 
                   - 17-61 used for 100GHz channels 
                   175, 185,...605 used for 50GHz channels 
                   0 - use the tx channel number";
            } //channel

          } //container channel

          container compatibility {
            description
                "Configure the optical mode and rate of operation";
            leaf mode {
              type enumeration {
                enum long-haul;
                enum metro;
                enum access;
                enum interop;
                enum interop2;
                enum interop3;
              }
              default "long-haul";
              description
                  "long-haul|metro|access|interop|interop2|interop3 
                   Default: long-haul";
            } //mode

          } //container compatibility

          container cpr-window-size {
            description
                "Configure the Carrier Phase Recovery window size";
            leaf window-size {
              type uint32;
              default 32;
              description
                  "[2|4|8|16|32|64] symbols - Default: 32";
            } //window-size

          } //container cpr-window-size

          container dispersion {
            description
                "Configure the dispersion compensation";
            leaf dispersion {
              type int32 {
                range "-50000..50000";
              }
              default 0;
              description
                  "[-50000..50000] ps/nm - Default: 0";
            } //dispersion

          } //container dispersion

          container mode {
            description
                "Configure the dispersion algorithm mode";
            leaf mode-id {
              type enumeration {
                enum automatic;
                enum manual;
              }
            } //mode-id

          } //container mode

          container report-alarms {
            description
                "Enable/disable logging of alarms";
            leaf modflt {
              type boolean;
            } //modflt

            leaf mod {
              type boolean;
            } //mod

            leaf netrx {
              type boolean;
            } //netrx

            leaf nettx {
              type boolean;
            } //nettx

            leaf hosttx {
              type boolean;
            } //hosttx

          } //container report-alarms

          container rx-los-reaction {
            description
                "Configure the reaction to an RX LOS";
            leaf rx-los-reaction-id {
              type enumeration {
                enum squelch;
              }
            } //rx-los-reaction-id

          } //container rx-los-reaction

          container rx-los-thresh {
            description
                "Configure the average input power LOS (Loss of Signal) threshold";
            leaf threshold {
              type string;
              default "-23.00";
              description
                  "[-24.00..-13.00] dBm - Default: -23.00";
            } //threshold

          } //container rx-los-thresh

          container sweep {
            description
                "Configure the dispersion sweep start and end values";
            leaf start {
              type int32 {
                range "-50000..50000";
              }
              default -25500;
              description
                  "[-50000..50000] ps/nm - Default: -25500";
            } //start

            leaf end {
              type int32 {
                range "-50000..50000";
              }
              default 2000;
              description
                  "[-50000..50000] ps/nm - Default: 2000";
            } //end

          } //container sweep

          container target-power {
            description
                "Configure the desired average output power";
            leaf power {
              type string;
              default "1.00";
              description
                  "[-20.00..3.00] dBm - Default: 1.00";
            } //power

          } //container target-power

        } //container coherent

        container tdcm {
          status "obsolete";
          description
              "Configure the Tunable Dispersion Compensation Module parameters";
          container channel {
            status "obsolete";
            description
                "Configure the tdcm received channel number";
            leaf channel {
              type uint32;
              description
                  "[0|17-61|175-605] 
                   - 17-61 used for 100GHz channels 
                   175, 185,...605 used for 50GHz channels 
                   0 - use the tx channel number";
            } //channel

          } //container channel

          container dispersion {
            status "obsolete";
            description
                "Configure the dispersion compensation for the link (ps/nm)";
            leaf dispersion {
              type int32 {
                range "-1200..1200";
              }
              default 0;
              description
                  "[-1200..1200] - Default: 0";
            } //dispersion

          } //container dispersion

          container mode {
            status "obsolete";
            description
                "Configure the dispersion algorithm mode used for this port";
            leaf mode-id {
              type enumeration {
                enum automatic;
                enum manual;
              }
            } //mode-id

          } //container mode

          container report-alarms {
            status "obsolete";
            description
                "Enable/disable logging of tdcm alarms on port";
            leaf nrdy {
              type boolean;
            } //nrdy

            leaf mth {
              type boolean;
            } //mth

            leaf mtl {
              type boolean;
            } //mtl

            leaf unlck {
              type boolean;
            } //unlck

            leaf tlim {
              type boolean;
            } //tlim

            leaf einv {
              type boolean;
            } //einv

            leaf com {
              type boolean;
            } //com

          } //container report-alarms

          container sweep {
            status "obsolete";
            description
                "Configure the dispersion sweep start and end values for the link (ps/nm)";
            leaf start {
              type int32 {
                range "-1200..1200";
              }
              default -1200;
              description
                  "[-1200..1200] - Default: -1200";
            } //start

            leaf end {
              type int32 {
                range "-1200..1200";
              }
              default 1200;
              description
                  "[-1200..1200] - Default: 1200";
            } //end

          } //container sweep

        } //container tdcm

        container wavetracker {
          description
              "Enable/Disable Wavelength Tracker on port.";
          container encode {
            description
                "Enable/Disable Wavelength Tracker encoding";
            leaf key1 {
              type uint32 {
                range "0..4095";
              }
            } //key1

            leaf key2 {
              type uint32 {
                range "0..4095";
              }
            } //key2

          } //container encode

          container report-alarm {
            description
                "Enable/disable logging of dwdm alarms on port";
            leaf enc-fail {
              type boolean;
            } //enc-fail

            leaf enc-degr {
              type boolean;
            } //enc-degr

            leaf pwr-fail {
              type boolean;
            } //pwr-fail

            leaf pwr-degr {
              type boolean;
            } //pwr-degr

            leaf pwr-high {
              type boolean;
            } //pwr-high

            leaf pwr-low {
              type boolean;
            } //pwr-low

            leaf missing {
              type boolean;
            } //missing

          } //container report-alarm

          container power-control {
            presence
                "Enable/Disable Wavelength Power Control";
            container target-power {
              description
                  "Configure desired average output power";
              leaf dBm {
                type string;
                description
                    "Attribute dBm for target-power";
              } //dBm

            } //container target-power

          } //container power-control

        } //container wavetracker

      } //container dwdm

      uses "conf-port-ethernet-r13:alu-conf-port-ethernet-r13";
      container hybrid-buffer-allocation {
        description
            "Configure hybrid port buffer allocation parameters";
        container egr-weight {
          description
              "Configure hybrid port egress weight parameters";
          leaf access {
            type uint32 {
              range "0..100";
            }
            default 50;
            description
                "[0..100] - Default: 50";
          } //access

          leaf network {
            type uint32 {
              range "0..100";
            }
            default 50;
            description
                "[0..100] - Default: 50";
          } //network

        } //container egr-weight

        container ing-weight {
          description
              "Configure hybrid port ingress weight parameters";
          leaf access {
            type uint32 {
              range "0..100";
            }
            default 50;
            description
                "[0..100] - Default: 50";
          } //access

          leaf network {
            type uint32 {
              range "0..100";
            }
            default 50;
            description
                "[0..100] - Default: 50";
          } //network

        } //container ing-weight

      } //container hybrid-buffer-allocation

      container modify-buffer-allocation-rate {
        description
            "Configure modify buffer allocation rate";
        container egr-percentage-of-rate {
          description
              "Configure egress percentage of rate";
          leaf egr-rate-percentage {
            type uint32 {
              range "1..1000";
            }
            description
                "Attribute egr-rate-percentage for egr-percentage-of-rate";
          } //egr-rate-percentage

        } //container egr-percentage-of-rate

        container ing-percentage-of-rate {
          description
              "Configure ingress percentage of rate";
          leaf ing-rate-percentage {
            type uint32 {
              range "1..1000";
            }
            description
                "[1..1000] - default is 100";
          } //ing-rate-percentage

        } //container ing-percentage-of-rate

      } //container modify-buffer-allocation-rate

      uses "conf-port-mbundle-r13:alu-conf-port-mbundle-r13";
      container named-pool-mode {
        description
            "Enable/Disable named pool mode";
        container egress {
          description
              "Configure named pool mode egress PORT parameters";
          container named-pool-policy {
            description
                "Configure egress named pool policy";
            leaf policy-name {
              type string {
                length "1..32";
              }
            } //policy-name

          } //container named-pool-policy

        } //container egress

        container ingress {
          description
              "Configure named pool mode ingress PORT parameters";
          container named-pool-policy {
            description
                "Configure ingress named pool policy";
            leaf policy-name {
              type string {
                length "1..32";
              }
            } //policy-name

          } //container named-pool-policy

        } //container ingress

      } //container named-pool-mode

      uses "conf-port-network-r13:alu-conf-port-network-r13";
      container otu {
        presence
            "Configure Optical Transport Unit (OTU) parameters";
        leaf async-mapping {
          type boolean;
          description
              "Enable/Disable OTU asynchronous mapping; synchronous when disabled";
        }

        container fec {
          description
              "Configure the Forwarding Error Correction (FEC) parameters";
          leaf g709-enhanced {
            type enumeration {
              enum g709;
              enum enhanced;
            }
            description
                "fec-mode";
          } //g709-enhanced

        } //container fec

        container otu2-lan-data-rate {
          description
              "Configure the 10GE LAN OTU2 Data Rate";
          leaf t11.049-11.096 {
            type string {
            }
            description
                "OTU2 data Lan Rate";
          } //t11.049-11.096

        } //container otu2-lan-data-rate

        container report-alarms {
          description
              "Enable/Disable the OTU alarms";
          leaf loc {
            type boolean;
          } //loc

          leaf los {
            type boolean;
          } //los

          leaf lof {
            type boolean;
          } //lof

          leaf lom {
            type boolean;
          } //lom

          leaf otu-ais {
            type boolean;
          } //otu-ais

          leaf otu-ber-sf {
            type boolean;
          } //otu-ber-sf

          leaf otu-ber-sd {
            type boolean;
          } //otu-ber-sd

          leaf otu-bdi {
            type boolean;
          } //otu-bdi

          leaf otu-tim {
            type boolean;
          } //otu-tim

          leaf otu-iae {
            type boolean;
          } //otu-iae

          leaf otu-biae {
            type boolean;
          } //otu-biae

          leaf fec-sf {
            type boolean;
          } //fec-sf

          leaf fec-sd {
            type boolean;
          } //fec-sd

          leaf fec-fail {
            type boolean;
          } //fec-fail

          leaf fec-uncorr {
            type boolean;
          } //fec-uncorr

          leaf odu-ais {
            type boolean;
          } //odu-ais

          leaf odu-oci {
            type boolean;
          } //odu-oci

          leaf odu-lck {
            type boolean;
          } //odu-lck

          leaf odu-bdi {
            type boolean;
          } //odu-bdi

          leaf odu-tim {
            type boolean;
          } //odu-tim

          leaf opu-tim {
            type boolean;
          } //opu-tim

          leaf opu-plm {
            type boolean;
          } //opu-plm

        } //container report-alarms

        container sd-threshold {
          description
              "Configure the Signal Degrade (SD) threshold";
          leaf threshold {
            type int32 {
              range "3..9";
            }
            description
                "Attribute threshold for sd-threshold";
          } //threshold

          leaf coefficient {
            type uint32 {
              range "10..99";
            }
            default 10;
            description
                "[10..99] - Default: 10";
          } //coefficient

        } //container sd-threshold

        container sd-threshold-clear {
          description
              "Configure the Signal Degrade (SD) threshold clear";
          leaf threshold {
            type uint32 {
              range "3..10";
            }
            default 8;
            description
                "[3..10] - Default: 8";
          } //threshold

          leaf coefficient {
            type uint32 {
              range "10..99";
            }
            default 10;
            description
                "[10..99] - Default: 10";
          } //coefficient

        } //container sd-threshold-clear

        container sf-sd-method {
          description
              "Configure the Signal Fail/Degrade method for the port";
          leaf bip8-fec {
            type enumeration {
              enum bip8;
              enum fec;
            }
            description
                "keywords - detection method.";
          } //bip8-fec

        } //container sf-sd-method

        container sf-threshold {
          description
              "Configure the Signal Fail (SF) threshold";
          leaf threshold {
            type int32 {
              range "3..8";
            }
            description
                "Attribute threshold for sf-threshold";
          } //threshold

          leaf coefficient {
            type uint32 {
              range "10..99";
            }
            default 10;
            description
                "[10..99] - Default: 10";
          } //coefficient

        } //container sf-threshold

        container sf-threshold-clear {
          description
              "Configure the Signal Fail (SF) threshold clear";
          leaf threshold {
            type uint32 {
              range "3..9";
            }
            default 6;
            description
                "[3..9] - Default: 6";
          } //threshold

          leaf coefficient {
            type uint32 {
              range "10..99";
            }
            default 10;
            description
                "[10..99] - Default: 10";
          } //coefficient

        } //container sf-threshold-clear

        container signal-type {
          status "obsolete";
          description
              "Configure the output signal as a single OTU or multiple (muxed) OTUs";
          leaf signal-type {
            type enumeration {
              enum otu4;
              enum otu4x2;
            }
            description
                "otu4|otu4x2";
          } //signal-type

        } //container signal-type

        container pm-tti {
          description
              "Configure the Path Monitoring Trail Trace Identifier parameters";
          container expected {
            description
                "Configure the Port's PM-TTI expected values";
            leaf string {
              type string {
                length "1..64";
              }
            } //string

            leaf-list bytes {
              type string {
                length "1..191";
              }
              max-elements 64;
              description
                  "<byte>[-<byte>...(up to 64 max)] 
                   <byte> - [00..FF] hexadecimal (e.g. A3) 
                   ";
            } //bytes

            leaf auto-generated {
              type boolean;
              description
                  "keyword - Use system generated (default) TTI";
            } //auto-generated

            leaf use-rx {
              type boolean;
              description
                  "keyword - Assign expected TTI to the currently received PM-TTI value.";
            } //use-rx

          } //container expected

          container mismatch-reaction {
            description
                "Configure the reaction to a mismatched TTI";
            leaf mismatch-reaction-id {
              type enumeration {
                enum squelch-rx;
              }
            } //mismatch-reaction-id

          } //container mismatch-reaction

          container tx {
            description
                "Configure the Port's PM-TTI Transmit parameters";
            leaf string {
              type string {
                length "1..64";
              }
            } //string

            leaf auto-generated {
              type boolean;
              description
                  "keyword - Use system generated (default) TTI";
            } //auto-generated

            leaf-list bytes {
              type string {
                length "1..191";
              }
              max-elements 64;
              description
                  "<byte>[-<byte>...(up to 64 max)] 
                   <byte> - [00..FF] hexadecimal (e.g. A3) 
                   ";
            } //bytes

          } //container tx

        } //container pm-tti

        container psi-payload {
          description
              "Configure the Payload Structure Identifier Payload parameters";
          container expected {
            description
                "Configure the Port's PSI Payload expected values";
            leaf byte {
              type string {
                length "1..2";
              }
              default "00";
              description
                  "[00..FF] Hexadecimal notation - Default: 00";
            } //byte

            leaf auto {
              type boolean;
              description
                  "keyword";
            } //auto

          } //container expected

          container mismatch-reaction {
            description
                "Configure the reaction to a mismatched payload";
            leaf mismatch-reaction-id {
              type enumeration {
                enum squelch-rx;
              }
            } //mismatch-reaction-id

          } //container mismatch-reaction

          container tx {
            description
                "Configure the Port's PSI Payload Transmit parameters";
            leaf byte {
              type string {
                length "1..2";
              }
              default "00";
              description
                  "[00..FF] Hexadecimal notation - Default: 00";
            } //byte

            leaf auto {
              type boolean;
              description
                  "keyword";
            } //auto

          } //container tx

        } //container psi-payload

        container psi-tti {
          description
              "Configure the Payload Structure Identifier Trail Trace Identifier parameters";
          container expected {
            description
                "Configure the Port's PSI-TTI expected values";
            leaf string {
              type string {
                length "1..255";
              }
            } //string

            leaf-list bytes {
              type string {
                length "1..764";
              }
              max-elements 255;
              description
                  "<byte>[-<byte>...(up to 255 max)] 
                   <byte> - [00..FF] hexadecimal (e.g. A3) 
                   ";
            } //bytes

            leaf auto-generated {
              type boolean;
              description
                  "keyword - Use system generated (default) TTI";
            } //auto-generated

            leaf use-rx {
              type boolean;
              description
                  "keyword - Assign expected TTI to the currently received PSI-TTI value.";
            } //use-rx

          } //container expected

          container mismatch-reaction {
            description
                "Configure the reaction to a mismatched TTI";
            leaf mismatch-reaction-id {
              type enumeration {
                enum squelch-rx;
              }
            } //mismatch-reaction-id

          } //container mismatch-reaction

          container tx {
            description
                "Configure the Port's PSI-TTI Transmit parameters";
            leaf string {
              type string {
                length "1..255";
              }
            } //string

            leaf auto-generated {
              type boolean;
              description
                  "keyword - Use system generated (default) TTI";
            } //auto-generated

            leaf-list bytes {
              type string {
                length "1..764";
              }
              max-elements 255;
              description
                  "<byte>[-<byte>...(up to 255 max)] 
                   <byte> - [00..FF] hexadecimal (e.g. A3) 
                   ";
            } //bytes

          } //container tx

        } //container psi-tti

        container sm-tti {
          description
              "Configure the Section Monitoring Trail Trace Identifier parameters";
          container expected {
            description
                "Configure the Port's SM-TTI expected values";
            leaf string {
              type string {
                length "1..64";
              }
            } //string

            leaf-list bytes {
              type string {
                length "1..191";
              }
              max-elements 64;
              description
                  "<byte>[-<byte>...(up to 64 max)] 
                   <byte> - [00..FF] hexadecimal (e.g. A3) 
                   ";
            } //bytes

            leaf auto-generated {
              type boolean;
              description
                  "keyword - Use system generated (default) TTI";
            } //auto-generated

            leaf use-rx {
              type boolean;
              description
                  "keyword - Assign expected TTI to the currently received SM-TTI value.";
            } //use-rx

          } //container expected

          container mismatch-reaction {
            description
                "Configure the reaction to a mismatched TTI";
            leaf mismatch-reaction-id {
              type enumeration {
                enum squelch-rx;
              }
            } //mismatch-reaction-id

          } //container mismatch-reaction

          container tx {
            description
                "Configure the Port's SM-TTI transmit parameters";
            leaf string {
              type string {
                length "1..64";
              }
            } //string

            leaf-list bytes {
              type string {
                length "1..191";
              }
              max-elements 64;
              description
                  "<byte>[-<byte>...(up to 64 max)] 
                   <byte> - [00..FF] hexadecimal (e.g. A3) 
                   ";
            } //bytes

            leaf auto-generated {
              type boolean;
              description
                  "keyword - Use system generated (default) TTI";
            } //auto-generated

          } //container tx

        } //container sm-tti

      } //container otu

      uses "conf-port-serial-r13:alu-conf-port-serial-r13";
      uses "conf-port-sonetsdh-r13:alu-conf-port-sonetsdh-r13";
      uses "conf-port-tdm-r13:alu-conf-port-tdm-r13";
      container transceiver {
        description
            "Configure the transceiver parameters";
        leaf digital-coherent-optics {
          type boolean;
          description
              "Enable/disable digital coherent optics on the transceiver";
        }

      } //container transceiver

      uses "conf-port-wlan-r13:alu-conf-port-wlan-r13";
    } //list port

  } //grouping alu-conf-port-r13

} //module  alu-conf-port-r13
