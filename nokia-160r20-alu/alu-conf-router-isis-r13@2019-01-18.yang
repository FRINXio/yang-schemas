module alu-conf-router-isis-r13 {
  yang-version "1";

  namespace "urn:alcatel-lucent.com:sros:ns:yang:conf-router-isis-r13";

  prefix "conf-router-isis-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure ISIS on SR OS based routers. 
       
       Copyright 2014-2015 Alcatel-Lucent, 2016 Nokia. All rights reserved. 
       Reproduction of this document is authorized on the condition that the 
       foregoing copyright notice is included. 
       
       This alu-conf-router-isis-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-01-18";

  grouping alu-conf-router-isis-r13 {
    list isis {
      key "isis-instance";
      description
          "Configure ISIS";
      leaf isis-instance {
        type uint32 {
          range "0..31";
        }
      } //isis-instance

      leaf advertise-passive-only {
        type boolean;
        description
            "Enable/disable ISIS to advertise only prefixes that belong to passive 
             interfaces";
      }

      container advertise-router-capability {
        description
            "Enable/disable router advertisement capabilities";
        leaf advertise-router-capability-id {
          type enumeration {
            enum area;
            enum as;
          }
        } //advertise-router-capability-id

      } //container advertise-router-capability

      leaf advertise-tunnel-link {
        type boolean;
        description
            "Enable/disable advertisement of tunnel link";
      }

      container all-l1isis {
        description
            "Specify the MAC address to use for All L1 ISIS routers";
        leaf ieee-address {
          type string;
          description
              "xx:xx:xx:xx:xx:xx or xx-xx-xx-xx-xx-xx";
        } //ieee-address

      } //container all-l1isis

      container all-l2isis {
        description
            "Specify the MAC address to use for All L2 ISIS routers";
        leaf ieee-address {
          type string;
          description
              "xx:xx:xx:xx:xx:xx or xx-xx-xx-xx-xx-xx";
        } //ieee-address

      } //container all-l2isis

      list area-id {
        key "area-address";
        description
            "Configure an area-id used by ISIS (up to 13 bytes)";
        leaf area-address {
          type string;
          description
              "xx[.xx][xx][.xx][xx]..(up to 13 bytes)";
        } //area-address

      } //list area-id

      container auth-keychain {
        description
            "Configure TCP authentication keychain to use for the session";
        leaf name {
          type string {
            length "1..32";
          }
          description
              "keychain-name (32 char max)";
        } //name

      } //container auth-keychain

      leaf authentication-check {
        type boolean;
        description
            "Enable/disable authentication on received ISIS protocol packets";
      }

      container authentication-key {
        description
            "Configure the authentication-key to be used";
        leaf authentication-key-hash-key {
          type string {
            length "1..500";
          }
          description
              "authentication-key - [254 chars max] 
               hash-key 
               hash2-key 
               custom-key";
        } //authentication-key-hash-key

        leaf hash-hash2-custom {
          type enumeration {
            enum hash;
            enum hash2;
            enum custom;
          }
          description
              "keywords - specify hashing scheme";
        } //hash-hash2-custom

      } //container authentication-key

      container authentication-type {
        description
            "Configure the authentication type to be used";
        leaf password-message-digest {
          type enumeration {
            enum password;
            enum message-digest;
          }
          description
              "keywords - specify authentication type";
        } //password-message-digest

      } //container authentication-type

      leaf csnp-authentication {
        type boolean;
        description
            "Enable/disable authentication on received ISIS protocol packets of type CSNP";
      }

      container database-export {
        description
            "Enable/Disable database export";
        leaf identifier {
          type string;
          description
              "[0..18446744073709551615]";
        } //identifier

        leaf bgp-ls-identifier {
          type uint32;
        } //bgp-ls-identifier

      } //container database-export

      container default-route-tag {
        description
            "Configure route tag for default route";
        leaf tag {
          type uint32 {
            range "1..4294967295";
          }
        } //tag

      } //container default-route-tag

      leaf disable-ldp-sync {
        type boolean;
        description
            "Disable/Enable synchronization of IGP and LDP";
      }

      container export {
        description
            "Configure export policies";
        leaf-list policy-name {
          type string {
            length "1..32";
          }
          max-elements 5;
          description
              "[32 chars max] - maximum 5 policies";
        } //policy-name

      } //container export

      container export-limit {
        description
            "Maximum number of routes (prefixes) that can be exported into IS-IS from the 
             route table.";
        leaf number {
          type uint32 {
            range "1..4294967295";
          }
        } //number

        leaf log {
          type uint16 {
            range "1..100";
          }
        } //log

      } //container export-limit

      leaf hello-authentication {
        type boolean;
        description
            "Enable/disable authentication on received ISIS protocol packets of type HELLO";
      }

      container hello-padding {
        description
            "Configure padding on ISIS hello packets";
        leaf hello-padding-id {
          type enumeration {
            enum none;
            enum adaptive;
            enum loose;
            enum strict;
          }
        } //hello-padding-id

      } //container hello-padding

      leaf ignore-attached-bit {
        type boolean;
        description
            "Enable/disable ISIS to ignore the ATT bit and therefore suppress the 
             installation of default routes";
      }

      leaf ignore-lsp-errors {
        type boolean;
        description
            "Enable/disable ISIS to ignore LSP packets with errors";
      }

      leaf ignore-narrow-metric {
        type boolean;
        description
            "Enable/disable ISIS to ignore links with narrow metrics when wide-metrics 
             support is enabled";
      }

      leaf iid-tlv-enable {
        type boolean;
        description
            "Enable use of IID TLV for this ISIS instance";
      }

      container import {
        description
            "Configure import policies";
        leaf-list policy-name {
          type string {
            length "1..32";
          }
          max-elements 5;
          description
              "[32 chars max] - maximum 5 policies";
        } //policy-name

      } //container import

      container ipv4-multicast-routing {
        description
            "Enable/Disable IPv4 multicast routing";
        leaf ipv4-multicast-routing-id {
          type enumeration {
            enum native;
            enum mt;
          }
        } //ipv4-multicast-routing-id

      } //container ipv4-multicast-routing

      leaf ipv4-routing {
        type boolean;
        description
            "Enable/Disable IPv4 routing";
      }

      container ipv6-multicast-routing {
        description
            "Enable/Disable IPv6 multicast routing";
        leaf ipv6-multicast-routing-id {
          type enumeration {
            enum native;
            enum mt;
          }
        } //ipv6-multicast-routing-id

      } //container ipv6-multicast-routing

      container ipv6-routing {
        description
            "Enable/Disable IPv6 routing";
        leaf native-mt {
          type enumeration {
            enum native;
            enum mt;
          }
          description
              "native - Use IS-IS IPv6 TLVs for IPv6 routing 
               mt - Use IS-IS multi-topology TLVs for IPv6 routing";
        } //native-mt

      } //container ipv6-routing

      leaf ldp-over-rsvp {
        type boolean;
        description
            "Allow ldp over rsvp processing in IS-IS";
      }

      container level-capability {
        description
            "Specifies ISIS levels on the system";
        leaf level-capability-id {
          type enumeration {
            enum level-1;
            enum level-2;
            enum level-1/2;
          }
        } //level-capability-id

      } //container level-capability

      container loopfree-alternate {
        status "obsolete";
        description
            "Enable/disable IP fast re-route capability for ISIS";
        leaf remote-lfa {
          type boolean;
        } //remote-lfa

        leaf max-pq-cost {
          type uint32;
        } //max-pq-cost

        leaf ti-lfa {
          type boolean;
        } //ti-lfa

        leaf max-sr-frr-labels {
          type uint32 {
            range "0..3";
          }
        } //max-sr-frr-labels

      } //container loopfree-alternate

      container loopfree-alternate-exclude {
        status "obsolete";
        description
            "Configure LFA exclude policies";
        leaf-list prefix-policy {
          type string {
            length "1..32";
          }
          max-elements 5;
        } //prefix-policy

      } //container loopfree-alternate-exclude

      container lsp-lifetime {
        description
            "Configure LSP lifetime";
        leaf seconds {
          type uint32 {
            range "350..65535";
          }
        } //seconds

      } //container lsp-lifetime

      container lsp-mtu-size {
        description
            "Configure LSP mtu-size";
        leaf size {
          type uint16 {
            range "490..9190";
          }
        } //size

      } //container lsp-mtu-size

      container lsp-refresh-interval {
        description
            "Configure LSP refresh interval";
        leaf seconds {
          type uint32 {
            range "150..65535";
          }
          default 600;
        } //seconds

        leaf half-lifetime {
          type enumeration {
            enum enable;
            enum disable;
          }
        } //half-lifetime

      } //container lsp-refresh-interval

      container lsp-wait {
        status "obsolete";
        description
            "Configure ISIS LSP wait times";
        leaf-list lsp-wait {
          type uint32 {
            range "0..4294967295";
          }
          max-elements 3;
          description
              "Attribute lsp-wait for lsp-wait";
        } //lsp-wait

      } //container lsp-wait

      container multicast-import {
        description
            "Enable/disable submission of routes into the multicast Route Table Manager by 
             ISIS";
        leaf ipv4 {
          type boolean;
        } //ipv4

        leaf ipv6 {
          type boolean;
        } //ipv6

        leaf both {
          type boolean;
        } //both

      } //container multicast-import

      container overload {
        description
            "Configure the local router so that it appears to be overloaded";
        leaf timeout {
          type uint32 {
            range "60..1800";
          }
        } //timeout

        leaf max-metric {
          type boolean;
        } //max-metric

      } //container overload

      leaf overload-export-external {
        type boolean;
        description
            "Enable/disable ISIS route advertisement for external routes in case of 
             overload";
      }

      leaf overload-export-interlevel {
        type boolean;
        description
            "Enable/disable ISIS route advertisement for interlevel routes in case of 
             overload";
      }

      container overload-on-boot {
        description
            "Configure the local router so that it appears to be overloaded at boot up";
        leaf timeout {
          type uint32 {
            range "60..1800";
          }
        } //timeout

        leaf max-metric {
          type boolean;
        } //max-metric

      } //container overload-on-boot

      leaf poi-tlv-enable {
        type boolean;
        description
            "Enable use of Purge Originator Identification TLV for this ISIS instance";
      }

      leaf prefix-attributes-tlv {
        type boolean;
        description
            "Enable/disable use of prefix attributes TLV for this ISIS instance";
      }

      container prefix-limit {
        description
            "Configure the limit for maximum number of prefixes IS-IS can support";
        leaf limit {
          type uint32 {
            range "1..4294967295";
          }
        } //limit

        leaf log-only {
          type boolean;
        } //log-only

        leaf threshold {
          type uint32 {
            range "0..100";
          }
        } //threshold

        leaf overload-timeout {
          type string;
          description
              "Attribute seconds|forever for prefix-limit";
        } //overload-timeout

      } //container prefix-limit

      leaf psnp-authentication {
        type boolean;
        description
            "Enable/disable authentication on received ISIS protocol packets of type PSNP";
      }

      container reference-bandwidth {
        description
            "Configure the reference bandwidth that provides the basis of bandwidth 
             relative costing";
        leaf bandwidth-in-kbps {
          type uint32 {
            range "1..4000000000";
          }
          default 100000000;
        } //bandwidth-in-kbps

        leaf tbps {
          type uint32 {
            range "1..4";
          }
        } //tbps

        leaf gbps {
          type uint32 {
            range "1..999";
          }
        } //gbps

        leaf mbps {
          type uint32 {
            range "1..999";
          }
        } //mbps

        leaf kbps {
          type uint32 {
            range "1..999";
          }
        } //kbps

      } //container reference-bandwidth

      list rib-priority {
        key "high";
        description
            "Configure RIB priority for ISIS.";
        leaf high {
          type boolean;
        } //high

        leaf prefix-list-name {
          type string {
            length "1..32";
          }
        } //prefix-list-name

        leaf tag {
          type uint32 {
            range "1..4294967295";
          }
        } //tag

      } //list rib-priority

      container router-id {
        description
            "Configure the router id";
        leaf router-id {
          type inet:ip-address;
          description
              "<ip-address>";
        } //router-id

      } //container router-id

      leaf rsvp-shortcut {
        type boolean;
        status "obsolete";
        description
            "Enable/disable RSVP shortcut";
      }

      leaf shutdown {
        type boolean;
        description
            "Administratively enable or disable the operation of ISIS";
      }

      container spf-wait {
        status "obsolete";
        description
            "Configure ISIS SPF wait times";
        leaf-list spf-wait {
          type uint32 {
            range "0..4294967295";
          }
          max-elements 3;
          description
              "Attribute spf-wait for spf-wait";
        } //spf-wait

      } //container spf-wait

      leaf standard-multi-instance {
        type boolean;
        description
            "Enable/Disable RFC standards compliant multi-instance behavior";
      }

      leaf strict-adjacency-check {
        type boolean;
        description
            "Enable/disable strict adjacency checks";
      }

      list summary-address {
        key "ip-prefix-ip-prefix-length netmask";
        description
            "Creates/deletes summary-addresses";
        leaf ip-prefix-ip-prefix-length {
          type string;
          description
              "Attribute ip-prefix/ip-prefix-length for summary-address";
        } //ip-prefix-ip-prefix-length

        leaf netmask {
          type string;
          description
              "a.b.c.d (network bits all 1 and host bits all 0)";
        } //netmask

        leaf level {
          type enumeration {
            enum level-1;
            enum level-2;
            enum level-1/2;
          }
        } //level

        leaf tag {
          type uint32 {
            range "1..4294967295";
          }
        } //tag

      } //list summary-address

      leaf suppress-attached-bit {
        type boolean;
        description
            "Enable/disable ISIS to suppress setting the ATT bit on LSPs";
      }

      container system-id {
        description
            "Configure system-id";
        leaf isis-system-id {
          type string {
            length "1..14";
          }
          description
              "6 octets system identifier (xxxx.xxxx.xxxx)";
        } //isis-system-id

      } //container system-id

      leaf traffic-engineering {
        type boolean;
        description
            "Configure traffic-engineering and configure if IGP shortcuts are required by 
             BGP";
      }

      container unicast-import-disable {
        description
            "Enable/disable submission of routes into the unicast Route Table Manager by 
             ISIS";
        leaf ipv4 {
          type boolean;
        } //ipv4

        leaf ipv6 {
          type boolean;
        } //ipv6

        leaf both {
          type boolean;
        } //both

      } //container unicast-import-disable

      container entropy-label {
        description
            "Configure ISIS entropy label";
        leaf override-tunnel-elc {
          type boolean;
          description
              "Configure ISIS received entropy label capability override";
        }

      } //container entropy-label

      container graceful-restart {
        presence
            "Enable/disable graceful-restart for ISIS";
        leaf helper-disable {
          type boolean;
          description
              "Enable/disable graceful restart helper mode for ISIS";
        }

      } //container graceful-restart

      container igp-shortcut {
        description
            "Configure ISIS IGP shortcut";
        leaf shutdown {
          type boolean;
          description
              "Administratively enable or disable IGP shortcut";
        }

        container tunnel-next-hop {
          description
              "Configure IGP shortcut tunnel next-hop";
          container family {
            description
                "Configure IGP shortcut tunnel next-hop family";
            leaf family-id {
              type enumeration {
                enum ipv4;
                enum ipv6;
                enum srv4;
                enum srv6;
              }
            } //family-id

            container resolution {
              description
                  "Configure resolution behavior for ISIS routes";
              leaf resolution-id {
                type enumeration {
                  enum any;
                  enum disabled;
                  enum filter;
                  enum match-family-ip;
                }
              } //resolution-id

            } //container resolution

            container resolution-filter {
              description
                  "Configure specific tunnels to be used for resolving ISIS routes";
              leaf rsvp {
                type boolean;
                description
                    "Enable/disable RSVP for tunnel next hop resolution";
              }

              leaf sr-te {
                type boolean;
                description
                    "Enable/disable SR-TE for tunnel next hop resolution";
              }

            } //container resolution-filter

          } //container family

        } //container tunnel-next-hop

      } //container igp-shortcut

      list interface {
        key "ip-int-name";
        description
            "Configure ISIS interface";
        leaf ip-int-name {
          type string {
            length "1..32";
          }
          description
              "[32 chars max] (Must start with a letter)";
        } //ip-int-name

        list adjacency-set {
          key "adjacency-set-id";
          description
              "Configure adjacency-set";
          leaf adjacency-set-id {
            type uint32 {
              range "1..4294967295";
            }
          } //adjacency-set-id

        } //list adjacency-set

        list bfd-enable {
          key "bfd-enable-id";
          description
              "Enable BFD";
          leaf bfd-enable-id {
            type enumeration {
              enum ipv4;
              enum ipv6;
            }
          } //bfd-enable-id

          leaf include-bfd-tlv {
            type boolean;
          } //include-bfd-tlv

        } //list bfd-enable

        container csnp-interval {
          description
              "Configure the frequency that CSN packets are sent from this interface";
          leaf seconds {
            type uint32 {
              range "1..65535";
            }
          } //seconds

        } //container csnp-interval

        leaf default-instance {
          type boolean;
          description
              "Enable/disable default instance on the interface";
        }

        container hello-auth-keychain {
          description
              "Configure authentication keychain to use for the session";
          leaf name {
            type string {
              length "1..32";
            }
            description
                "keychain-name (32 char max)";
          } //name

        } //container hello-auth-keychain

        leaf hello-authentication {
          type boolean;
          description
              "Enable/disable hello-authentication on the interface";
        }

        container hello-authentication-key {
          description
              "Configure the authentication-key";
          leaf authentication-key-hash-key {
            type string {
              length "1..500";
            }
            description
                "authentication-key - [254 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container hello-authentication-key

        container hello-authentication-type {
          description
              "Configure hello-authentication-type to be enabled";
          leaf password-message-digest {
            type enumeration {
              enum password;
              enum message-digest;
            }
            description
                "keywords - specify authentication type";
          } //password-message-digest

        } //container hello-authentication-type

        container hello-padding {
          description
              "Configure padding on ISIS hello packets";
          leaf hello-padding-id {
            type enumeration {
              enum none;
              enum adaptive;
              enum loose;
              enum strict;
            }
          } //hello-padding-id

        } //container hello-padding

        container interface-type {
          description
              "Configure the interface type to be either broadcast or point-to-point";
          leaf broadcast-point-to-point {
            type enumeration {
              enum broadcast;
              enum point-to-point;
            }
            description
                "keywords - specify interface type";
          } //broadcast-point-to-point

        } //container interface-type

        container ipv4-adjacency-sid {
          description
              "Configure ipv4-adjacency-sid";
          leaf label {
            type uint32 {
              range "1..1048575";
            }
            description
                "[1..1048575] - within srlb range";
          } //label

        } //container ipv4-adjacency-sid

        leaf ipv4-multicast-disable {
          type boolean;
          description
              "Disable IS-IS IPv4 multicast routing for the interface";
        }

        container ipv4-node-sid {
          description
              "Configure ipv4-node-sid";
          leaf index {
            type uint32;
          } //index

          leaf label {
            type uint32;
          } //label

          leaf clear-n-flag {
            type boolean;
          } //clear-n-flag

        } //container ipv4-node-sid

        container ipv6-adjacency-sid {
          description
              "Configure ipv6-adjacency-sid";
          leaf label {
            type uint32 {
              range "1..1048575";
            }
            description
                "[1..1048575] - within srlb range";
          } //label

        } //container ipv6-adjacency-sid

        leaf ipv6-multicast-disable {
          type boolean;
          description
              "Disable IS-IS IPv6 multicast routing for the interface";
        }

        container ipv6-node-sid {
          description
              "Configure ipv6-node-sid";
          leaf index {
            type uint32;
          } //index

          leaf label {
            type uint32;
          } //label

          leaf clear-n-flag {
            type boolean;
          } //clear-n-flag

        } //container ipv6-node-sid

        leaf ipv6-unicast-disable {
          type boolean;
          description
              "Disable IS-IS IPv6 unicast routing for the interface";
        }

        container level-capability {
          description
              "Specifies ISIS levels for this interface";
          leaf level-1-level-2-level-1-2 {
            type enumeration {
              enum level-1;
              enum level-2;
              enum level-1/2;
            }
            description
                "level";
          } //level-1-level-2-level-1-2

        } //container level-capability

        container lfa-policy-map {
          description
              "Configure a route-next-hop template";
          leaf route-nh-template {
            type string {
              length "1..32";
            }
          } //route-nh-template

        } //container lfa-policy-map

        container load-balancing-weight {
          description
              "Configure load-balancing-weight";
          leaf load-balancing-weight-id {
            type uint32;
          } //load-balancing-weight-id

        } //container load-balancing-weight

        leaf loopfree-alternate-exclude {
          type boolean;
          description
              "Enable/disable LFA for ISIS on this interface";
        }

        container lsp-pacing-interval {
          description
              "Configure the interval for sending LSPs from the interface";
          leaf milli-seconds {
            type uint32 {
              range "0..65535";
            }
          } //milli-seconds

        } //container lsp-pacing-interval

        container mesh-group {
          description
              "Configure mesh groups";
          leaf value {
            type uint64 {
              range "1..2000000000";
            }
          } //value

          leaf blocked {
            type boolean;
            description
                "keyword - specifies the interface to be blocked";
          } //blocked

        } //container mesh-group

        leaf passive {
          type boolean;
          description
              "Configure passive interface";
        }

        container retransmit-interval {
          description
              "Configure the minimum interval between LSP packets retransmission for the 
               given interface";
          leaf seconds {
            type uint32 {
              range "1..65535";
            }
          } //seconds

        } //container retransmit-interval

        leaf shutdown {
          type boolean;
          description
              "Administratively Enable/disable the interface";
        }

        leaf sid-protection {
          type boolean;
          description
              "Enable/disable the SID protection";
        }

        container tag {
          description
              "Configure a route tag to the IP addresses of an interface";
          leaf tag {
            type uint32 {
              range "1..4294967295";
            }
          } //tag

        } //container tag

        list level {
          key "level-id";
          description
              "Configure the default parameters for level one and two interfaces";
          leaf level-id {
            type enumeration {
              enum 1;
              enum 2;
            }
          } //level-id

          container hello-auth-keychain {
            description
                "Configure authentication keychain to use for the session";
            leaf name {
              type string {
                length "1..32";
              }
              description
                  "keychain-name (32 char max)";
            } //name

          } //container hello-auth-keychain

          container hello-authentication-key {
            description
                "Configure the authentication-key";
            leaf authentication-key-hash-key {
              type string {
                length "1..500";
              }
              description
                  "authentication-key - [254 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container hello-authentication-key

          container hello-authentication-type {
            description
                "Configure hello-authentication-type to be enabled";
            leaf password-message-digest {
              type enumeration {
                enum password;
                enum message-digest;
              }
              description
                  "keywords - specify authentication type";
            } //password-message-digest

          } //container hello-authentication-type

          container hello-interval {
            description
                "Configure hello-interval for this interface";
            leaf seconds {
              type uint32 {
                range "1..20000";
              }
            } //seconds

          } //container hello-interval

          container hello-multiplier {
            description
                "Configure hello-multiplier for this level";
            leaf multiplier {
              type int32 {
                range "2..100";
              }
            } //multiplier

          } //container hello-multiplier

          container hello-padding {
            description
                "Configure padding on ISIS hello packets";
            leaf hello-padding-id {
              type enumeration {
                enum none;
                enum adaptive;
                enum loose;
                enum strict;
              }
            } //hello-padding-id

          } //container hello-padding

          container ipv4-multicast-metric {
            description
                "Configure IS-IS interface metric for IPv4 multicast";
            leaf IPv4-multicast-metric {
              type uint32 {
                range "1..16777215";
              }
            } //IPv4-multicast-metric

          } //container ipv4-multicast-metric

          container ipv6-multicast-metric {
            description
                "Configure IS-IS interface metric for IPv6 multicast";
            leaf IPv6-multicast-metric {
              type uint32 {
                range "1..16777215";
              }
            } //IPv6-multicast-metric

          } //container ipv6-multicast-metric

          container ipv6-unicast-metric {
            description
                "Configure IS-IS interface metric for IPv6 unicast";
            leaf ipv6-metric {
              type uint32 {
                range "1..16777215";
              }
            } //ipv6-metric

          } //container ipv6-unicast-metric

          container metric {
            description
                "Configure IS-IS interface metric for IPv4 unicast";
            leaf ipv4-metric {
              type uint32 {
                range "1..16777215";
              }
            } //ipv4-metric

          } //container metric

          leaf passive {
            type boolean;
            description
                "Configure passive";
          }

          container priority {
            description
                "Configure the priority that serves to determine which router on a multi-access 
                 network becomes the designated router";
            leaf number {
              type uint16 {
                range "0..127";
              }
            } //number

          } //container priority

          container sd-offset {
            description
                "Configure the signal degrade offset";
            leaf sd-offset {
              type uint32 {
                range "1..16777215";
              }
            } //sd-offset

          } //container sd-offset

          container sf-offset {
            description
                "Configure the signal fail offset";
            leaf sf-offset {
              type uint32 {
                range "1..16777215";
              }
            } //sf-offset

          } //container sf-offset

        } //list level

      } //list interface

      list level {
        key "level";
        description
            "Configure the default global parameters both level one and two interfaces";
        leaf level {
          type enumeration {
            enum 1;
            enum 2;
          }
        } //level

        leaf advertise-router-capability {
          type boolean;
          description
              "Enable/disable router advertisement capabilities";
        }

        container auth-keychain {
          description
              "Configure TCP authentication keychain to use for the session";
          leaf name {
            type string {
              length "1..32";
            }
            description
                "keychain-name (32 char max)";
          } //name

        } //container auth-keychain

        container authentication-key {
          description
              "Configure the authentication-key to be used";
          leaf authentication-key-hash-key {
            type string {
              length "1..500";
            }
            description
                "authentication-key - [254 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        container authentication-type {
          description
              "Configure the authentication type to be used";
          leaf password-message-digest {
            type enumeration {
              enum password;
              enum message-digest;
            }
            description
                "keywords - specif authentication type";
          } //password-message-digest

        } //container authentication-type

        leaf csnp-authentication {
          type boolean;
          description
              "Enable/disable authentication per CSNP message type at ISIS level.";
        }

        leaf database-export-exclude {
          type boolean;
          description
              "Enable/disable database export at ISIS level";
        }

        container default-ipv4-multicast-metric {
          description
              "Configure default metric for IPv4 multicast";
          leaf ipv4-multicast-metric {
            type uint32 {
              range "1..16777215";
            }
          } //ipv4-multicast-metric

        } //container default-ipv4-multicast-metric

        container default-ipv6-multicast-metric {
          description
              "Configure default metric for IPv6 multicast";
          leaf ipv6-multicast-metric {
            type uint32 {
              range "1..16777215";
            }
          } //ipv6-multicast-metric

        } //container default-ipv6-multicast-metric

        container default-ipv6-unicast-metric {
          description
              "Configure default metric for IPv6 unicast";
          leaf ipv6-metric {
            type uint32 {
              range "1..16777215";
            }
          } //ipv6-metric

        } //container default-ipv6-unicast-metric

        container default-metric {
          description
              "Configure default metric for IPv4 unicast";
          leaf ipv4-metric {
            type uint32 {
              range "1..16777215";
            }
          } //ipv4-metric

        } //container default-metric

        container external-preference {
          description
              "Configure external-preference";
          leaf external-preference {
            type uint16 {
              range "1..255";
            }
          } //external-preference

        } //container external-preference

        leaf hello-authentication {
          type boolean;
          description
              "Enable/disable authentication per HELLO message type at ISIS level.";
        }

        container hello-padding {
          description
              "Configure padding on ISIS hello packets";
          leaf hello-padding-id {
            type enumeration {
              enum none;
              enum adaptive;
              enum loose;
              enum strict;
            }
          } //hello-padding-id

        } //container hello-padding

        leaf loopfree-alternate-exclude {
          type boolean;
          description
              "Enable/disable LFA at ISIS level.";
        }

        container lsp-mtu-size {
          description
              "Configure LSP mtu-size";
          leaf size {
            type uint16 {
              range "490..9190";
            }
          } //size

        } //container lsp-mtu-size

        container preference {
          description
              "Configure preference";
          leaf preference {
            type uint16 {
              range "1..255";
            }
          } //preference

        } //container preference

        leaf psnp-authentication {
          type boolean;
          description
              "Enable/disable authentication per PSNP message type at ISIS level.";
        }

        leaf wide-metrics-only {
          type boolean;
          description
              "Enable/disable wide-metrics advertisements in the LSPs";
        }

        container bier {
          presence
              "Configure BIER parameters";
          leaf shutdown {
            type boolean;
            description
                "Configure BIER admin state";
          }

          container template {
            description
                "Configure BIER template";
            leaf template-string {
              type string {
                length "1..32";
              }
            } //template-string

          } //container template

        } //container bier

      } //list level

      list link-group {
        key "link-group-name";
        description
            "Specifies ISIS link groups on the system";
        leaf link-group-name {
          type string {
            length "1..32";
          }
        } //link-group-name

        container description {
          description
              "Configure the description for the associated link group";
          leaf description-string {
            type string {
            }
          } //description-string

        } //container description

        list level {
          key "level-id";
          description
              "Configure the default parameters for level one and two link groups";
          leaf level-id {
            type enumeration {
              enum 1;
              enum 2;
            }
          } //level-id

          container ipv4-multicast-metric-offset {
            description
                "Configure the IPv4 multicast metric offset";
            leaf ipv4-multicast-metric-offset-id {
              type uint32 {
                range "1..16777215";
              }
            } //ipv4-multicast-metric-offset-id

          } //container ipv4-multicast-metric-offset

          container ipv4-unicast-metric-offset {
            description
                "Configure the IPv4 unicast metric offset";
            leaf ipv4-unicast-metric-offset-id {
              type uint32 {
                range "1..16777215";
              }
            } //ipv4-unicast-metric-offset-id

          } //container ipv4-unicast-metric-offset

          container ipv6-multicast-metric-offset {
            description
                "Configure the IPv6 multicast metric offset";
            leaf ipv6-multicast-metric-offset-id {
              type uint32 {
                range "1..16777215";
              }
            } //ipv6-multicast-metric-offset-id

          } //container ipv6-multicast-metric-offset

          container ipv6-unicast-metric-offset {
            description
                "Configure the IPv6 unicast metric offset";
            leaf ipv6-unicast-metric-offset-id {
              type uint32 {
                range "1..16777215";
              }
            } //ipv6-unicast-metric-offset-id

          } //container ipv6-unicast-metric-offset

          list member {
            key "interface-name";
            description
                "Configure the member interfaces";
            leaf interface-name {
              type string {
                length "1..32";
              }
            } //interface-name

          } //list member

          container oper-members {
            description
                "Configure the threshold for oper members";
            leaf oper-members-id {
              type uint32 {
                range "1..8";
              }
            } //oper-members-id

          } //container oper-members

          container revert-members {
            description
                "Configure the threshold for revert members";
            leaf revert-members-id {
              type uint32 {
                range "1..8";
              }
            } //revert-members-id

          } //container revert-members

        } //list level

      } //list link-group

      container loopfree-alternates {
        presence
            "Enable/disable fast re-route capability for ISIS";
        container exclude {
          description
              "Configure LFA exclude policies";
          container prefix-policy {
            description
                "Configure LFA exclude prefix policies";
            leaf-list prefix-policy {
              type string {
                length "1..32";
              }
              max-elements 5;
            } //prefix-policy

          } //container prefix-policy

        } //container exclude

        container remote-lfa {
          description
              "Enable/disable remote loopfree-alternate";
          leaf max-pq-cost {
            type uint32;
            default 4261412864;
            description
                "[0..4294967295] - default: 4261412864";
          } //max-pq-cost

          container node-protect {
            description
                "Enable/disable node protection";
            leaf max-pq-nodes {
              type uint32 {
                range "1..32";
              }
              default 16;
              description
                  "[1..32] - default: 16";
            } //max-pq-nodes

          } //container node-protect

        } //container remote-lfa

        container ti-lfa {
          description
              "Enable/disable Topology Independent loopfree-alternate";
          leaf max-sr-frr-labels {
            type uint32 {
              range "0..3";
            }
            default 2;
            description
                "[0..3] - default: 2";
          } //max-sr-frr-labels

          leaf node-protect {
            type boolean;
            description
                "Enable/disable node protection";
          }

        } //container ti-lfa

      } //container loopfree-alternates

      container multi-topology {
        presence
            "Enable/disable IS-IS multi-topology support";
        leaf ipv4-multicast {
          type boolean;
          description
              "Enable multi-topology TLVs and global support for MT3";
        }

        leaf ipv6-multicast {
          type boolean;
          description
              "Enable multi-topology TLVs and global support for MT4";
        }

        leaf ipv6-unicast {
          type boolean;
          description
              "Enable multi-topology TLVs and global support for MT2";
        }

      } //container multi-topology

      container segment-routing {
        presence
            "Configure ISIS segment-routing";
        container adj-sid-hold {
          description
              "Configure adjacency SID hold time";
          leaf seconds {
            type uint32 {
              range "1..300";
            }
            default 15;
            description
                "[1..300] - default: 15";
          } //seconds

        } //container adj-sid-hold

        container entropy-label {
          description
              "Configure entropy label capability";
          leaf entropy-label-id {
            type enumeration {
              enum force-disable;
              enum enable;
            }
          } //entropy-label-id

        } //container entropy-label

        container export-tunnel-table {
          description
              "Configure tunnel table export";
          leaf ldp {
            type boolean;
          } //ldp

        } //container export-tunnel-table

        container prefix-sid-range {
          description
              "Configure prefix-sid-range";
          leaf global {
            type boolean;
          } //global

          leaf start-label {
            type uint32 {
              range "0..524287";
            }
          } //start-label

          leaf max-index {
            type uint32 {
              range "1..524287";
            }
          } //max-index

        } //container prefix-sid-range

        leaf shutdown {
          type boolean;
          description
              "Administratively enable or disable segment-routing";
        }

        container srlb {
          description
              "Configure segment routing local block";
          leaf reserved-label-block-name {
            type string;
          } //reserved-label-block-name

        } //container srlb

        container tunnel-mtu {
          description
              "Configure tunnel MTU size";
          leaf tunnel-mtu-id {
            type uint32 {
              range "512..9198";
            }
          } //tunnel-mtu-id

        } //container tunnel-mtu

        container tunnel-table-pref {
          description
              "Configure tunnel-table-preference";
          leaf tunnel-table-pref-id {
            type uint32 {
              range "1..255";
            }
          } //tunnel-table-pref-id

        } //container tunnel-table-pref

        list adjacency-set {
          key "adjacency-set-id";
          description
              "Configure adjacency-set";
          leaf adjacency-set-id {
            type uint32 {
              range "1..4294967295";
            }
          } //adjacency-set-id

          container family {
            description
                "Configure adjacency-set family";
            leaf family-id {
              type enumeration {
                enum ipv4;
                enum ipv6;
              }
            } //family-id

          } //container family

          container parallel {
            description
                "Configure parallel option";
            leaf no-advertise {
              type boolean;
            } //no-advertise

          } //container parallel

          container sid {
            description
                "Configure adjacency-sid";
            leaf label {
              type uint32 {
                range "1..1048575";
              }
              description
                  "[1..1048575] - within srlb range";
            } //label

          } //container sid

        } //list adjacency-set

        container mapping-server {
          presence
              "Configure segment routing mapping server";
          leaf shutdown {
            type boolean;
            description
                "Administratively enable or disable ISIS SR mapping server";
          }

          list sid-map {
            key "node-sid index";
            description
                "Configure ISIS SR mapping server SID map";
            leaf node-sid {
              type boolean;
            } //node-sid

            leaf index {
              type uint32;
            } //index

            leaf range {
              type uint16;
            } //range

            leaf prefix {
              type string;
              description
                  "Attribute ip-address[/mask] for sid-map";
            } //prefix

            leaf netmask {
              type string;
              description
                  "a.b.c.d (network bits all 1 and host bits all 0)";
            } //netmask

            leaf set-flags {
              type enumeration {
                enum s;
              }
            } //set-flags

            leaf level {
              type enumeration {
                enum 1;
                enum 2;
                enum 1/2;
              }
            } //level

            leaf clear-n-flag {
              type boolean;
            } //clear-n-flag

          } //list sid-map

        } //container mapping-server

      } //container segment-routing

      container timers {
        description
            "Configure ISIS timers";
        container lsp-wait {
          description
              "Configure ISIS LSP wait times";
          leaf lsp-wait {
            type uint32 {
              range "10..120000";
            }
            description
                "[10..120000] in milliseconds";
          } //lsp-wait

          leaf lsp-initial-wait {
            type uint32 {
              range "10..100000";
            }
            description
                "[10..100000] in milliseconds";
          } //lsp-initial-wait

          leaf lsp-second-wait {
            type uint32 {
              range "10..100000";
            }
            description
                "[10..100000] in milliseconds";
          } //lsp-second-wait

        } //container lsp-wait

        container spf-wait {
          description
              "Configure ISIS SPF wait times";
          leaf spf-wait {
            type uint32 {
              range "10..120000";
            }
            description
                "[10..120000] in milliseconds";
          } //spf-wait

          leaf spf-initial-wait {
            type uint32 {
              range "10..100000";
            }
            description
                "[10..100000] in milliseconds";
          } //spf-initial-wait

          leaf spf-second-wait {
            type uint32 {
              range "10..100000";
            }
            description
                "[10..100000] in milliseconds";
          } //spf-second-wait

        } //container spf-wait

      } //container timers

    } //list isis

  } //grouping alu-conf-router-isis-r13

} //module  alu-conf-router-isis-r13
