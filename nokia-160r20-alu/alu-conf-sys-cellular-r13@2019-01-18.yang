module alu-conf-sys-cellular-r13 {
  yang-version "1";

  namespace "urn:alcatel-lucent.com:sros:ns:yang:conf-sys-cellular-r13";

  prefix "conf-sys-cellular-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure system-wide cellular parameters on 
       SR OS based routers. 
       
       Copyright 2014-2015 Alcatel-Lucent, 2016 Nokia. All rights reserved. 
       Reproduction of this document is authorized on the condition that the 
       foregoing copyright notice is included. 
       
       This alu-conf-sys-cellular-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-01-18";

  grouping alu-conf-sys-cellular-r13 {
    container cellular {
      description
          "Configure system-wide cellular parameters";
      list pdn-profile {
        key "pdn-profile-number";
        description
            "Configure Packet Data Network (PDN) profile parameters";
        leaf pdn-profile-number {
          type uint32 {
            range "1..2";
          }
        } //pdn-profile-number

        container apn {
          description
              "Configure the Access Point Name";
          leaf apn-string {
            type string {
              length "1..100";
            }
          } //apn-string

        } //container apn

        container authentication {
          description
              "Configure the method of authentication for the PDN";
          leaf authentication-id {
            type enumeration {
              enum pap;
              enum chap;
            }
          } //authentication-id

        } //container authentication

        container description {
          description
              "Configure the description for this profile";
          leaf description-string {
            type string {
            }
          } //description-string

        } //container description

        container password {
          description
              "Configure the password for pap/chap authentication";
          leaf password {
            type string {
              length "1..500";
            }
            description
                "[64 chars max]";
          } //password

          leaf hash-hash2-custom {
            type enumeration {
              enum hash;
              enum hash2;
              enum custom;
            }
          } //hash-hash2-custom

        } //container password

        container username {
          description
              "Configure the username for pap/chap authentication";
          leaf username-string {
            type string {
              length "1..255";
            }
          } //username-string

        } //container username

      } //list pdn-profile

    } //container cellular

  } //grouping alu-conf-sys-cellular-r13

} //module  alu-conf-sys-cellular-r13
