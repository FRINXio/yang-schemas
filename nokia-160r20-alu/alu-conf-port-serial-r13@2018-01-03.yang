module alu-conf-port-serial-r13 {
  yang-version "1";

  namespace "urn:alcatel-lucent.com:sros:ns:yang:conf-port-serial-r13";

  prefix "conf-port-serial-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure attributes for a Serial port on SR 
       OS based routers. 
       
       Copyright 2014-2015 Alcatel-Lucent, 2016 Nokia. All rights reserved. 
       Reproduction of this document is authorized on the condition that the 
       foregoing copyright notice is included. 
       
       This alu-conf-port-serial-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-01-03";

  grouping alu-conf-port-serial-r13 {
    container serial {
      description
          "Configure attributes for a Serial port";
      container rs232 {
        description
            "Configure RS-232 channel parameters";
        container character-length {
          description
              "Configure the number of data bits in a character";
          leaf t6-7-8 {
            type enumeration {
              enum 6;
              enum 7;
              enum 8;
            }
            description
                "keywords";
          } //t6-7-8

        } //container character-length

        container hold-time {
          description
              "Configure a channels dampening timers in 100s of milliseconds";
          leaf up {
            type uint32 {
              range "0..100";
            }
            description
                "[0..100] in 100s of milliseconds";
          } //up

          leaf down {
            type uint32 {
              range "0..100";
            }
            description
                "[0..100] in 100s of milliseconds";
          } //down

        } //container hold-time

        container loopback {
          description
              "Activate a loopback on the channel";
          leaf bidir-e {
            type enumeration {
              enum bidir-e;
            }
            description
                "bidirectional Loopback E is closer to line";
          } //bidir-e

        } //container loopback

        container parity {
          description
              "Configure the parity bit in a character";
          leaf odd-even-mark-space {
            type enumeration {
              enum odd;
              enum even;
              enum mark;
              enum space;
            }
            description
                "keywords";
          } //odd-even-mark-space

        } //container parity

        container speed {
          description
              "Configure the speed of the interface";
          leaf speed-id {
            type enumeration {
              enum 600;
              enum 1200;
              enum 2400;
              enum 4800;
              enum 9600;
              enum 19200;
              enum 38400;
              enum 57600;
              enum 115200;
            }
          } //speed-id

        } //container speed

        container stop-bits {
          description
              "Configure the number of stop bits in a character";
          leaf t1-2 {
            type enumeration {
              enum 1;
              enum 2;
            }
            description
                "keywords";
          } //t1-2

        } //container stop-bits

        container control-lead {
          description
              "Configure control lead parameters";
          container input {
            description
                "Configure input control lead parameters";
            container dtr-dsr {
              description
                  "Configure input control lead Data Terminal Ready (DCE) / Data Set Ready (DTE)";
              leaf high-low {
                type enumeration {
                  enum high;
                  enum low;
                }
                description
                    "ASSUMED_ON|ASSUMED_OFF";
              } //high-low

            } //container dtr-dsr

            container rts-dcd {
              description
                  "Configure input control lead Request To Send (DCE) / Data Carrier Detect (DTE)";
              leaf high-low {
                type enumeration {
                  enum high;
                  enum low;
                }
                description
                    "ASSUMED_ON|ASSUMED_OFF";
              } //high-low

            } //container rts-dcd

          } //container input

          container monitor {
            description
                "Configure monitor control lead parameters";
            container dtr-dsr {
              description
                  "Configure monitoring for control lead Data Terminal Ready (DCE) / Data Set 
                   Ready (DTE)";
              leaf on-off {
                type enumeration {
                  enum on;
                  enum off;
                }
              } //on-off

            } //container dtr-dsr

            container rts-dcd {
              description
                  "Configure monitoring for control lead Request To Send (DCE) / Data Carrier 
                   Detect (DTE)";
              leaf on-off {
                type enumeration {
                  enum on;
                  enum off;
                }
              } //on-off

            } //container rts-dcd

          } //container monitor

          container output {
            description
                "Configure output control lead parameters";
            container cts-alb {
              description
                  "Configure output control lead Clear To Send (DCE) / Analog LoopBack (DTE)";
              leaf high-low {
                type enumeration {
                  enum high;
                  enum low;
                }
                description
                    "FORCED_ON|FORCED_OFF";
              } //high-low

            } //container cts-alb

            container dcd-rts {
              description
                  "Configure input control lead Data Carrier Detect (DCE) / Request To Send (DTE)";
              leaf high-low {
                type enumeration {
                  enum high;
                  enum low;
                }
                description
                    "FORCED_ON|FORCED_OFF";
              } //high-low

            } //container dcd-rts

            container ri-rdl {
              description
                  "Configure output control lead Ring Indicator (DCE) / Remote Digital Loopback 
                   (DTE)";
              leaf high-low {
                type enumeration {
                  enum high;
                  enum low;
                }
                description
                    "FORCED_ON|FORCED_OFF";
              } //high-low

            } //container ri-rdl

          } //container output

        } //container control-lead

        container socket {
          description
              "Create/delete Serial sockets";
          container rx {
            description
                "Configure receive parameters";
            container squelch-delay {
              description
                  "Configure the delay before squelch is automatically applied";
              leaf seconds {
                type uint32;
                description
                    "Attribute seconds for squelch-delay";
              } //seconds

            } //container squelch-delay

            leaf squelch-reset {
              type boolean;
              description
                  "Manually reset squelch";
            }

            container unsquelch-delay {
              description
                  "Configure the delay before squelch is automatically cleared";
              leaf seconds {
                type uint32;
                description
                    "Attribute seconds for unsquelch-delay";
              } //seconds

            } //container unsquelch-delay

            container eop {
              description
                  "Configure end of packet parameters";
              container idle-timeout {
                description
                    "Configure the maximum period of idle time since the last rx character to 
                     trigger EOP";
                leaf milliseconds {
                  type uint32 {
                    range "0..60000";
                  }
                  description
                      "Attribute milliseconds for idle-timeout";
                } //milliseconds

              } //container idle-timeout

              container length {
                description
                    "Configure the maximum number of rx characters to trigger EOP";
                leaf bytes {
                  type uint32 {
                    range "0..9194";
                  }
                  description
                      "Attribute bytes for length";
                } //bytes

              } //container length

              container special-char {
                description
                    "Configure the numerical value of the special rx character to trigger EOP";
                leaf value {
                  type string;
                  description
                      "Attribute value for special-char";
                } //value

              } //container special-char

            } //container eop

          } //container rx

          container tx {
            description
                "Configure transmit parameters";
            container inter-session-delay {
              description
                  "Configure the delay between finishing the current session and starting the 
                   next session";
              leaf milliseconds {
                type uint32 {
                  range "0..60000";
                }
                description
                    "Attribute milliseconds for inter-session-delay";
              } //milliseconds

            } //container inter-session-delay

          } //container tx

        } //container socket

      } //container rs232

    } //container serial

  } //grouping alu-conf-port-serial-r13

} //module  alu-conf-port-serial-r13
