module alu-conf-svc-vpls-split-r13 {
  yang-version "1";

  namespace "urn:alcatel-lucent.com:sros:ns:yang:conf-svc-vpls-split-r13";

  prefix "conf-svc-vpls-split-r13";

  import alu-types {
    prefix "alu";
  }

  alu:alu-major-release "rel16";

  organization "Alcatel-Lucent";

  contact
      "Alcatel-Lucent SR OS Support 
       Web: <http://www.alcatel-lucent.com>";

  description
      "Alcatel-Lucent YANG Data model to configure split horizon groups on SR OS 
       based routers. 
       
       Copyright 2014-2015 Alcatel-Lucent, 2016 Nokia. All rights reserved. 
       Reproduction of this document is authorized on the condition that the 
       foregoing copyright notice is included. 
       
       This alu-conf-svc-vpls-split-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2017-09-06";

  grouping alu-conf-svc-vpls-split-r13 {
    list split-horizon-group {
      key "group-name";
      description
          "Configure split horizon groups";
      leaf group-name {
        type string {
          length "1..32";
        }
      } //group-name

      leaf residential-group {
        type boolean;
        description
            "keyword - only allowed during creation";
      } //residential-group

      leaf auto-learn-mac-protect {
        type boolean;
        description
            "Enable/disable automatic update of MAC protect list";
      }

      container description {
        description
            "Description for this group";
        leaf description-string {
          type string {
            length "1..80";
          }
        } //description-string

      } //container description

      container restrict-protected-src {
        description
            "Enable/disable protected src MAC restriction (applies only to SAPs)";
        leaf alarm-only {
          type boolean;
          description
              "keyword - only trap on a protected MAC (applies only to SAPs)";
        } //alarm-only

        leaf discard-frame {
          type boolean;
          description
              "keyword - discard frame and trap on a protected MAC";
        } //discard-frame

      } //container restrict-protected-src

      leaf restrict-unprotected-dst {
        type boolean;
        description
            "Enable/disable unprotected dest MAC restriction";
      }

    } //list split-horizon-group

  } //grouping alu-conf-svc-vpls-split-r13

} //module  alu-conf-svc-vpls-split-r13
