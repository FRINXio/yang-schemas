module alu-conf-svc-vprn-dhcps-r13 {
  yang-version "1";

  namespace "urn:alcatel-lucent.com:sros:ns:yang:conf-svc-vprn-dhcps-r13";

  prefix "conf-svc-vprn-dhcps-r13";

  import alu-types {
    prefix "alu";
  }
  import ietf-inet-types {
    prefix "inet";
  }

  alu:alu-major-release "rel16";

  organization "Alcatel-Lucent";

  contact
      "Alcatel-Lucent SR OS Support 
       Web: <http://www.alcatel-lucent.com>";

  description
      "Alcatel-Lucent YANG Data model to configure local DHCP servers for VPRN 
       services on SR OS based routers. 
       
       Copyright 2014-2015 Alcatel-Lucent, 2016 Nokia. All rights reserved. 
       Reproduction of this document is authorized on the condition that the 
       foregoing copyright notice is included. 
       
       This alu-conf-svc-vprn-dhcps-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-05-31";

  grouping alu-conf-svc-vprn-dhcps-r13 {
    container dhcp {
      description
          "Configure local DHCP servers for VPRN services";
      list local-dhcp-server {
        key "server-name";
        description
            "Configure the local DHCP server";
        leaf server-name {
          type string {
            length "1..32";
          }
        } //server-name

        container description {
          description
              "Description for this local DHCP server";
          leaf description-string {
            type string {
              length "1..80";
            }
          } //description-string

        } //container description

        leaf force-renews {
          type boolean;
          description
              "Enable/disable sending FORCERENEW messages";
        }

        container lease-hold-time {
          description
              "Configure the lease hold time";
          leaf days {
            type uint32 {
              range "0..7305";
            }
          } //days

          leaf hrs {
            type uint32 {
              range "0..23";
            }
          } //hrs

          leaf min {
            type uint32 {
              range "0..59";
            }
          } //min

          leaf sec {
            type uint32 {
              range "0..59";
            }
          } //sec

        } //container lease-hold-time

        leaf shutdown {
          type boolean;
          description
              "Administratively enable/disable the local DHCP server";
        }

        container use-gi-address {
          description
              "Enable/disable use of GI address matching";
          leaf scope {
            type enumeration {
              enum subnet;
              enum pool;
            }
          } //scope

        } //container use-gi-address

        container use-pool-from-client {
          description
              "Enable/disable use of pool indicated by DHCP client";
          leaf delimiter {
            type string {
              length "1";
            }
          } //delimiter

        } //container use-pool-from-client

        container user-db {
          description
              "Assign a local user database for authentication";
          leaf local-user-db-name {
            type string {
              length "1..32";
            }
          } //local-user-db-name

        } //container user-db

        container user-ident {
          description
              "Configure the user identification method";
          leaf user-ident-id {
            type enumeration {
              enum client-id;
              enum circuit-id;
              enum mac;
              enum mac-circuit-id;
              enum remote-id;
            }
          } //user-ident-id

        } //container user-ident

        container failover {
          description
              "Configure failover";
          leaf ignore-mclt-on-takeover {
            type boolean;
            description
                "Ignore the Maximum Client Lead Time delay while taking over the peer address 
                 space";
          }

          container maximum-client-lead-time {
            description
                "Configure the maximum client lead time";
            leaf hrs {
              type int32 {
                range "1..23";
              }
            } //hrs

            leaf min {
              type int32 {
                range "1..59";
              }
            } //min

            leaf sec {
              type int32 {
                range "1..59";
              }
            } //sec

          } //container maximum-client-lead-time

          container partner-down-delay {
            description
                "Configure the partner-down delay";
            leaf hrs {
              type int32 {
                range "1..23";
              }
            } //hrs

            leaf min {
              type int32 {
                range "1..59";
              }
            } //min

            leaf sec {
              type int32 {
                range "0..59";
              }
            } //sec

          } //container partner-down-delay

          container peer {
            description
                "Create a sync tag";
            leaf ip-address {
              type string;
              description
                  "Attribute ip-address for peer";
            } //ip-address

            leaf tag {
              type string {
                length "1..32";
              }
            } //tag

          } //container peer

          leaf shutdown {
            type boolean;
            description
                "Administratively enable/disable the failover facility";
          }

          container startup-wait-time {
            description
                "Configure the startup wait time";
            leaf min {
              type int32 {
                range "1..59";
              }
            } //min

            leaf sec {
              type int32 {
                range "1..59";
              }
            } //sec

            leaf hrs {
              type uint32 {
              }
            } //hrs

          } //container startup-wait-time

        } //container failover

        container lease-hold-time-for {
          presence
              "Configure additional cases to apply the lease-hold-time to (other than 
               unsolicited releases)";
          leaf internal-lease-ipsec {
            type boolean;
            description
                "Apply the lease hold timer also to internal ipsec leases";
          }

          leaf solicited-release {
            type boolean;
            description
                "Apply the lease hold timer also for solicited releases";
          }

        } //container lease-hold-time-for

        list pool {
          key "pool-name";
          description
              "Configure an IP address pool";
          leaf pool-name {
            type string {
              length "1..32";
            }
          } //pool-name

          container description {
            description
                "Description for this IP address pool";
            leaf description-string {
              type string {
                length "1..80";
              }
            } //description-string

          } //container description

          container max-lease-time {
            description
                "Configure the maximum lease time";
            leaf days {
              type int32 {
                range "0..3650";
              }
            } //days

            leaf hrs {
              type int32 {
                range "0..23";
              }
            } //hrs

            leaf min {
              type int32 {
                range "0..59";
              }
            } //min

            leaf sec {
              type int32 {
                range "0..59";
              }
            } //sec

          } //container max-lease-time

          container min-lease-time {
            description
                "Configure the minimum lease time";
            leaf days {
              type int32 {
                range "0..3650";
              }
            } //days

            leaf hrs {
              type int32 {
                range "0..23";
              }
            } //hrs

            leaf min {
              type int32 {
                range "0..59";
              }
            } //min

            leaf sec {
              type int32 {
                range "0..59";
              }
            } //sec

          } //container min-lease-time

          container minimum-free {
            description
                "Configure the minimum number of free addresses";
            leaf minimum-free {
              type uint32 {
                range "0..255";
              }
            } //minimum-free

            leaf percent {
              type boolean;
              description
                  "keyword - Indicates the value indicates a percentage";
            } //percent

            leaf event-when-depleted {
              type boolean;
              description
                  "keyword";
            } //event-when-depleted

          } //container minimum-free

          leaf nak-non-matching-subnet {
            type boolean;
            description
                "Configure this server to reply with DHCPNAK to DHCPREQUEST for a subnet that 
                 does not match any range in this pool (rather than silently drop the request)";
          }

          container offer-time {
            description
                "Configure the offer time";
            leaf min {
              type int32 {
                range "0..10";
              }
            } //min

            leaf sec {
              type int32 {
                range "0..59";
              }
            } //sec

          } //container offer-time

          container failover {
            description
                "Configure failover";
            leaf ignore-mclt-on-takeover {
              type boolean;
              description
                  "Ignore the Maximum Client Lead Time delay while taking over the pool address 
                   space from the partner";
            }

            container maximum-client-lead-time {
              description
                  "Configure the maximum client lead time";
              leaf hrs {
                type int32 {
                  range "1..23";
                }
              } //hrs

              leaf min {
                type int32 {
                  range "1..59";
                }
              } //min

              leaf sec {
                type int32 {
                  range "1..59";
                }
              } //sec

            } //container maximum-client-lead-time

            container partner-down-delay {
              description
                  "Configure the partner-down delay";
              leaf hrs {
                type int32 {
                  range "1..23";
                }
              } //hrs

              leaf min {
                type int32 {
                  range "1..59";
                }
              } //min

              leaf sec {
                type int32 {
                  range "0..59";
                }
              } //sec

            } //container partner-down-delay

            container peer {
              description
                  "Create a sync tag";
              leaf ip-address {
                type string;
                description
                    "Attribute ip-address for peer";
              } //ip-address

              leaf tag {
                type string {
                  length "1..32";
                }
              } //tag

            } //container peer

            leaf shutdown {
              type boolean;
              description
                  "Administratively enable/disable the failover facility";
            }

            container startup-wait-time {
              description
                  "Configure the startup wait time";
              leaf min {
                type int32 {
                  range "1..59";
                }
              } //min

              leaf sec {
                type int32 {
                  range "1..59";
                }
              } //sec

              leaf hrs {
                type uint32 {
                }
              } //hrs

            } //container startup-wait-time

          } //container failover

          container options {
            description
                "Configure pool-specific DHCP options";
            list custom-option {
              key "option-number";
              description
                  "Configure a DHCP option";
              leaf option-number {
                type int32 {
                  range "1..254";
                }
              } //option-number

              leaf-list address {
                type inet:ip-address;
                max-elements 4;
              } //address

              leaf string {
                type string {
                  length "1..127";
                }
              } //string

              leaf hex {
                type string {
                }
                description
                    "[0x0..0xFFFFFFFF...(max 254 hex nibbles)]";
              } //hex

            } //list custom-option

            container dns-server {
              description
                  "Configure the DNS server";
              leaf-list ip-address {
                type inet:ip-address;
                max-elements 4;
              } //ip-address

            } //container dns-server

            container domain-name {
              description
                  "Configure the domain name";
              leaf domain-name {
                type string {
                  length "1..127";
                }
              } //domain-name

            } //container domain-name

            container lease-rebind-time {
              description
                  "Configure the lease rebind time";
              leaf days {
                type int32 {
                  range "0..3650";
                }
              } //days

              leaf hrs {
                type int32 {
                  range "0..23";
                }
              } //hrs

              leaf min {
                type int32 {
                  range "0..59";
                }
              } //min

              leaf sec {
                type int32 {
                  range "0..59";
                }
              } //sec

            } //container lease-rebind-time

            container lease-renew-time {
              description
                  "Configure the lease renew time";
              leaf days {
                type int32 {
                  range "0..3650";
                }
              } //days

              leaf hrs {
                type int32 {
                  range "0..23";
                }
              } //hrs

              leaf min {
                type int32 {
                  range "0..59";
                }
              } //min

              leaf sec {
                type int32 {
                  range "0..59";
                }
              } //sec

            } //container lease-renew-time

            container lease-time {
              description
                  "Configure the lease time";
              leaf days {
                type int32 {
                  range "0..3650";
                }
              } //days

              leaf hrs {
                type int32 {
                  range "0..23";
                }
              } //hrs

              leaf min {
                type int32 {
                  range "0..59";
                }
              } //min

              leaf sec {
                type int32 {
                  range "0..59";
                }
              } //sec

            } //container lease-time

            container netbios-name-server {
              description
                  "Configure the netbios name server";
              leaf-list ip-address {
                type inet:ip-address;
                max-elements 4;
              } //ip-address

            } //container netbios-name-server

            container netbios-node-type {
              description
                  "Configure the netbios node type";
              leaf netbios-node-type {
                type string {
                  length "1";
                }
                description
                    "B|P|M|H";
              } //netbios-node-type

            } //container netbios-node-type

          } //container options

          list subnet {
            key "ip-address-mask netmask";
            description
                "Configure a subnet";
            leaf ip-address-mask {
              type string;
              description
                  "ip-address a.b.c.d (no multicast address) 
                   mask [8..30]";
            } //ip-address-mask

            leaf netmask {
              type string;
              description
                  "a.b.c.d any mask expressed as dotted quad";
            } //netmask

            list address-range {
              key "start-ip-address end-ip-address";
              description
                  "Include range of IP addresses";
              leaf start-ip-address {
                type inet:ip-address;
              } //start-ip-address

              leaf end-ip-address {
                type inet:ip-address;
              } //end-ip-address

              leaf failover {
                type enumeration {
                  enum local;
                  enum remote;
                  enum access-driven;
                }
              } //failover

            } //list address-range

            leaf drain {
              type boolean;
              description
                  "Configure the subnet draining";
            }

            list exclude-addresses {
              key "start-ip-address end-ip-address";
              description
                  "Exclude range of IP addresses";
              leaf start-ip-address {
                type inet:ip-address;
              } //start-ip-address

              leaf end-ip-address {
                type inet:ip-address;
              } //end-ip-address

            } //list exclude-addresses

            container maximum-declined {
              description
                  "Configure the maximum number of declined addresses";
              leaf maximum-declined {
                type uint32;
              } //maximum-declined

            } //container maximum-declined

            container minimum-free {
              description
                  "Configure the minimum number of free addresses";
              leaf minimum-free {
                type uint32 {
                  range "0..255";
                }
              } //minimum-free

              leaf percent {
                type boolean;
                description
                    "keyword - Indicates the value indicates a percentage";
              } //percent

              leaf event-when-depleted {
                type boolean;
                description
                    "keyword";
              } //event-when-depleted

            } //container minimum-free

            container options {
              description
                  "Configure subnet-specific DHCP options";
              list custom-option {
                key "option-number";
                description
                    "Configure a DHCP option";
                leaf option-number {
                  type int32 {
                    range "1..254";
                  }
                } //option-number

                leaf-list address {
                  type inet:ip-address;
                  max-elements 4;
                } //address

                leaf string {
                  type string {
                    length "1..127";
                  }
                } //string

                leaf hex {
                  type string {
                  }
                  description
                      "[0x0..0xFFFFFFFF...(max 254 hex nibbles)]";
                } //hex

              } //list custom-option

              container default-router {
                description
                    "Configure the default router";
                leaf-list ip-address {
                  type inet:ip-address;
                  max-elements 4;
                } //ip-address

              } //container default-router

              container subnet-mask {
                description
                    "Configure the subnet mask";
                leaf ip-address {
                  type inet:ip-address;
                } //ip-address

              } //container subnet-mask

            } //container options

          } //list subnet

        } //list pool

      } //list local-dhcp-server

    } //container dhcp

  } //grouping alu-conf-svc-vprn-dhcps-r13

} //module  alu-conf-svc-vprn-dhcps-r13
