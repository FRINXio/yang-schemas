module Cisco-IOS-XR-tty-server-oper {

  /*** NAMESPACE / PREFIX DEFINITION ***/

  namespace "http://cisco.com/ns/yang/Cisco-IOS-XR-tty-server-oper";


  prefix "tty-server-oper";

  /*** LINKAGE (IMPORTS / INCLUDES) ***/

  import Cisco-IOS-XR-types { prefix "xr"; }

  import Cisco-IOS-XR-tty-management-datatypes { prefix "dt1"; }

  include Cisco-IOS-XR-tty-server-oper-sub5 {
    revision-date 2015-07-30;
  }

  include Cisco-IOS-XR-tty-server-oper-sub4 {
    revision-date 2015-07-30;
  }

  include Cisco-IOS-XR-tty-server-oper-sub3 {
    revision-date 2015-07-30;
  }

  include Cisco-IOS-XR-tty-server-oper-sub2 {
    revision-date 2015-07-30;
  }

  include Cisco-IOS-XR-tty-server-oper-sub1 {
    revision-date 2015-07-30;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tty-server package operational data.

     This module contains definitions
     for the following management objects:
       tty: TTY Line Configuration

     Copyright (c) 2013-2015 by Cisco Systems, Inc.
     All rights reserved.";

  revision "2015-07-30" {
    description
      "Descriptions updated.";
  }

  revision "2015-01-07" {
    description
      "IOS XR 5.3.1 revision.";
  }

  typedef Line-state {
    type enumeration {
      enum none {
        value 0;
        description "Line not connected";
      }
      enum registered {
        value 1;
        description "Line registered";
      }
      enum in-use {
        value 2;
        description "Line active and in use";
      }
    }
    description "Line state";
  }
  typedef Session-operation {
    type enumeration {
      enum none {
        value 0;
        description "No sessions on the line";
      }
      enum setup {
        value 1;
        description "Session getting set up";
      }
      enum shell {
        value 2;
        description "Session active with a shell";
      }
      enum transitioning {
        value 3;
        description "Session in transitioning phase";
      }
      enum packet {
        value 4;
        description "Session ready to receive packets";
      }
    }
    description "Session operation";
  }

  grouping STATE {
    description
      "Common node of console-line, vty-line,
      auxiliary-line";

    container state {
      xr:xr-xml-map "tty_server_oper:State";
      description "Line state information";

      container template {
        xr:xr-xml-map "tty_server_oper:Template";
        description
          "Information related to template applied to the
          line";
        leaf name {
          xr:xr-xml-map "tty_server_oper:Name";
          type string;
          description "Name of the template";
        }
      }

      container general {
        xr:xr-xml-map "tty_server_oper:General";
        description "General information";
        leaf operation {
          xr:xr-xml-map "tty_server_oper:Operation";
          type Session-operation;
          description "application running of on the tty line";
        }
        leaf general-state {
          xr:xr-xml-map "tty_server_oper:GeneralState";
          type Line-state;
          description "State of the line";
        }
      }
    }
  }

  grouping GENERAL-STATISTICS {
    description
      "Common node of console-statistics, vty-statistics
      , auxiliary-statistics";

    container general-statistics {
      xr:xr-xml-map "tty_server_oper:GeneralStatistics";
      description "General statistics of line";
      uses TTY-GENERAL-STATS;
    }
  }

  grouping AAA {
    description
      "Common node of console-statistics, vty-statistics
      , auxiliary-statistics";

    container aaa {
      xr:xr-xml-map "tty_server_oper:AAA";
      description "AAA related statistics";
      uses TTY-AAA-STATS;
    }
  }

  grouping RS232 {
    description
      "Common node of console-statistics,
      auxiliary-statistics";

    container rs232 {
      xr:xr-xml-map "tty_server_oper:RS232";
      description "RS232 statistics of console line";
      uses TTY-RS232-STATS;
    }
  }

  grouping EXEC {
    description
      "Common node of console-statistics, vty-statistics
      , auxiliary-statistics";

    container exec {
      xr:xr-xml-map "tty_server_oper:Exec";
      description "Exec related statistics";
      uses TTY-EXEC-PROP-STATS;
    }
  }

  grouping CONFIGURATION {
    description
      "Common node of console-line, vty-line,
      auxiliary-line";

    container configuration {
      xr:xr-xml-map "tty_server_oper:Configuration";
      description "Configuration information of the line";

      container connection-configuration {
        xr:xr-xml-map "tty_server_oper:ConnectionConfiguration";
        description "Conection configuration information";

        container transport-input {
          xr:xr-xml-map "tty_server_oper:TransportInput";
          description
            "Protocols to use when connecting to the
            terminal server";
          leaf select {
            xr:xr-xml-map "tty_server_oper:Select";
            type dt1:Tty-transport-protocol-select;
            default "all";
            description "Choose transport protocols";
          }
          leaf protocol1 {
            xr:xr-xml-map "tty_server_oper:Protocol1";
            when "../select = 'some'" {
              description "../Select = 2";
            }
            type dt1:Tty-transport-protocol;
            description "Transport protocol1";
          }
          leaf protocol2 {
            xr:xr-xml-map "tty_server_oper:Protocol2";
            when "../select = 'some'" {
              description "../Select = 2";
            }
            type dt1:Tty-transport-protocol;
            description "Transport protocol2";
          }
          leaf none {
            xr:xr-xml-map "tty_server_oper:None";
            type int32;
            description "Not used";
          }
        }
        leaf acl-out {
          xr:xr-xml-map "tty_server_oper:ACLOut";
          type string;
          description "ACL for outbound traffic";
        }
        leaf acl-in {
          xr:xr-xml-map "tty_server_oper:ACLIn";
          type string;
          description "ACL for inbound traffic";
        }
      }
    }
  }

  container tty {
    xr:xr-xml-map "tty_server_oper:TTY";
    config false;
    description "TTY Line Configuration";

    container console-nodes {
      xr:xr-xml-map "tty_server_oper:ConsoleNodeTable";
      description "List of Nodes for console";

      list console-node {
        xr:xr-xml-map "tty_server_oper:ConsoleNode";
        key "id";
        description "Console line configuration on a node";

        container console-line {
          xr:xr-xml-map "tty_server_oper:ConsoleLine";
          description "Console line";

          container console-statistics {
            xr:xr-xml-map "tty_server_oper:ConsoleStatistics";
            description "Statistics of the console line";
            uses RS232;
            uses GENERAL-STATISTICS;
            uses EXEC;
            uses AAA;
          }
          uses STATE;
          uses CONFIGURATION;
        }
        leaf id {
          xr:xr-xml-map "tty_server_oper:ID";
          type xr:Node-id;
          description "Node ID";
        }
      }
    }

    container vty-lines {
      xr:xr-xml-map "tty_server_oper:VTYLineTable";
      description "List of VTY lines";

      list vty-line {
        xr:xr-xml-map "tty_server_oper:VTYLine";
        key "line-number";
        description "VTY Line";

        container vty-statistics {
          xr:xr-xml-map "tty_server_oper:VTYStatistics";
          description "Statistics of the VTY line";

          container connection {
            xr:xr-xml-map "tty_server_oper:Connection";
            description "Connection related statistics";
            uses TTY-CONNECTION-STATS;
          }
          uses GENERAL-STATISTICS;
          uses EXEC;
          uses AAA;
        }
        leaf line-number {
          xr:xr-xml-map "tty_server_oper:LineNumber";
          type int32;
          description "VTY Line number";
        }
        uses STATE;
        uses CONFIGURATION;
      }
    }

    container auxiliary-nodes {
      xr:xr-xml-map "tty_server_oper:AuxiliaryNodeTable";
      description "List of Nodes attached with an auxiliary line";

      list auxiliary-node {
        xr:xr-xml-map "tty_server_oper:AuxiliaryNode";
        key "id";
        description "Line configuration on a node";

        container auxiliary-line {
          xr:xr-xml-map "tty_server_oper:AuxiliaryLine";
          description "Auxiliary line";

          container auxiliary-statistics {
            xr:xr-xml-map "tty_server_oper:AuxiliaryStatistics";
            description "Statistics of the auxiliary line";
            uses RS232;
            uses GENERAL-STATISTICS;
            uses EXEC;
            uses AAA;
          }
          uses STATE;
          uses CONFIGURATION;
        }
        leaf id {
          xr:xr-xml-map "tty_server_oper:ID";
          type xr:Node-id;
          description "Node ID";
        }
      }
    }
  }
}
