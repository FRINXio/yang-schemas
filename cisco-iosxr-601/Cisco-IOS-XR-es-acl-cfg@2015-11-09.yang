module Cisco-IOS-XR-es-acl-cfg {

  /*** NAMESPACE / PREFIX DEFINITION ***/

  namespace "http://cisco.com/ns/yang/Cisco-IOS-XR-es-acl-cfg";


  prefix "es-acl-cfg";

  /*** LINKAGE (IMPORTS / INCLUDES) ***/

  import Cisco-IOS-XR-types { prefix "xr"; }

  import Cisco-IOS-XR-common-acl-datatypes { prefix "dt1"; }

  include Cisco-IOS-XR-es-ace-cfg {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR es-acl package configuration.

     This module contains definitions
     for the following management objects:
       es-acl: Layer 2 ACL configuration data

     Copyright (c) 2013-2015 by Cisco Systems, Inc.
     All rights reserved.";

  revision "2015-11-09" {
    description
      "IOS XR 6.0 revision.";
  }

  typedef Es-acl-name {
    type xr:Cisco-ios-xr-string {
      length "0..65";
    }
    description "Es acl name";
  }

  container es-acl {
    xr:xr-xml-map "es_acl_cfg:ES_ACL";
    description "Layer 2 ACL configuration data";

    container accesses {
      xr:xr-xml-map "es_acl_cfg:AccessListTable";
      description "Table of access lists";

      list access {
        xr:xr-xml-map "es_acl_cfg:AccessList";
        key "name";
        description "An ACL";

        container access-list-entries {
          xr:xr-xml-map "es_acl_cfg:AccessListEntryTable";
          description
            "ACL entry table; contains list of access list
            entries";

          list access-list-entry {
            xr:xr-xml-map "es_acl_cfg:AccessListEntry";
            xr:xr-cli-map "ethernet-services access-list <string> ";
            key "sequence-number";
            description
              "An ACL entry; either a description (remark)
              or anAccess List Entry to match against";
            leaf sequence-number {
              xr:xr-xml-map "es_acl_cfg:SequenceNumber";
              type dt1:Acl-sequence-number-range;
              description "Sequence number of access list entry";
            }
            uses ES-ACL-CONFIG-ACE;
          }
        }
        leaf name {
          xr:xr-xml-map "es_acl_cfg:Name";
          type Es-acl-name;
          description "Name of the access list";
        }
      }
    }
  }
}
