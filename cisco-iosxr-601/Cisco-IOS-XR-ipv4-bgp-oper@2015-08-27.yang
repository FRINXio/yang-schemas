module Cisco-IOS-XR-ipv4-bgp-oper {

  /*** NAMESPACE / PREFIX DEFINITION ***/

  namespace "http://cisco.com/ns/yang/Cisco-IOS-XR-ipv4-bgp-oper";


  prefix "ipv4-bgp-oper";

  /*** LINKAGE (IMPORTS / INCLUDES) ***/

  import ietf-inet-types { prefix "inet"; }

  import Cisco-IOS-XR-types { prefix "xr"; }

  import Cisco-IOS-XR-ipv4-bgp-datatypes { prefix "dt1"; }

  include Cisco-IOS-XR-ipv4-bgp-oper-sub1 {
    revision-date 2015-08-27;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-bgp package operational data.

     This module contains definitions
     for the following management objects:
       bgp: BGP operational data

     Copyright (c) 2013-2015 by Cisco Systems, Inc.
     All rights reserved.";

  revision "2015-08-27" {
    description
      "IOS XR 5.3.2 revision.";
  }

  typedef Bgp-rpki-edm-af {
    type enumeration {
      enum ipv4 {
        value 2;
        description "IPv4";
      }
      enum ipv6 {
        value 26;
        description "IPv6";
      }
    }
    description "Bgp rpki edm af";
  }
  typedef Bgp-route {
    type enumeration {
      enum used {
        value 0;
        description "Used path from neighbor";
      }
      enum received-only {
        value 1;
        description "Received only path from neighbor";
      }
      enum rib {
        value 2;
        description "Redistributed from the RIB";
      }
      enum aggregate {
        value 3;
        description "Locally generated aggregate";
      }
    }
    description "Bgp route";
  }
  typedef Bgp-entity {
    type enumeration {
      enum af-group {
        value 0;
        description "Address family group";
      }
      enum session-group {
        value 1;
        description "Session group";
      }
      enum neighbor-group {
        value 2;
        description "Neighbor group";
      }
      enum neighbor {
        value 3;
        description "Neighbor";
      }
    }
    description "Bgp entity";
  }
  typedef Bgp-route-distinguisher {
    type string;
    description "Bgp route distinguisher";
  }

  grouping UPDATE-GENERATION-PROCESS {
    description "Common node of instance-active, instance-standby";

    container update-generation-process {
      xr:xr-xml-map "bgp_oper:UpdateGenerationProcess";
      description "Update generation for the process";
      uses BGP-UPDGEN-PROC-BAG;
    }
  }

  grouping PATH {
    description
      "Common node of path-table, path-used-table,
      path-labeled-table";

    list path {
      xr:xr-xml-map "bgp_oper:Path";
      description "A BGP path table entry";
      leaf rd {
        xr:xr-xml-map "bgp_oper:RD";
        type Bgp-route-distinguisher;
        description "Route Distinguisher value";
      }
      leaf network {
        xr:xr-xml-map "bgp_oper:Network";
        type inet:ip-prefix;
        description "Network in prefix/length format";
      }
      leaf neighbor-address {
        xr:xr-xml-map "bgp_oper:NeighborAddress";
        type inet:ip-address-no-zone;
        description "Neighbor adddress";
      }
      leaf route-type {
        xr:xr-xml-map "bgp_oper:RouteType";
        type Bgp-route;
        description "Route Type";
      }
      leaf source-rd {
        xr:xr-xml-map "bgp_oper:SourceRD";
        type Bgp-route-distinguisher;
        description "Source Route Distinguisher value";
      }
      leaf path-id {
        xr:xr-xml-map "bgp_oper:PathID";
        type int32;
        description "Received Path ID";
      }
      uses BGP-PATH-BAG;
    }
  }

  grouping BMP {
    description "Common node of default-vrf, vrf";

    container bmp {
      xr:xr-xml-map "bgp_oper:BMP";
      description "BMP related Operational Data";

      container server-summaries {
        xr:xr-xml-map "bgp_oper:ServerSummaryTable";
        description "Table of BMP Servers";

        list server-summary {
          xr:xr-xml-map "bgp_oper:ServerSummary";
          key "server-id";
          description "Summary Information about BMP server";
          leaf server-id {
            xr:xr-xml-map "bgp_oper:ServerID";
            type uint32 {
              range "1..8";
            }
            description "BMP Server ID";
          }
          uses BGP-BMP-SRVR-BAG;
        }
      }

      container server-neighbors {
        xr:xr-xml-map "bgp_oper:ServerNeighborTable";
        description "Table of Neighbors for a BMP Server";

        list server-neighbor {
          xr:xr-xml-map "bgp_oper:ServerNeighbor";
          key "server-id";
          description
            "BMP Server under which neighbor info are
            needed";

          container monitored-neighbors {
            xr:xr-xml-map "bgp_oper:MonitoredNeighborTable";
            description
              "List of Neighbors under which BMP Server is
              confgiured";

            list monitored-neighbor {
              xr:xr-xml-map "bgp_oper:MonitoredNeighbor";
              key "neighbor-address";
              description
                "Information about a neighbor monitored by
                BMP server";
              leaf neighbor-address {
                xr:xr-xml-map "bgp_oper:NeighborAddress";
                type inet:ip-address-no-zone;
                description "Neighbor address";
              }
              uses BGP-BMP-NBR-BAG;
            }
          }
          leaf server-id {
            xr:xr-xml-map "bgp_oper:ServerID";
            type int32;
            description "BMP Server ID";
          }
        }
      }
    }
  }

  grouping ATTRIBUTE-FILTER-GROUP-TABLE {
    description "Common node of instance-active, instance-standby";

    container attribute-filter-groups {
      xr:xr-xml-map "bgp_oper:AttributeFilterGroupTable";
      description "All attribute-filter groups in this instance";

      list attribute-filter-group {
        xr:xr-xml-map "bgp_oper:AttributeFilterGroup";
        key "group-name";
        description "Attribute-filter group";
        leaf group-name {
          xr:xr-xml-map "bgp_oper:GroupName";
          type xr:Cisco-ios-xr-string;
          description "Attribute-filter group name";
        }
        uses BGP-ATTRFILTER-GROUP-BAG;
      }
    }
  }

  grouping NEXT-HOP-VRF-TABLE {
    description "Common node of default-vrf, vrf";

    container next-hop-vrfs {
      xr:xr-xml-map "bgp_oper:NextHopVRFTable";
      description "The BGP VRF table";

      list next-hop-vrf {
        xr:xr-xml-map "bgp_oper:NextHopVRF";
        key "process-id";
        description "A BGP Next-hop VRF table entry";
        leaf process-id {
          xr:xr-xml-map "bgp_oper:ProcessID";
          type int32;
          description "Process instance ID";
        }
        uses BGP-NEXTHOP-VRF-BAG;
      }
    }
  }

  grouping ATTRIBUTE-TABLE {
    description
      "Common node of instance-active, instance-standby,
      af";

    container attributes {
      xr:xr-xml-map "bgp_oper:AttributeTable";
      description "The BGP Attribute table";

      list attribute {
        xr:xr-xml-map "bgp_oper:Attribute";
        description "A BGP Attribute table entry";
        leaf process-id {
          xr:xr-xml-map "bgp_oper:ProcessID";
          type int32;
          description "Process instance ID";
        }
        leaf attribute-iid {
          xr:xr-xml-map "bgp_oper:AttributeIID";
          type int32;
          description "Attribute IID";
        }
        leaf attribute-cache-bucket {
          xr:xr-xml-map "bgp_oper:AttributeCacheBucket";
          type int32;
          description "Attribute cache bucket";
        }
        leaf attribute-cache-id {
          xr:xr-xml-map "bgp_oper:AttributeCacheID";
          type int32;
          description "Attribute cache ID";
        }
        uses BGP-ATTR-BAG;
      }
    }
  }

  grouping SESSION-TABLE {
    description "Common node of default-vrf, vrf";

    container sessions {
      xr:xr-xml-map "bgp_oper:SessionTable";
      description "The BGP session table";

      list session {
        xr:xr-xml-map "bgp_oper:Session";
        key "neighbor-address";
        description "A BGP session table entry";
        leaf neighbor-address {
          xr:xr-xml-map "bgp_oper:NeighborAddress";
          type inet:ip-address-no-zone;
          description "Neighbor address";
        }
        uses BGP-NBR-BRIEF-BAG;
      }
    }
  }

  grouping POSTIT-TABLE {
    description "Common node of default-vrf, vrf";

    container postits {
      xr:xr-xml-map "bgp_oper:PostitTable";
      description "The BGP Neighbor table";

      list postit {
        xr:xr-xml-map "bgp_oper:Postit";
        key "neighbor-address";
        description "A BGP Postit table entry";
        leaf neighbor-address {
          xr:xr-xml-map "bgp_oper:NeighborAddress";
          type inet:ip-address-no-zone;
          description "Neighbor address";
        }
        uses BGP-NEIGHBOR-NSR-BAG;
      }
    }
  }

  grouping UPDATE-INBOUND-ERROR-PROCESS {
    description "Common node of instance-active, instance-standby";

    container update-inbound-error-process {
      xr:xr-xml-map "bgp_oper:UpdateInboundErrorProcess";
      description
        "Update inbound error information for the process";
      uses BGP-UPDERR-PROC-BAG;
    }
  }

  grouping PROCESS-INFO-TABLE {
    description "Common node of default-vrf, vrf";

    container process-infos {
      xr:xr-xml-map "bgp_oper:ProcessInfoTable";
      description "The BGP Process instance table";

      list process-info {
        xr:xr-xml-map "bgp_oper:ProcessInfo";
        key "process-id";
        description "A Process instance table entry";
        leaf process-id {
          xr:xr-xml-map "bgp_oper:ProcessID";
          type int32;
          description "Process Instance ID";
        }
        uses BGP-PROCESS-INFO-BAG;
      }
    }
  }

  grouping RPKI-SUMMARY {
    description "Common node of instance-active, instance-standby";

    container rpki-summary {
      xr:xr-xml-map "bgp_oper:RPKISummary";
      description "RPKI Summary Info";
      uses BGP-RPKI-SUMMARY-BAG;
    }
  }

  grouping VRF-TABLE {
    description "Common node of instance-active, instance-standby";

    container vrfs {
      xr:xr-xml-map "bgp_oper:VRFTable";
      description "VRF related operational data";

      list vrf {
        xr:xr-xml-map "bgp_oper:VRF";
        key "vrf-name";
        description "Operational data for a particular VRF";
        leaf vrf-name {
          xr:xr-xml-map "bgp_oper:VRFName";
          type xr:Cisco-ios-xr-string;
          description "Name of the VRF";
        }
        uses UPDATE-INBOUND-ERROR-VRF;
        uses AF-TABLE;
        uses INFORMATION;
        uses UPDATE-INBOUND-FILTER-VRF;
        uses POSTIT-TABLE;
        uses GLOBAL-PROCESS-INFO;
        uses PROCESS-INFO-TABLE;
        uses UPDATE-INBOUND-ERROR-NEIGHBOR-TABLE;
        uses UPDATE-INBOUND-FILTER-NEIGHBOR-TABLE;
        uses BMP;
        uses SESSION-TABLE;
        uses NEIGHBOR-TABLE;
        uses NEXT-HOP-VRF-TABLE;
        uses MESSAGE-LOG-TABLE;
      }
    }
  }

  grouping PROCESS-TABLE {
    description "Common node of instance-active, instance-standby";

    container processes {
      xr:xr-xml-map "bgp_oper:ProcessTable";
      description "BGP process instance ID table";

      list process {
        xr:xr-xml-map "bgp_oper:Process";
        key "process-id";
        description "A particular process instance";

        container process-vrfs {
          xr:xr-xml-map "bgp_oper:ProcessVRFTable";
          description "VRF related operational data";

          list process-vrf {
            xr:xr-xml-map "bgp_oper:ProcessVRF";
            key "vrf-name";
            description "Operational data for a particular VRF";

            container process-afs {
              xr:xr-xml-map "bgp_oper:ProcessAFTable";
              description "BGP address family table";

              list process-af {
                xr:xr-xml-map "bgp_oper:ProcessAF";
                key "af-name";
                description "A particular address family";
                leaf af-name {
                  xr:xr-xml-map "bgp_oper:AFName";
                  type dt1:Bgp-address-family;
                  description "Address family";
                }
                uses NETWORK-LOOKUP-ALL-RD-TABLE;
                uses PATH-USED-TABLE;
                uses RPC-SET-TABLE;
                uses NETWORK-PREFIX-TABLE;
                uses NETWORK-TABLE;
                uses PATH-TABLE;
                uses PATH-LABELED-TABLE;
                uses NETWORK-ALL-RD-TABLE;
              }
            }
            leaf vrf-name {
              xr:xr-xml-map "bgp_oper:VRFName";
              type xr:Cisco-ios-xr-string;
              description "Name of the VRF";
            }
          }
        }
        leaf process-id {
          xr:xr-xml-map "bgp_oper:ProcessID";
          type int32;
          description "Process instance ID";
        }
      }
    }
  }

  grouping PATH-LABELED-TABLE {
    description "Common node of af, process-af";

    container path-labeled-table {
      xr:xr-xml-map "bgp_oper:PathLabeledTable";
      description "The BGP Path Labeled Table";
      uses PATH;
    }
  }

  grouping UPDATE-INBOUND-FILTER-VRF {
    description "Common node of default-vrf, vrf";

    container update-inbound-filter-vrf {
      xr:xr-xml-map "bgp_oper:UpdateInboundFilterVRF";
      description
        "Update inbound filtering information for the VRF";
      uses BGP-UPDFILTER-VRF-BAG;
    }
  }

  grouping PATH-TABLE {
    description "Common node of af, process-af";

    container path-table {
      xr:xr-xml-map "bgp_oper:PathTable";
      description "The BGP Path Table";
      uses PATH;
    }
  }

  grouping RPKI-REFRESH-AF-TABLE {
    description "Common node of instance-active, instance-standby";

    container rpki-refresh-afs {
      xr:xr-xml-map "bgp_oper:RPKIRefreshAFTable";
      description "RPKI Refresh Table (per AF)";

      list rpki-refresh-af {
        xr:xr-xml-map "bgp_oper:RPKIRefreshAF";
        key "af-name";
        description "RPKI Refresh List";
        leaf af-name {
          xr:xr-xml-map "bgp_oper:AFName";
          type Bgp-rpki-edm-af;
          description "Adress family";
        }
        uses BGP-RPKI-REFRESH-LIST-BAG;
      }
    }
  }

  grouping PATH-USED-TABLE {
    description "Common node of af, process-af";

    container path-used-table {
      xr:xr-xml-map "bgp_oper:PathUsedTable";
      description "The BGP Path Used Table";
      uses PATH;
    }
  }

  grouping RPC-SET-TABLE {
    description "Common node of af, process-af";

    container rpc-sets {
      xr:xr-xml-map "bgp_oper:RPCSetTable";
      description "BGP next-hop set table";

      list rpc-set {
        xr:xr-xml-map "bgp_oper:RPCSet";
        key "rpc-set-index";
        description "A BGP next-hop set";
        leaf rpc-set-index {
          xr:xr-xml-map "bgp_oper:RPCSetIndex";
          type int32;
          description "Nexthop set index";
        }
        uses BGP-RPC-SET-BAG;
      }
    }
  }

  grouping NETWORK-LOOKUP-ALL-RD-TABLE {
    description "Common node of af, process-af";

    container network-lookup-all-rds {
      xr:xr-xml-map "bgp_oper:NetworkLookupAllRDTable";
      description "The BGP Network Lookup Table";

      list network-lookup-all-rd {
        xr:xr-xml-map "bgp_oper:NetworkLookupAllRD";
        key "network-prefix";
        description "The BGP Network Lookup table";

        container network-lookup-rds {
          xr:xr-xml-map "bgp_oper:NetworkLookupRDTable";
          description "The BGP Network Lookup table";

          list network-lookup-rd {
            xr:xr-xml-map "bgp_oper:NetworkLookupRD";
            key "rd";
            description "A BGP Network table entry";
            leaf rd {
              xr:xr-xml-map "bgp_oper:RD";
              type Bgp-route-distinguisher;
              description "Route Distinguisher value";
            }
            uses BGP-NET-BAG;
          }
        }
        leaf network-prefix {
          xr:xr-xml-map "bgp_oper:NetworkPrefix";
          type inet:ip-address-no-zone;
          description "Network ";
        }
      }
    }
  }

  grouping INFORMATION {
    description "Common node of default-vrf, vrf";

    container information {
      xr:xr-xml-map "bgp_oper:Information";
      description "Meta data for VRF";
      uses BGP-VRF-INFO-BAG;
    }
  }

  grouping ENTITY-CONFIGURATION-TABLE {
    description
      "Common node of config-instance-default-vrf,
      config-vrf";

    container entity-configurations {
      xr:xr-xml-map "bgp_oper:EntityConfigurationTable";
      description "The BGP Entity Configuration table";

      list entity-configuration {
        xr:xr-xml-map "bgp_oper:EntityConfiguration";
        description "A BGP Entity Configuration table entry";
        leaf entity-type {
          xr:xr-xml-map "bgp_oper:EntityType";
          type Bgp-entity;
          description "Entity type";
        }
        leaf neighbor-address {
          xr:xr-xml-map "bgp_oper:NeighborAddress";
          type inet:ip-address-no-zone;
          description "Neighbor address";
        }
        leaf entity-name {
          xr:xr-xml-map "bgp_oper:EntityName";
          type xr:Cisco-ios-xr-string;
          description "Entity name";
        }
        uses BGP-CONFIG-ENTITY-BAG;
      }
    }
  }

  grouping DEFAULT-VRF {
    description "Common node of instance-active, instance-standby";

    container default-vrf {
      xr:xr-xml-map "bgp_oper:DefaultVRF";
      description "Default VRF related operational data";
      uses UPDATE-INBOUND-ERROR-VRF;
      uses AF-TABLE;
      uses INFORMATION;
      uses UPDATE-INBOUND-FILTER-VRF;
      uses POSTIT-TABLE;
      uses GLOBAL-PROCESS-INFO;
      uses PROCESS-INFO-TABLE;
      uses UPDATE-INBOUND-ERROR-NEIGHBOR-TABLE;
      uses UPDATE-INBOUND-FILTER-NEIGHBOR-TABLE;
      uses BMP;
      uses SESSION-TABLE;
      uses NEIGHBOR-TABLE;
      uses NEXT-HOP-VRF-TABLE;
      uses MESSAGE-LOG-TABLE;
    }
  }

  grouping NETWORK-PREFIX-TABLE {
    description "Common node of af, process-af";

    container network-prefixes {
      xr:xr-xml-map "bgp_oper:NetworkPrefixTable";
      description "The BGP Network Lookup table";

      list network-prefix {
        xr:xr-xml-map "bgp_oper:NetworkPrefix";
        description "A BGP Network Lookup prefix entry";

        container network-lookups {
          xr:xr-xml-map "bgp_oper:NetworkLookupTable";
          description "The BGP Network Lookup table";

          list network-lookup {
            xr:xr-xml-map "bgp_oper:NetworkLookup";
            key "process-id";
            description "A BGP Network Lookup table entry";
            leaf process-id {
              xr:xr-xml-map "bgp_oper:ProcessID";
              type int32;
              description "Process instance ID";
            }
            uses BGP-NET-BAG;
          }
        }
        leaf rd {
          xr:xr-xml-map "bgp_oper:RD";
          type Bgp-route-distinguisher;
          description "Route Distinguisher value";
        }
        leaf network-prefix {
          xr:xr-xml-map "bgp_oper:NetworkPrefix";
          type inet:ip-address-no-zone;
          description "Network prefix";
        }
      }
    }
  }

  grouping UPDATE-INBOUND-ERROR-VRF {
    description "Common node of default-vrf, vrf";

    container update-inbound-error-vrf {
      xr:xr-xml-map "bgp_oper:UpdateInboundErrorVRF";
      description "Update inbound error information for the VRF";
      uses BGP-UPDERR-VRF-BAG;
    }
  }

  grouping UPDATE-INBOUND-FILTER-NEIGHBOR-TABLE {
    description "Common node of default-vrf, vrf";

    container update-inbound-filter-neighbors {
      xr:xr-xml-map "bgp_oper:UpdateInboundFilterNeighborTable";
      description
        "Update inbound filtering information for all
        neighbors";

      list update-inbound-filter-neighbor {
        xr:xr-xml-map "bgp_oper:UpdateInboundFilterNeighbor";
        key "neighbor-address";
        description
          "Update inbound filtering information for
          neighbor";
        leaf neighbor-address {
          xr:xr-xml-map "bgp_oper:NeighborAddress";
          type inet:ip-address-no-zone;
          description "Neighbor address";
        }
        uses BGP-UPDFILTER-NBR-BAG;
      }
    }
  }

  grouping NETWORK-TABLE {
    description "Common node of af, process-af";

    container networks {
      xr:xr-xml-map "bgp_oper:NetworkTable";
      description "The BGP Network Table";

      list network {
        xr:xr-xml-map "bgp_oper:Network";
        description "A BGP Network table entry";
        leaf rd {
          xr:xr-xml-map "bgp_oper:RD";
          type Bgp-route-distinguisher;
          description "Route Distinguisher value";
        }
        leaf network {
          xr:xr-xml-map "bgp_oper:Network";
          type inet:ip-prefix;
          description "Network in prefix/length format";
        }
        leaf process-id {
          xr:xr-xml-map "bgp_oper:ProcessID";
          type int32;
          description "Process instance ID";
        }
        uses BGP-NET-BAG;
      }
    }
  }

  grouping NETWORK-ALL-RD-TABLE {
    description "Common node of af, process-af";

    container network-all-rds {
      xr:xr-xml-map "bgp_oper:NetworkAllRDTable";
      description "The BGP Network Lookup Table";

      list network-all-rd {
        xr:xr-xml-map "bgp_oper:NetworkAllRD";
        key "network-addr network-prefix";
        description "The BGP Network Lookup table";

        container network-rds {
          xr:xr-xml-map "bgp_oper:NetworkRDTable";
          description "The BGP Network Lookup table";

          list network-rd {
            xr:xr-xml-map "bgp_oper:NetworkRD";
            key "rd";
            description "A BGP Network table entry";
            leaf rd {
              xr:xr-xml-map "bgp_oper:RD";
              type Bgp-route-distinguisher;
              description "Route Distinguisher value";
            }
            uses BGP-NET-BAG;
          }
        }
        leaf network-addr {
          xr:xr-xml-map "bgp_oper:Network";
          type inet:ip-address;
          description
            "Network in prefix/length format (address part)";
        }
        leaf network-prefix {
          xr:xr-xml-map "bgp_oper:Network";
          type uint16 {
            range "0..128";
          }
          description
            "Network in prefix/length format (prefix part)";
        }
      }
    }
  }

  grouping CONFIGURATION-USER-TABLE {
    description
      "Common node of config-instance-default-vrf,
      config-vrf";

    container configuration-users {
      xr:xr-xml-map "bgp_oper:ConfigurationUserTable";
      description "The BGP configuration users table";

      list configuration-user {
        xr:xr-xml-map "bgp_oper:ConfigurationUser";
        description "A BGP configuration user table entry";
        leaf entity-type {
          xr:xr-xml-map "bgp_oper:EntityType";
          type Bgp-entity;
          description "Entity type";
        }
        leaf neighbor-address {
          xr:xr-xml-map "bgp_oper:NeighborAddress";
          type inet:ip-address-no-zone;
          description "Neighbor address";
        }
        leaf entity-name {
          xr:xr-xml-map "bgp_oper:EntityName";
          type xr:Cisco-ios-xr-string;
          description "Entity name";
        }
        uses BGP-CONFIG-RELATIVES-BAG;
      }
    }
  }

  grouping UPDATE-INBOUND-ERROR-NEIGHBOR-TABLE {
    description "Common node of default-vrf, vrf";

    container update-inbound-error-neighbors {
      xr:xr-xml-map "bgp_oper:UpdateInboundErrorNeighborTable";
      description
        "Update inbound error information for all
        neighbors";

      list update-inbound-error-neighbor {
        xr:xr-xml-map "bgp_oper:UpdateInboundErrorNeighbor";
        key "neighbor-address";
        description "Update inbound error information for neighbor";
        leaf neighbor-address {
          xr:xr-xml-map "bgp_oper:NeighborAddress";
          type inet:ip-address-no-zone;
          description "Neighbor address";
        }
        uses BGP-UPDERR-NBR-BAG;
      }
    }
  }

  grouping RPKI-SERVER-LIST {
    description "Common node of instance-active, instance-standby";

    container rpki-server-list {
      xr:xr-xml-map "bgp_oper:RPKIServerList";
      description "RPKI Server Table";
      uses BGP-RPKI-CACHES-BAG;
    }
  }

  grouping GLOBAL-PROCESS-INFO {
    description "Common node of default-vrf, vrf";

    container global-process-info {
      xr:xr-xml-map "bgp_oper:GlobalProcessInfo";
      description "The Global Process information table";
      uses BGP-GLOBAL-PROCESS-INFO-BAG;
    }
  }

  grouping RT-TABLE {
    description "Common node of instance-active, instance-standby";

    container rt-entries {
      xr:xr-xml-map "bgp_oper:RTTable";
      description "BGP Route Target Sets Table";

      list rt-entry {
        xr:xr-xml-map "bgp_oper:RTEntry";
        description "BGP Route Target Set Entry";
        leaf route-target-lower-bytes {
          xr:xr-xml-map "bgp_oper:RouteTargetLowerBytes";
          type int32;
          description "Lower 4 bytes of RT";
        }
        leaf route-target-upper-bytes {
          xr:xr-xml-map "bgp_oper:RouteTargetUpperBytes";
          type int32;
          description "Upper 4 bytes of RT";
        }
        leaf af-name {
          xr:xr-xml-map "bgp_oper:AFName";
          type dt1:Bgp-address-family;
          description "Address family";
        }
        leaf request-id {
          xr:xr-xml-map "bgp_oper:RequestId";
          type int32;
          description "Random Request ID";
        }
        uses BGP-VRF-RT-BAG;
      }
    }
  }

  grouping RPKI-ROUTE-TABLE {
    description "Common node of instance-active, instance-standby";

    container rpki-routes {
      xr:xr-xml-map "bgp_oper:RPKIRouteTable";
      description "BGP RPKI ROA table";

      list rpki-route {
        xr:xr-xml-map "bgp_oper:RPKIRoute";
        description "RPKI Path Group";
        leaf af-name {
          xr:xr-xml-map "bgp_oper:AFName";
          type Bgp-rpki-edm-af;
          description "Address family";
        }
        leaf address {
          xr:xr-xml-map "bgp_oper:Address";
          type xr:Cisco-ios-xr-string;
          description "Route Address (IPv4 / IPv6)";
        }
        leaf minimum {
          xr:xr-xml-map "bgp_oper:Minimum";
          type int32;
          description "Minimum Prefix Length";
        }
        leaf maximum {
          xr:xr-xml-map "bgp_oper:Maximum";
          type int32;
          description "Maximum Prefix Length";
        }
        uses BGP-RPKI-ROUTES-BAG;
      }
    }
  }

  grouping NEIGHBOR-TABLE {
    description "Common node of default-vrf, vrf";

    container neighbors {
      xr:xr-xml-map "bgp_oper:NeighborTable";
      description "The BGP Neighbor table";

      list neighbor {
        xr:xr-xml-map "bgp_oper:Neighbor";
        key "neighbor-address";
        description "A BGP Neighbor table entry";
        leaf neighbor-address {
          xr:xr-xml-map "bgp_oper:NeighborAddress";
          type inet:ip-address-no-zone;
          description "Neighbor address";
        }
        uses BGP-NBR-BAG;
      }
    }
  }

  grouping MESSAGE-LOG-TABLE {
    description "Common node of default-vrf, vrf";

    container message-logs {
      xr:xr-xml-map "bgp_oper:MessageLogTable";
      description "The BGP Neighbor Message table";

      list message-log {
        xr:xr-xml-map "bgp_oper:MessageLog";
        description "A BGP Message log entry";
        leaf neighbor-address {
          xr:xr-xml-map "bgp_oper:NeighborAddress";
          type inet:ip-address-no-zone;
          description "Neighbor address";
        }
        leaf direction {
          xr:xr-xml-map "bgp_oper:Direction";
          type int32;
          description "Direction";
        }
        uses BGP-MSGLOG-NBR-BAG;
      }
    }
  }

  grouping AF-TABLE {
    description "Common node of default-vrf, vrf";

    container afs {
      xr:xr-xml-map "bgp_oper:AFTable";
      description "BGP address family table";

      list af {
        xr:xr-xml-map "bgp_oper:AF";
        key "af-name";
        description "A particular address family";

        container policies {
          xr:xr-xml-map "bgp_oper:PolicyTable";
          description "The BGP Policy Table";

          list policy {
            xr:xr-xml-map "bgp_oper:Policy";
            description "A BGP Policy table entry";
            leaf rd {
              xr:xr-xml-map "bgp_oper:RD";
              type Bgp-route-distinguisher;
              description "Route Distinguisher value";
            }
            leaf network {
              xr:xr-xml-map "bgp_oper:Network";
              type inet:ip-prefix;
              description "Network in prefix/length format";
            }
            leaf neighbor-address {
              xr:xr-xml-map "bgp_oper:NeighborAddress";
              type inet:ip-address-no-zone;
              description "Neighbor address";
            }
            uses BGP-PATH-ADV-BAG;
          }
        }

        container global-af-process-info {
          xr:xr-xml-map "bgp_oper:GlobalAFProcessInfo";
          description
            "The Global Address Family Process information
            table";
          uses BGP-GLOBAL-PROCESS-INFO-AF-BAG;
        }

        container advertised-path-xr {
          xr:xr-xml-map "bgp_oper:AdvertisedPathTable";
          description "The BGP Advertised path table (bestpath)";

          list advertised-path {
            xr:xr-xml-map "bgp_oper:AdvertisedPath";
            description
              "A BGP Advertised path table entry (bestpath)";
            leaf rd {
              xr:xr-xml-map "bgp_oper:RD";
              type Bgp-route-distinguisher;
              description "Route Distinguisher value";
            }
            leaf network {
              xr:xr-xml-map "bgp_oper:Network";
              type inet:ip-prefix;
              description "Network in prefix/length format";
            }
            leaf neighbor-address {
              xr:xr-xml-map "bgp_oper:NeighborAddress";
              type inet:ip-address-no-zone;
              description "Neighbor address";
            }
            uses BGP-PATH-BAG;
          }
        }

        container sourced-networks {
          xr:xr-xml-map "bgp_oper:SourcedNetworkTable";
          description "The BGP Convergence table";

          list sourced-network {
            xr:xr-xml-map "bgp_oper:SourcedNetwork";
            key "network";
            description "A BGP network command table entry";
            leaf network {
              xr:xr-xml-map "bgp_oper:Network";
              type inet:ip-prefix;
              description "Network in prefix/length format";
            }
            uses BGP-STATIC-ROUTES-BAG;
          }
        }

        container update-groups {
          xr:xr-xml-map "bgp_oper:UpdateGroupTable";
          description "The BGP Update group table";

          list update-group {
            xr:xr-xml-map "bgp_oper:UpdateGroup";
            description "A BGP Update group table entry";
            leaf process-id {
              xr:xr-xml-map "bgp_oper:ProcessID";
              type int32;
              description "Process instance ID";
            }
            leaf update-group-id {
              xr:xr-xml-map "bgp_oper:UpdateGroupID";
              type int32;
              description "Update group index";
            }
            leaf filter-group-id {
              xr:xr-xml-map "bgp_oper:FilterGroupID";
              type int32;
              description "Filter group index";
            }
            uses BGP-UPDGRP-BAG;
          }
        }

        container update-generation-sub-groups {
          xr:xr-xml-map "bgp_oper:UpdateGenerationSubGroupTable";
          description "Update generation for all sub-groups";

          list update-generation-sub-group {
            xr:xr-xml-map "bgp_oper:UpdateGenerationSubGroup";
            description "Update generation for sub-group";
            leaf update-group-index {
              xr:xr-xml-map "bgp_oper:UpdateGroupIndex";
              type int32;
              description "Update-group index";
            }
            leaf sub-group-index {
              xr:xr-xml-map "bgp_oper:SubGroupIndex";
              type int32;
              description "Sub-group index";
            }
            leaf sub-group-id {
              xr:xr-xml-map "bgp_oper:SubGroupID";
              type int32;
              description "Sub-group ID";
            }
            uses BGP-UPDGEN-SUBGRP-BAG;
          }
        }

        container next-hop-address-families {
          xr:xr-xml-map "bgp_oper:NextHopAddressFamilyTable";
          description "Address family of nexthop table";

          list next-hop-address-family {
            xr:xr-xml-map "bgp_oper:NextHopAddressFamily";
            key "next-hop-af-name";
            description "Nexthop Address family";

            container next-hop-af-vrf-afs {
              xr:xr-xml-map "bgp_oper:NextHopAF_VRF_AFTable";
              description "The BGP VRF AF table";

              list next-hop-af-vrf-af {
                xr:xr-xml-map "bgp_oper:NextHopAF_VRF_AF";
                key "process-id";
                description "A BGP Next-hop VRF AF table entry";
                leaf process-id {
                  xr:xr-xml-map "bgp_oper:ProcessID";
                  type int32;
                  description "Process instance ID";
                }
                uses BGP-NEXTHOP-VRF-AF-BAG;
              }
            }

            container next-hop-afs {
              xr:xr-xml-map "bgp_oper:NextHopAFTable";
              description "The BGP Next-hop table";

              list next-hop-af {
                xr:xr-xml-map "bgp_oper:NextHopAF";
                description "A BGP Next hop entry";
                leaf next-hop-address {
                  xr:xr-xml-map "bgp_oper:NextHopAddress";
                  type inet:ip-address-no-zone;
                  description "Next hop address";
                }
                leaf attribute-set {
                  xr:xr-xml-map "bgp_oper:AttributeSet";
                  type xr:Cisco-ios-xr-string;
                  description "Attribute Set Name";
                }
                uses BGP-NEXTHOP-BAG;
              }
            }
            leaf next-hop-af-name {
              xr:xr-xml-map "bgp_oper:NextHopAFName";
              type dt1:Bgp-address-family;
              description "Address family";
            }
          }
        }

        container convergences {
          xr:xr-xml-map "bgp_oper:ConvergenceTable";
          description "The BGP Convergence table";

          list convergence {
            xr:xr-xml-map "bgp_oper:Convergence";
            key "process-id";
            description "A BGP Convergence table entry";
            leaf process-id {
              xr:xr-xml-map "bgp_oper:ProcessID";
              type int32;
              description "Process instance ID";
            }
            uses BGP-CONVERGENCE-BAG;
          }
        }

        container rt-set-counters {
          xr:xr-xml-map "bgp_oper:RTSetCounterTable";
          description "The RT-set counter table";

          list rt-set-counter {
            xr:xr-xml-map "bgp_oper:RTSetCounter";
            key "rt-set-id";
            description "One RT-set counter table entry";
            leaf rt-set-id {
              xr:xr-xml-map "bgp_oper:RTSetID";
              type int32;
              description "RTSet ID";
            }
            uses BGP-RTSET-BAG;
          }
        }

        container update-generation-update-groups {
          xr:xr-xml-map "bgp_oper:UpdateGenerationUpdateGroupTable";
          description "Update generation for all update-groups";

          list update-generation-update-group {
            xr:xr-xml-map "bgp_oper:UpdateGenerationUpdateGroup";
            key "update-group-index";
            description "Update generation for update-group";
            leaf update-group-index {
              xr:xr-xml-map "bgp_oper:UpdateGroupIndex";
              type int32;
              description "Update-group index";
            }
            uses BGP-UPDGEN-UPDGRP-BAG;
          }
        }

        container update-generation-filter-groups {
          xr:xr-xml-map "bgp_oper:UpdateGenerationFilterGroupTable";
          description
            "Update generation for all filter-groups under
            a sub-group";

          list update-generation-filter-group {
            xr:xr-xml-map "bgp_oper:UpdateGenerationFilterGroup";
            description "Update generation for filter-group";
            leaf update-group-index {
              xr:xr-xml-map "bgp_oper:UpdateGroupIndex";
              type int32;
              description "Update-group index";
            }
            leaf sub-group-index {
              xr:xr-xml-map "bgp_oper:SubGroupIndex";
              type int32;
              description "Sub-group index";
            }
            leaf sub-group-id {
              xr:xr-xml-map "bgp_oper:SubGroupID";
              type int32;
              description "Sub-group ID";
            }
            leaf filter-group-index {
              xr:xr-xml-map "bgp_oper:FilterGroupIndex";
              type int32;
              description "Filter-group index";
            }
            uses BGP-UPDGEN-FILTERGRP-BAG;
          }
        }

        container advertised-path-counts {
          xr:xr-xml-map "bgp_oper:AdvertisedPathCountTable";
          description "The BGP Advertised paths table (bestpath)";

          list advertised-path-count {
            xr:xr-xml-map "bgp_oper:AdvertisedPathCount";
            key "neighbor-address";
            description
              "The BGP Advertised path table Count
              (bestpath)";
            leaf neighbor-address {
              xr:xr-xml-map "bgp_oper:NeighborAddress";
              type inet:ip-address-no-zone;
              description "Neighbor address";
            }
            uses BGP-NBR-ADV-CNT-BAG;
          }
        }

        container advertised-paths {
          xr:xr-xml-map "bgp_oper:AdvertisedPathsTable";
          description "The BGP Advertised paths table (add-paths)";

          list advertised-path {
            xr:xr-xml-map "bgp_oper:AdvertisedPaths";
            description
              "A BGP Advertised paths table entry
              (add-paths)";
            leaf rd {
              xr:xr-xml-map "bgp_oper:RD";
              type Bgp-route-distinguisher;
              description "Route Distinguisher value";
            }
            leaf network {
              xr:xr-xml-map "bgp_oper:Network";
              type inet:ip-prefix;
              description "Network in prefix/length format";
            }
            leaf neighbor-address {
              xr:xr-xml-map "bgp_oper:NeighborAddress";
              type inet:ip-address-no-zone;
              description "Neighbor address";
            }
            uses BGP-PATH-MULTI;
          }
        }

        container update-generation-neighbors {
          xr:xr-xml-map "bgp_oper:UpdateGenerationNeighborTable";
          description "Update generation for all neighbors";

          list update-generation-neighbor {
            xr:xr-xml-map "bgp_oper:UpdateGenerationNeighbor";
            description "Update generation for neighbor";
            leaf update-group-index {
              xr:xr-xml-map "bgp_oper:UpdateGroupIndex";
              type int32;
              description "Update-group index";
            }
            leaf sub-group-index {
              xr:xr-xml-map "bgp_oper:SubGroupIndex";
              type int32;
              description "Sub-group index";
            }
            leaf sub-group-id {
              xr:xr-xml-map "bgp_oper:SubGroupID";
              type int32;
              description "Sub-group ID";
            }
            leaf filter-group-index {
              xr:xr-xml-map "bgp_oper:FilterGroupIndex";
              type int32;
              description "Filter-group index";
            }
            leaf neighbor-address {
              xr:xr-xml-map "bgp_oper:NeighborAddress";
              type inet:ip-address-no-zone;
              description "Neighbor address";
            }
            uses BGP-UPDGEN-NBR-BAG;
          }
        }

        container update-generation-address-family {
          xr:xr-xml-map "bgp_oper:UpdateGenerationAddressFamily";
          description "Update generation for address-family";
          uses BGP-UPDGEN-AF-BAG;
        }

        container dampenings {
          xr:xr-xml-map "bgp_oper:DampeningTable";
          description "The BGP Dampening table";

          list dampening {
            xr:xr-xml-map "bgp_oper:Dampening";
            description "A BGP Dampening table entry";
            leaf reuse {
              xr:xr-xml-map "bgp_oper:Reuse";
              type int32;
              description "Reuse array index";
            }
            leaf version {
              xr:xr-xml-map "bgp_oper:Version";
              type int32;
              description "Version number";
            }
            leaf rd {
              xr:xr-xml-map "bgp_oper:RD";
              type Bgp-route-distinguisher;
              description "Route Distinguisher value";
            }
            leaf network {
              xr:xr-xml-map "bgp_oper:Network";
              type inet:ip-prefix;
              description "Network in prefix/length format";
            }
            leaf neighbor-address {
              xr:xr-xml-map "bgp_oper:NeighborAddress";
              type inet:ip-address-no-zone;
              description "Neighbor address";
            }
            leaf source-rd {
              xr:xr-xml-map "bgp_oper:SourceRD";
              type Bgp-route-distinguisher;
              description "Source Route Distinguisher value";
            }
            leaf path-id {
              xr:xr-xml-map "bgp_oper:PathID";
              type int32;
              description "Received Path ID";
            }
            uses BGP-PATH-BAG;
          }
        }

        container af-process-infos {
          xr:xr-xml-map "bgp_oper:AFProcessInfoTable";
          description "The BGP Process address family table";

          list af-process-info {
            xr:xr-xml-map "bgp_oper:AFProcessInfo";
            key "process-id";
            description "A BGP Process address family table entry";
            leaf process-id {
              xr:xr-xml-map "bgp_oper:ProcessID";
              type int32;
              description "Process Instance ID";
            }
            uses BGP-PROCESS-INFO-AF-BAG;
          }
        }

        container prefix-filters {
          xr:xr-xml-map "bgp_oper:PrefixFilterTable";
          description "The BGP Prefix Filter table";

          list prefix-filter {
            xr:xr-xml-map "bgp_oper:PrefixFilter";
            key "neighbor-address";
            description "A BGP prefix filter table entry";
            leaf neighbor-address {
              xr:xr-xml-map "bgp_oper:NeighborAddress";
              type inet:ip-address-no-zone;
              description "Neighbor address";
            }
            uses BGP-RCV-PFXLST-BAG;
          }
        }
        leaf af-name {
          xr:xr-xml-map "bgp_oper:AFName";
          type dt1:Bgp-address-family;
          description "Address family";
        }
        uses NETWORK-LOOKUP-ALL-RD-TABLE;
        uses PATH-USED-TABLE;
        uses RPC-SET-TABLE;
        uses NETWORK-PREFIX-TABLE;
        uses ATTRIBUTE-TABLE;
        uses NETWORK-TABLE;
        uses PATH-TABLE;
        uses PATH-LABELED-TABLE;
        uses NETWORK-ALL-RD-TABLE;
      }
    }
  }

  grouping CONFIGURATION-INHERITANCE-TABLE {
    description
      "Common node of config-instance-default-vrf,
      config-vrf";

    container configuration-inheritances {
      xr:xr-xml-map "bgp_oper:ConfigurationInheritanceTable";
      description "The BGP configurataion inheritance table";

      list configuration-inheritance {
        xr:xr-xml-map "bgp_oper:ConfigurationInheritance";
        description "A BGP configuration inheritance table entry";
        leaf entity-type {
          xr:xr-xml-map "bgp_oper:EntityType";
          type Bgp-entity;
          description "Entity type";
        }
        leaf neighbor-address {
          xr:xr-xml-map "bgp_oper:NeighborAddress";
          type inet:ip-address-no-zone;
          description "Neighbor address";
        }
        leaf entity-name {
          xr:xr-xml-map "bgp_oper:EntityName";
          type xr:Cisco-ios-xr-string;
          description "Entity name";
        }
        uses BGP-CONFIG-RELATIVES-BAG;
      }
    }
  }

  grouping UPDATE-INBOUND-FILTER-PROCESS {
    description "Common node of instance-active, instance-standby";

    container update-inbound-filter-process {
      xr:xr-xml-map "bgp_oper:UpdateInboundFilterProcess";
      description
        "Update inbound filtering information for the
        process";
      uses BGP-UPDFILTER-PROC-BAG;
    }
  }

  container bgp {
    xr:xr-xml-map "bgp_oper:BGP";
    config false;
    description "BGP operational data";

    container config-instances {
      xr:xr-xml-map "bgp_oper:ConfigInstanceTable";
      description "Instance specific BGP data";

      list config-instance {
        xr:xr-xml-map "bgp_oper:ConfigInstance";
        key "instance-name";
        description "Instance specific BGP data";

        container config-instance-default-vrf {
          xr:xr-xml-map "bgp_oper:ConfigInstanceDefaultVRF";
          description "Default VRF related configuration data";
          uses ENTITY-CONFIGURATION-TABLE;
          uses CONFIGURATION-USER-TABLE;
          uses CONFIGURATION-INHERITANCE-TABLE;
        }

        container config-vrfs {
          xr:xr-xml-map "bgp_oper:ConfigInstanceVRFTable";
          description "VRF related configuration data";

          list config-vrf {
            xr:xr-xml-map "bgp_oper:ConfigVRF";
            key "vrf-name";
            description "Configuration data for a particular VRF";
            leaf vrf-name {
              xr:xr-xml-map "bgp_oper:VRFName";
              type xr:Cisco-ios-xr-string;
              description "Name of the VRF";
            }
            uses ENTITY-CONFIGURATION-TABLE;
            uses CONFIGURATION-USER-TABLE;
            uses CONFIGURATION-INHERITANCE-TABLE;
          }
        }
        leaf instance-name {
          xr:xr-xml-map "bgp_oper:InstanceName";
          type xr:Cisco-ios-xr-string;
          description "Name of the BGP instance";
        }
      }
    }

    container instances {
      xr:xr-xml-map "bgp_oper:InstanceTable";
      description "Instance specific BGP data";

      list instance {
        xr:xr-xml-map "bgp_oper:Instance";
        key "instance-name";
        description "Instance specific BGP data";

        container instance-active {
          xr:xr-xml-map "bgp_oper:InstanceActive";
          description "Active BGP operational data";

          container label-entries {
            xr:xr-xml-map "bgp_oper:LabelTable";
            description "BGP Label Table";

            list label-entry {
              xr:xr-xml-map "bgp_oper:LabelEntry";
              key "label";
              description "BGP Label Entry";
              leaf label {
                xr:xr-xml-map "bgp_oper:Label";
                type int32;
                description "Label index";
              }
              uses BGP-LABEL-BAG;
            }
          }

          container label-summary {
            xr:xr-xml-map "bgp_oper:LabelSummary";
            description "BGP Label Summary";
            uses BGP-LABEL-SUMMARY-BAG;
          }

          container label-rpf-entries {
            xr:xr-xml-map "bgp_oper:LabelRPFTable";
            description "BGP Label RPF Table";

            list label-rpf-entry {
              xr:xr-xml-map "bgp_oper:LabelRPFEntry";
              key "label";
              description "BGP Label RPF Entry";
              leaf label {
                xr:xr-xml-map "bgp_oper:Label";
                type int32;
                description "Label index";
              }
              uses BGP-LABEL-RPF-BAG;
            }
          }
          uses PROCESS-TABLE;
          uses UPDATE-GENERATION-PROCESS;
          uses RPKI-REFRESH-AF-TABLE;
          uses VRF-TABLE;
          uses DEFAULT-VRF;
          uses UPDATE-INBOUND-FILTER-PROCESS;
          uses ATTRIBUTE-TABLE;
          uses RT-TABLE;
          uses ATTRIBUTE-FILTER-GROUP-TABLE;
          uses RPKI-SERVER-LIST;
          uses RPKI-ROUTE-TABLE;
          uses UPDATE-INBOUND-ERROR-PROCESS;
          uses RPKI-SUMMARY;
        }

        container instance-standby {
          xr:xr-xml-map "bgp_oper:InstanceStandby";
          description "Standby BGP operational data";
          uses PROCESS-TABLE;
          uses UPDATE-GENERATION-PROCESS;
          uses RPKI-REFRESH-AF-TABLE;
          uses VRF-TABLE;
          uses DEFAULT-VRF;
          uses UPDATE-INBOUND-FILTER-PROCESS;
          uses ATTRIBUTE-TABLE;
          uses RT-TABLE;
          uses ATTRIBUTE-FILTER-GROUP-TABLE;
          uses RPKI-SERVER-LIST;
          uses RPKI-ROUTE-TABLE;
          uses UPDATE-INBOUND-ERROR-PROCESS;
          uses RPKI-SUMMARY;
        }
        leaf instance-name {
          xr:xr-xml-map "bgp_oper:InstanceName";
          type xr:Cisco-ios-xr-string;
          description "Name of the BGP instance";
        }
      }
    }

    container bpm-instances-table {
      xr:xr-xml-map "bgp_oper:BPMInstancesTable";
      description "BGP instances information";

      container bpm-instances {
        xr:xr-xml-map "bgp_oper:BPMInstances";
        description "BGP instances information";
        uses BGP-INSTANCES-INFO-BAG;
      }
    }
  }
}
