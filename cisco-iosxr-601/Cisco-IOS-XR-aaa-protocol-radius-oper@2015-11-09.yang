module Cisco-IOS-XR-aaa-protocol-radius-oper {

  /*** NAMESPACE / PREFIX DEFINITION ***/

  namespace "http://cisco.com/ns/yang"+
    "/Cisco-IOS-XR-aaa-protocol-radius-oper";


  prefix "aaa-protocol-radius-oper";

  /*** LINKAGE (IMPORTS / INCLUDES) ***/

  import ietf-inet-types { prefix "inet"; }

  import Cisco-IOS-XR-types { prefix "xr"; }

  import Cisco-IOS-XR-aaa-locald-oper { prefix "a1"; }

  include Cisco-IOS-XR-aaa-protocol-radius-oper-sub2 {
    revision-date 2015-11-09;
  }

  include Cisco-IOS-XR-aaa-protocol-radius-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-protocol-radius package operational data.

     This module contains definitions
     for the following management objects:
       radius: RADIUS operational data

     This YANG module augments the
       Cisco-IOS-XR-aaa-locald-oper
     module with state data.

     Copyright (c) 2013-2015 by Cisco Systems, Inc.
     All rights reserved.";

  revision "2015-11-09" {
    description
      "IOS XR 6.0 revision.";
  }

  typedef Aaa-port-range {
    type uint32 {
      range "1..65535";
    }
    description "Aaa port range";
  }

  container radius {
    xr:xr-xml-map "radius_oper:RADIUS";
    config false;
    description "RADIUS operational data";

    container nodes {
      xr:xr-xml-map "radius_oper:NodeTable";
      description "Contains all the nodes";

      list node {
        xr:xr-xml-map "radius_oper:Node";
        key "node-name";
        description "RADIUS operational data for a particular node";

        container client {
          xr:xr-xml-map "radius_oper:Client";
          description "RADIUS client data";
          uses RADIUS-CLIENT-XML;
        }

        container dead-criteria {
          xr:xr-xml-map "radius_oper:DeadCriteria";
          description "RADIUS dead criteria information";

          container hosts {
            xr:xr-xml-map "radius_oper:HostTable";
            description "RADIUS server dead criteria host table";

            list host {
              xr:xr-xml-map "radius_oper:Host";
              description "RADIUS Server";
              leaf ip-address {
                xr:xr-xml-map "radius_oper:IPAddress";
                type inet:ip-address-no-zone;
                description "IP address of RADIUS server";
              }
              leaf auth-port-number {
                xr:xr-xml-map "radius_oper:AuthPortNumber";
                type Aaa-port-range;
                description
                  "Authentication Port number (standard port
                  1645)";
              }
              leaf acct-port-number {
                xr:xr-xml-map "radius_oper:AcctPortNumber";
                type Aaa-port-range;
                description
                  "Accounting Port number (standard port 1646)";
              }
              uses RADIUS-DEAD-CRITERIA;
            }
          }
        }

        container authentication {
          xr:xr-xml-map "radius_oper:Authentication";
          description "RADIUS authentication data";
          uses RADIUS-SERVER-AUTHENTICATION;
        }

        container accounting {
          xr:xr-xml-map "radius_oper:Accounting";
          description "RADIUS accounting data";
          uses RADIUS-SERVER-ACCOUNTING;
        }

        container server-groups {
          xr:xr-xml-map "radius_oper:ServerGroupTable";
          description "RADIUS server group table";

          list server-group {
            xr:xr-xml-map "radius_oper:ServerGroup";
            key "server-group-name";
            description "RADIUS server group data";
            leaf server-group-name {
              xr:xr-xml-map "radius_oper:ServerGroupName";
              type xr:Cisco-ios-xr-string;
              description "Group name";
            }
            uses RADIUS-GROUPS-SERVERS;
          }
        }

        container dynamic-authorization {
          xr:xr-xml-map "radius_oper:DynamicAuthorization";
          description "Dynamic authorization data";
          uses RADIUS-DYNAMIC-SERVER;
        }
        leaf node-name {
          xr:xr-xml-map "radius_oper:NodeName";
          type xr:Node-id;
          description "Node name";
        }
      }
    }
  }

  augment "/a1:aaa" {

    container radius {
      xr:xr-xml-map "aaa_radius_oper:RADIUS";
      description "RADIUS operational data";

      container servers {
        xr:xr-xml-map "aaa_radius_oper:ServerTable";
        description "List of RADIUS servers configured";

        list server {
          xr:xr-xml-map "aaa_radius_oper:Server";
          description "RADIUS Server";
          leaf ip-address {
            xr:xr-xml-map "aaa_radius_oper:IPAddress";
            type inet:ip-address-no-zone;
            description "IP address of RADIUS server";
          }
          leaf auth-port-number {
            xr:xr-xml-map "aaa_radius_oper:AuthPortNumber";
            type Aaa-port-range;
            description
              "Authentication Port number (standard port
              1645)";
          }
          leaf acct-port-number {
            xr:xr-xml-map "aaa_radius_oper:AcctPortNumber";
            type Aaa-port-range;
            description
              "Accounting Port number (standard port 1646)";
          }
          uses RADIUS-SERVERBAG;
        }
      }

      container global {
        xr:xr-xml-map "aaa_radius_oper:Global";
        description "RADIUS Client Information";
        uses RADIUS-CLIENTBAG;
      }
    }
    description
      "This augment extends the operational data of
      'Cisco-IOS-XR-aaa-locald-oper'";
  }
}
