submodule Cisco-IOS-XR-ip-tcp-oper-sub2 {

  belongs-to Cisco-IOS-XR-ip-tcp-oper {
    prefix Cisco-IOS-XR-ip-tcp-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-tcp package operational data.

     Copyright (c) 2013-2015 by Cisco Systems, Inc.
     All rights reserved.";

  revision "2015-11-09" {
    description
      "IOS XR 6.0 revision.";
  }


  grouping IP-TCP {
    description "TCP Traffic Information";
    leaf tcp-input-packets {
      xr:xr-xml-map "ip_tcp:TCPInputPackets";
      type uint32;
      description "TCP packets received";
    }
    leaf tcp-checksum-error-packets {
      xr:xr-xml-map "ip_tcp:TCPChecksumErrorPackets";
      type uint32;
      description "TCP packets with checksum errors";
    }
    leaf tcp-dropped-packets {
      xr:xr-xml-map "ip_tcp:TCPDroppedPackets";
      type uint32;
      description "TCP packets dropped (no port)";
    }
    leaf tcp-output-packets {
      xr:xr-xml-map "ip_tcp:TCPOutputPackets";
      type uint32;
      description "TCP packets transmitted";
    }
    leaf tcp-retransmitted-packets {
      xr:xr-xml-map "ip_tcp:TCPRetransmittedPackets";
      type uint32;
      description "TCP packets retransmitted";
    }
  }
}
