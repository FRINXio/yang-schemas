module Cisco-IOS-XR-ha-eem-policy-oper {

  /*** NAMESPACE / PREFIX DEFINITION ***/

  namespace "http://cisco.com/ns"+
    "/yang/Cisco-IOS-XR-ha-eem-policy-oper";


  prefix "ha-eem-policy-oper";

  /*** LINKAGE (IMPORTS / INCLUDES) ***/

  import Cisco-IOS-XR-types { prefix "xr"; }

  include Cisco-IOS-XR-ha-eem-policy-oper-sub1 {
    revision-date 2016-02-05;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ha-eem-policy package operational data.

     This module contains definitions
     for the following management objects:
       eem: EEM operational data

     Copyright (c) 2013-2015 by Cisco Systems, Inc.
     All rights reserved.";

  revision "2016-02-05" {
    description
      "IOS XR 6.0.1 revision.";
  }

  revision "2015-11-09" {
    description
      "IOS XR 6.0 revision.";
  }


  container eem {
    xr:xr-xml-map "fh_iox_oper:EEM";
    config false;
    description "EEM operational data";

    container dir-user {
      xr:xr-xml-map "fh_iox_oper:DirUser";
      description "directory user";

      container library {
        xr:xr-xml-map "fh_iox_oper:Library";
        description "directory user library";
        uses EEM-DIR-USR;
      }

      container policy {
        xr:xr-xml-map "fh_iox_oper:Policy";
        description "directory user policy";
        uses EEM-DIR-USR;
      }
    }

    container env-variables {
      xr:xr-xml-map "fh_iox_oper:EnvVariableTable";
      description "list of environmental variables";

      list env-variable {
        xr:xr-xml-map "fh_iox_oper:EnvVariable";
        key "name";
        description "environmental variables name and value ";
        leaf name {
          xr:xr-xml-map "fh_iox_oper:Name";
          type xr:Cisco-ios-xr-string;
          description "Environmental variable name";
        }
        uses EEM-ENV;
      }
    }

    container refresh-time {
      xr:xr-xml-map "fh_iox_oper:RefreshTime";
      description "Refresh time";
      uses EEM-REFRESH-TIME;
    }

    container reg-policies {
      xr:xr-xml-map "fh_iox_oper:RegPolicyTable";
      description "list the registered policies";

      list reg-policy {
        xr:xr-xml-map "fh_iox_oper:RegPolicy";
        key "name";
        description "policy name and create time ";
        leaf name {
          xr:xr-xml-map "fh_iox_oper:Name";
          type xr:Cisco-ios-xr-string;
          description "policy name";
        }
        uses EEM-POLICY-REG;
      }
    }

    container avl-policies {
      xr:xr-xml-map "fh_iox_oper:AvailablePolicyTable";
      description "list the available policies";

      list avl-policy {
        xr:xr-xml-map "fh_iox_oper:AvlPolicy";
        key "name";
        description "policy name and create time ";
        leaf name {
          xr:xr-xml-map "fh_iox_oper:Name";
          type xr:Cisco-ios-xr-string;
          description "System policy name";
        }
        uses EEM-POLICY;
      }
    }
  }
}
