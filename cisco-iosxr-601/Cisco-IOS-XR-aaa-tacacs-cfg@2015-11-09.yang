module Cisco-IOS-XR-aaa-tacacs-cfg {

  /*** NAMESPACE / PREFIX DEFINITION ***/

  namespace "http://cisco.com/ns/yang/Cisco-IOS-XR-aaa-tacacs-cfg";


  prefix "aaa-tacacs-cfg";

  /*** LINKAGE (IMPORTS / INCLUDES) ***/

  import ietf-inet-types { prefix "inet"; }

  import Cisco-IOS-XR-types { prefix "xr"; }

  import Cisco-IOS-XR-aaa-lib-cfg { prefix "a1"; }

  import Cisco-IOS-XR-aaa-locald-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-tacacs package configuration.

     This YANG module augments the
       Cisco-IOS-XR-aaa-lib-cfg,
       Cisco-IOS-XR-aaa-locald-cfg
     modules with configuration data.

     Copyright (c) 2013-2015 by Cisco Systems, Inc.
     All rights reserved.";

  revision "2015-11-09" {
    description
      "IOS XR 6.0 revision.";
  }

  typedef Aaa-tacacs-port-range {
    type uint32 {
      range "1..65535";
    }
    description "Aaa tacacs port range";
  }
  typedef Tacacs-dscp-value {
    type union {
      type enumeration {
        enum af11 {
          value 10;
          description "Match packets with AF11 DSCP";
        }
        enum af12 {
          value 12;
          description "Match packets with AF12 DSCP";
        }
        enum af13 {
          value 14;
          description "Match packets with AF13 DSCP";
        }
        enum af21 {
          value 18;
          description "Match packets with AF21 DSCP";
        }
        enum af22 {
          value 20;
          description "Match packets with AF22 DSCP";
        }
        enum af23 {
          value 22;
          description "Match packets with AF23 DSCP";
        }
        enum af31 {
          value 26;
          description "Match packets with AF31 DSCP";
        }
        enum af32 {
          value 28;
          description "Match packets with AF32 DSCP";
        }
        enum af33 {
          value 30;
          description "Match packets with AF33 DSCP";
        }
        enum af41 {
          value 34;
          description "Match packets with AF41 DSCP";
        }
        enum af42 {
          value 36;
          description "Match packets with AF42 DSCP";
        }
        enum af43 {
          value 38;
          description "Match packets with AF43 DSCP";
        }
        enum cs1 {
          value 8;
          description "Match packets with CS1 DSCP";
        }
        enum cs2 {
          value 16;
          description "Match packets with CS2 DSCP";
        }
        enum cs3 {
          value 24;
          description "Match packets with CS3 DSCP";
        }
        enum cs4 {
          value 32;
          description "Match packets with CS4 DSCP";
        }
        enum cs5 {
          value 40;
          description "Match packets with CS5 DSCP";
        }
        enum cs6 {
          value 48;
          description "Match packets with CS6 DSCP";
        }
        enum cs7 {
          value 56;
          description "Match packets with CS7 DSCP";
        }
        enum default {
          value 0;
          description "Match packets with 0000 DSCP";
        }
        enum ef {
          value 46;
          description "Match packets with EF DSCP";
        }
      }
      type uint32 {
        range "0..63";
      }
    }
    description "Tacacs dscp value";
  }
  typedef Aaa-tacacs-timeout {
    type uint32 {
      range "1..1000";
    }
    description "Aaa tacacs timeout";
  }

  grouping KEY {
    description "Common node of tacacs, host, private-server";
    leaf key {
      xr:xr-xml-map "aaa_tacacs_cfg:Key";
      type xr:Proprietary-password;
      description "Set TACACS+ encryption key";
    }
  }

  grouping TIMEOUT {
    description "Common node of tacacs, host, private-server";
    leaf timeout {
      xr:xr-xml-map "aaa_tacacs_cfg:Timeout";
      type Aaa-tacacs-timeout;
      default "5";
      description "Time to wait for a TACACS+ server to reply";
    }
  }

  grouping DSCP {
    description "Common node of ipv4, ipv6";
    leaf dscp {
      xr:xr-xml-map "aaa_tacacs_cfg:DSCP";
      type Tacacs-dscp-value;
      description "Specify the DSCP value";
    }
  }

  grouping SINGLE-CONNECT {
    description "Common node of tacacs, host";
    leaf single-connect {
      xr:xr-xml-map "aaa_tacacs_cfg:SingleConnect";
      type boolean;
      default "false";
      description
        "Use a single connection for all sessions for a
        given TACACS+ server";
    }
  }

  augment "/a1:aaa" {

    container tacacs {
      xr:xr-xml-map "aaa_tacacs_cfg:TACACS";
      description "Modify TACACS+ query parameters";

      container ipv6 {
        xr:xr-xml-map "aaa_tacacs_cfg:IPv6";
        description "IPv6 configuration";
        uses DSCP;
      }

      container hosts {
        xr:xr-xml-map "aaa_tacacs_cfg:HostTable";
        description "Specify a TACACS+ server";

        list host {
          xr:xr-xml-map "aaa_tacacs_cfg:Host";
          key "ordering-index ip-address port-number";
          description "One of the TACACS+ servers";
          leaf ordering-index {
            xr:xr-xml-map "aaa_tacacs_cfg:OrderingIndex";
            type int32;
            description
              "This is used to sort the servers in the order
              of precedence";
          }
          leaf ip-address {
            xr:xr-xml-map "aaa_tacacs_cfg:IPAddress";
            type inet:ip-address-no-zone;
            description "IP address of TACACS+ server";
          }
          leaf port-number {
            xr:xr-xml-map "aaa_tacacs_cfg:PortNumber";
            type Aaa-tacacs-port-range;
            description "Port number (standard 49)";
          }
          uses KEY;
          uses TIMEOUT;
          uses SINGLE-CONNECT;
        }
      }

      container ipv4 {
        xr:xr-xml-map "aaa_tacacs_cfg:IPv4";
        description "IPv4 configuration";
        uses DSCP;
      }

      container vrfs {
        xr:xr-xml-map "aaa_tacacs_cfg:VRFTable";
        description "List of VRFs";

        list vrf {
          xr:xr-xml-map "aaa_tacacs_cfg:VRF";
          key "vrf-name";
          description "A VRF";
          leaf source-interface {
            xr:xr-xml-map "aaa_tacacs_cfg:SourceInterface";
            type xr:Interface-name;
            description
              "Specify interface for source address in
              TACACS+ packets";
          }
          leaf vrf-name {
            xr:xr-xml-map "aaa_tacacs_cfg:VRFName";
            type xr:Cisco-ios-xr-string;
            description
              "VRF name. Specify 'default' for default VRF";
          }
        }
      }
      uses KEY;
      uses TIMEOUT;
      uses SINGLE-CONNECT;
    }
    description
      "This augment extends the configuration data of
      'Cisco-IOS-XR-aaa-lib-cfg'";
  }

  augment "/a1:aaa/a2:server-groups" {

    container tacacs-server-groups {
      xr:xr-xml-map "aaa_tacacs_cfg:TACACSServerGroupTable";
      description "TACACS+ server-group definition";

      list tacacs-server-group {
        xr:xr-xml-map "aaa_tacacs_cfg:TACACSServerGroup";
        key "server-group-name";
        description "TACACS+ Server group name";

        container servers {
          xr:xr-xml-map "aaa_tacacs_cfg:ServerTable";
          description "Specify a TACACS+ server";

          list server {
            xr:xr-xml-map "aaa_tacacs_cfg:Server";
            key "ordering-index ip-address";
            description "A server to include in the server group";
            leaf ordering-index {
              xr:xr-xml-map "aaa_tacacs_cfg:OrderingIndex";
              type int32;
              description
                "This is used to sort the servers in the
                order of precedence";
            }
            leaf ip-address {
              xr:xr-xml-map "aaa_tacacs_cfg:IPAddress";
              type inet:ip-address-no-zone;
              description "IP address of TACACS+ server";
            }
          }
        }

        container private-servers {
          xr:xr-xml-map "aaa_tacacs_cfg:PrivateServerTable";
          description
            "List of private TACACS servers present in the
            group";

          list private-server {
            xr:xr-xml-map "aaa_tacacs_cfg:PrivateServer";
            key "ordering-index ip-address port-number";
            description
              "A private server to include in the server
              group";
            leaf ordering-index {
              xr:xr-xml-map "aaa_tacacs_cfg:OrderingIndex";
              type int32;
              description
                "This is used to sort the servers in the
                order of precedence";
            }
            leaf ip-address {
              xr:xr-xml-map "aaa_tacacs_cfg:IPAddress";
              type inet:ip-address-no-zone;
              description "IP address of TACACS+ server";
            }
            leaf port-number {
              xr:xr-xml-map "aaa_tacacs_cfg:PortNumber";
              type Aaa-tacacs-port-range;
              description "Port number (standard 49)";
            }
            uses KEY;
            uses TIMEOUT;
          }
        }
        leaf vrf {
          xr:xr-xml-map "aaa_tacacs_cfg:VRF";
          type string;
          description "Specify VRF name of TACACS group";
        }
        leaf server-group-name {
          xr:xr-xml-map "aaa_tacacs_cfg:ServerGroupName";
          type xr:Cisco-ios-xr-string;
          description "TACACS+ Server group name";
        }
      }
    }
    description
      "This augment extends the configuration data of
      'Cisco-IOS-XR-aaa-locald-cfg'";
  }
}
