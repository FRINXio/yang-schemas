submodule Cisco-IOS-XR-aaa-protocol-radius-oper-sub1 {

  belongs-to Cisco-IOS-XR-aaa-protocol-radius-oper {
    prefix Cisco-IOS-XR-aaa-protocol-radius-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR aaa-protocol-radius package operational data.

     Copyright (c) 2013-2015 by Cisco Systems, Inc.
     All rights reserved.";

  revision "2015-11-09" {
    description
      "IOS XR 6.0 revision.";
  }


  grouping RADIUS-CLIENTBAG {
    description "RADIUS CLIENTBAG";
    leaf unknown-authentication-response {
      xr:xr-xml-map "show_radius:UnknownAuthenticationResponse";
      type uint32;
      description
        "Number of RADIUS Access-Responsepackets received
        from unknownaddresses";
    }
    leaf authentication-nas-id {
      xr:xr-xml-map "show_radius:AuthenticationNAS_ID";
      type string;
      description
        "NAS-Identifier of the RADIUSauthentication
        client";
    }
    leaf unknown-accounting-response {
      xr:xr-xml-map "show_radius:UnknownAccountingResponse";
      type uint32;
      description
        "Number of RADIUS Accounting-Responsepackets
        received from unknownaddresses";
    }
    leaf accounting-nas-id {
      xr:xr-xml-map "show_radius:AccountingNAS_ID";
      type string;
      description "NAS-Identifier of the RADIUSaccounting client";
    }
  }

  grouping RADIUS-SERVERBAG {
    description "RADIUS SERVERBAG";
    leaf ipv4-address {
      xr:xr-xml-map "show_radius:IPV4_Address";
      type inet:ipv4-address;
      description "IP address of RADIUS server";
    }
    leaf priority {
      xr:xr-xml-map "show_radius:Priority";
      type uint32;
      description
        "A number that indicates the priority            
        of the server";
    }
    leaf timeout-xr {
      xr:xr-xml-map "show_radius:timeout-xr";
      type uint32;
      units "second";
      description "Per-server timeout in seconds";
    }
    leaf retransmit {
      xr:xr-xml-map "show_radius:Retransmit";
      type uint32;
      description "Per-server retransmit";
    }
    leaf dead-time {
      xr:xr-xml-map "show_radius:DeadTime";
      type uint32;
      units "minute";
      description "Per-server deadtime in minutes";
    }
    leaf dead-detect-time {
      xr:xr-xml-map "show_radius:DeadDetectTime";
      type uint32;
      units "second";
      description "Per-server dead-detect time in seconds";
    }
    leaf dead-detect-tries {
      xr:xr-xml-map "show_radius:DeadDetectTries";
      type uint32;
      description "Per-server dead-detect tries";
    }
    leaf authentication-port {
      xr:xr-xml-map "show_radius:AuthenticationPort";
      type uint32;
      description "Authentication port";
    }
    leaf accounting-port {
      xr:xr-xml-map "show_radius:AccountingPort";
      type uint32;
      description "Accounting port";
    }
    leaf state {
      xr:xr-xml-map "show_radius:State";
      type string;
      description "State of the server UP/DOWN";
    }
    leaf current-state-duration {
      xr:xr-xml-map "show_radius:CurrentStateDuration";
      type uint32;
      description
        "Elapsed time the server has been in             
        current state";
    }
    leaf previous-state-duration {
      xr:xr-xml-map "show_radius:PreviousStateDuration";
      type uint32;
      description
        "Elapsed time the server was been in             
        previous state";
    }
    leaf packets-in {
      xr:xr-xml-map "show_radius:PacketsIn";
      type uint32;
      description "Total number of incoming packets read";
    }
    leaf packets-out {
      xr:xr-xml-map "show_radius:PacketsOut";
      type uint32;
      description "Total number of outgoing packets sent";
    }
    leaf timeouts {
      xr:xr-xml-map "show_radius:Timeouts";
      type uint32;
      description "Total number of packets timed-out";
    }
    leaf aborts {
      xr:xr-xml-map "show_radius:Aborts";
      type uint32;
      description "Total number of requests aborted";
    }
    leaf replies-expected {
      xr:xr-xml-map "show_radius:RepliesExpected";
      type uint32;
      description "Number of replies expected to arrive";
    }
    leaf redirected-requests {
      xr:xr-xml-map "show_radius:RedirectedRequests";
      type uint32;
      description "Number of requests redirected";
    }
    leaf authentication-rtt {
      xr:xr-xml-map "show_radius:AuthenticationRTT";
      type uint32;
      units "millisecond";
      description
        "Round-trip time for authentication              
        in milliseconds";
    }
    leaf access-requests {
      xr:xr-xml-map "show_radius:AccessRequests";
      type uint32;
      description "Number of access requests";
    }
    leaf access-request-retransmits {
      xr:xr-xml-map "show_radius:AccessRequestRetransmits";
      type uint32;
      description
        "Number of retransmitted                         
        access requests";
    }
    leaf access-accepts {
      xr:xr-xml-map "show_radius:AccessAccepts";
      type uint32;
      description "Number of access accepts";
    }
    leaf access-rejects {
      xr:xr-xml-map "show_radius:AccessRejects";
      type uint32;
      description "Number of access rejects";
    }
    leaf access-challenges {
      xr:xr-xml-map "show_radius:AccessChallenges";
      type uint32;
      description "Number of access challenges";
    }
    leaf bad-access-responses {
      xr:xr-xml-map "show_radius:BadAccessResponses";
      type uint32;
      description "Number of bad access responses";
    }
    leaf bad-access-authenticators {
      xr:xr-xml-map "show_radius:BadAccessAuthenticators";
      type uint32;
      description "Number of bad access authenticators";
    }
    leaf pending-access-requests {
      xr:xr-xml-map "show_radius:PendingAccessRequests";
      type uint32;
      description "Number of pending access requests";
    }
    leaf access-timeouts {
      xr:xr-xml-map "show_radius:AccessTimeouts";
      type uint32;
      description "Number of access packets timed-out";
    }
    leaf unknown-access-types {
      xr:xr-xml-map "show_radius:UnknownAccessTypes";
      type uint32;
      description
        "Number of packets received with unknown         
        type from authentication server";
    }
    leaf dropped-access-responses {
      xr:xr-xml-map "show_radius:DroppedAccessResponses";
      type uint32;
      description "Number of access responses dropped";
    }
    leaf throttled-access-reqs {
      xr:xr-xml-map "show_radius:ThrottledAccessReqs";
      type uint32;
      description "No of throttled access reqs stats";
    }
    leaf throttled-timed-out-reqs {
      xr:xr-xml-map "show_radius:ThrottledTimedOutReqs";
      type uint32;
      description "No of access reqs that is throttled is timedout";
    }
    leaf throttled-dropped-reqs {
      xr:xr-xml-map "show_radius:ThrottledDroppedReqs";
      type uint32;
      description "No of discarded access reqs";
    }
    leaf max-throttled-access-reqs {
      xr:xr-xml-map "show_radius:MaxThrottledAccessReqs";
      type uint32;
      description "Max throttled access reqs";
    }
    leaf currently-throttled-access-reqs {
      xr:xr-xml-map "show_radius:CurrentlyThrottledAccessReqs";
      type uint32;
      description "No of currently throttled access reqs";
    }
    leaf authen-response-time {
      xr:xr-xml-map "show_radius:AuthenResponseTime";
      type uint32;
      description
        "Average response time for authentication
        requests";
    }
    leaf authen-transaction-successess {
      xr:xr-xml-map "show_radius:AuthenTransactionSuccessess";
      type uint32;
      description "Number of succeeded authentication transactions";
    }
    leaf authen-transaction-failure {
      xr:xr-xml-map "show_radius:AuthenTransactionFailure";
      type uint32;
      description "Number of failed authentication transactions";
    }
    leaf authen-unexpected-responses {
      xr:xr-xml-map "show_radius:AuthenUnexpectedResponses";
      type uint32;
      description "Number of unexpected authentication responses";
    }
    leaf authen-server-error-responses {
      xr:xr-xml-map "show_radius:AuthenServerErrorResponses";
      type uint32;
      description "Number of server error authentication responses";
    }
    leaf authen-incorrect-responses {
      xr:xr-xml-map "show_radius:AuthenIncorrectResponses";
      type uint32;
      description "Number of incorrect authentication responses";
    }
    leaf author-requests {
      xr:xr-xml-map "show_radius:AuthorRequests";
      type uint32;
      description "Number of access requests";
    }
    leaf author-request-timeouts {
      xr:xr-xml-map "show_radius:AuthorRequestTimeouts";
      type uint32;
      description "Number of access packets timed out";
    }
    leaf author-response-time {
      xr:xr-xml-map "show_radius:AuthorResponseTime";
      type uint32;
      description
        "Average response time for authorization requests";
    }
    leaf author-transaction-successess {
      xr:xr-xml-map "show_radius:AuthorTransactionSuccessess";
      type uint32;
      description "Number of succeeded authorization transactions";
    }
    leaf author-transaction-failure {
      xr:xr-xml-map "show_radius:AuthorTransactionFailure";
      type uint32;
      description "Number of failed authorization transactions";
    }
    leaf author-unexpected-responses {
      xr:xr-xml-map "show_radius:AuthorUnexpectedResponses";
      type uint32;
      description "Number of unexpected authorization responses";
    }
    leaf author-server-error-responses {
      xr:xr-xml-map "show_radius:AuthorServerErrorResponses";
      type uint32;
      description "Number of server error authorization responses";
    }
    leaf author-incorrect-responses {
      xr:xr-xml-map "show_radius:AuthorIncorrectResponses";
      type uint32;
      description "Number of incorrect authorization responses";
    }
    leaf accounting-rtt {
      xr:xr-xml-map "show_radius:AccountingRTT";
      type uint32;
      units "millisecond";
      description
        "Round-trip time for accounting                  
        in milliseconds";
    }
    leaf accounting-requests {
      xr:xr-xml-map "show_radius:AccountingRequests";
      type uint32;
      description "Number of accounting requests";
    }
    leaf accounting-retransmits {
      xr:xr-xml-map "show_radius:AccountingRetransmits";
      type uint32;
      description
        "Number of retransmitted                         
        accounting requests";
    }
    leaf accounting-responses {
      xr:xr-xml-map "show_radius:AccountingResponses";
      type uint32;
      description "Number of accounting responses";
    }
    leaf bad-accounting-responses {
      xr:xr-xml-map "show_radius:BadAccountingResponses";
      type uint32;
      description "Number of bad accounting responses";
    }
    leaf bad-accounting-authenticators {
      xr:xr-xml-map "show_radius:BadAccountingAuthenticators";
      type uint32;
      description
        "Number of bad accounting                        
        authenticators";
    }
    leaf pending-accounting-requets {
      xr:xr-xml-map "show_radius:PendingAccountingRequets";
      type uint32;
      description "Number of pending accounting requests";
    }
    leaf accounting-timeouts {
      xr:xr-xml-map "show_radius:AccountingTimeouts";
      type uint32;
      description
        "Number of accounting packets                    
        timed-out";
    }
    leaf unknown-accounting-types {
      xr:xr-xml-map "show_radius:UnknownAccountingTypes";
      type uint32;
      description
        "Number of packets received with unknown         
        type from accounting server";
    }
    leaf dropped-accounting-responses {
      xr:xr-xml-map "show_radius:DroppedAccountingResponses";
      type uint32;
      description
        "Number of accounting responses                  
        dropped";
    }
    leaf is-a-private-server {
      xr:xr-xml-map "show_radius:IsAPrivateServer";
      type boolean;
      description "Is a private server";
    }
    leaf total-test-auth-reqs {
      xr:xr-xml-map "show_radius:total_test_auth_reqs";
      type uint32;
      description "Total auth test request";
    }
    leaf total-test-auth-timeouts {
      xr:xr-xml-map "show_radius:total_test_auth_timeouts";
      type uint32;
      description "Total auth test timeouts";
    }
    leaf total-test-auth-response {
      xr:xr-xml-map "show_radius:total_test_auth_response";
      type uint32;
      description "Total auth test response";
    }
    leaf total-test-auth-pending {
      xr:xr-xml-map "show_radius:total_test_auth_pending";
      type uint32;
      description "Total auth test pending";
    }
    leaf total-test-acct-reqs {
      xr:xr-xml-map "show_radius:total_test_acct_reqs";
      type uint32;
      description " Total acct test req";
    }
    leaf total-test-acct-timeouts {
      xr:xr-xml-map "show_radius:total_test_acct_timeouts";
      type uint32;
      description "Total acct test timeouts";
    }
    leaf total-test-acct-response {
      xr:xr-xml-map "show_radius:total_test_acct_response";
      type uint32;
      description "Total acct test response";
    }
    leaf total-test-acct-pending {
      xr:xr-xml-map "show_radius:total_test_acct_pending";
      type uint32;
      description "Total acct test pending";
    }
    leaf throttled-acct-transactions {
      xr:xr-xml-map "show_radius:ThrottledAcctTransactions";
      type uint32;
      description "No of throttled acct transactions stats";
    }
    leaf throttled-acct-timed-out-stats {
      xr:xr-xml-map "show_radius:ThrottledAcctTimedOutStats";
      type uint32;
      description
        "No of acct transaction that is throttled is
        timedout";
    }
    leaf throttled-acct-failures-stats {
      xr:xr-xml-map "show_radius:ThrottledAcctFailuresStats";
      type uint32;
      description "No of acct discarded transaction";
    }
    leaf max-acct-throttled {
      xr:xr-xml-map "show_radius:MaxAcctThrottled";
      type uint32;
      description "Max throttled acct transactions";
    }
    leaf throttleda-acct-transactions {
      xr:xr-xml-map "show_radius:ThrottledaAcctTransactions";
      type uint32;
      description "No of currently throttled acct transactions";
    }
    leaf acct-unexpected-responses {
      xr:xr-xml-map "show_radius:AcctUnexpectedResponses";
      type uint32;
      description "Number of unexpected accounting responses";
    }
    leaf acct-server-error-responses {
      xr:xr-xml-map "show_radius:AcctServerErrorResponses";
      type uint32;
      description "Number of server error accounting responses";
    }
    leaf acct-incorrect-responses {
      xr:xr-xml-map "show_radius:AcctIncorrectResponses";
      type uint32;
      description "Number of incorrect accounting responses";
    }
    leaf acct-response-time {
      xr:xr-xml-map "show_radius:AcctResponseTime";
      type uint32;
      description
        "Average response time for authentication
        requests";
    }
    leaf acct-transaction-successess {
      xr:xr-xml-map "show_radius:AcctTransactionSuccessess";
      type uint32;
      description "Number of succeeded authentication transactions";
    }
    leaf acct-transaction-failure {
      xr:xr-xml-map "show_radius:AcctTransactionFailure";
      type uint32;
      description "Number of failed authentication transactions";
    }
    leaf total-deadtime {
      xr:xr-xml-map "show_radius:total_deadtime";
      type uint32;
      description
        "Total time of Server being in DEAD              
        state";
    }
    leaf last-deadtime {
      xr:xr-xml-map "show_radius:last_deadtime";
      type uint32;
      description
        "Time of Server being in DEAD state,             
        after last UP";
    }
    leaf is-quarantined {
      xr:xr-xml-map "show_radius:is_quarantined";
      type boolean;
      description
        "flag to indicate Server is quarantined          
        or not (Automated TEST in progress)";
    }
    leaf group-name {
      xr:xr-xml-map "show_radius:Group_Name";
      type string;
      description "Server group name for private server";
    }
    leaf ip-address-xr {
      xr:xr-xml-map "show_radius:ip-address-xr";
      type string;
      description "IP address buffer";
    }
    leaf family {
      xr:xr-xml-map "show_radius:Family";
      type string;
      description "IP address Family";
    }
  }
}
