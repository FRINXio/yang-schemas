module Cisco-IOS-XR-ip-rib-ipv6-oper {

  /*** NAMESPACE / PREFIX DEFINITION ***/

  namespace "http://cisco.com/ns/yang/Cisco-IOS-XR-ip-rib-ipv6-oper";


  prefix "ip-rib-ipv6-oper";

  /*** LINKAGE (IMPORTS / INCLUDES) ***/

  import ietf-inet-types { prefix "inet"; }

  import Cisco-IOS-XR-types { prefix "xr"; }

  include Cisco-IOS-XR-ip-rib-ipv6-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rib-ipv6 package operational data.

     This module contains definitions
     for the following management objects:
       ipv6-rib: RIB operational data
       ipv6-rib-stdby: ipv6 rib stdby

     Copyright (c) 2013-2015 by Cisco Systems, Inc.
     All rights reserved.";

  revision "2015-11-09" {
    description
      "IOS XR 6.0 revision.";
  }


  grouping VRF-TABLE {
    description "Common node of ipv6-rib, ipv6-rib-stdby";

    container vrfs {
      xr:xr-xml-map "ip-rib_ipv6_oper:VRFTable";
      description "VRF table";

      list vrf {
        xr:xr-xml-map "ip-rib_ipv6_oper:VRF";
        key "vrf-name";
        description "Specific VRF";

        container afs {
          xr:xr-xml-map "ip-rib_ipv6_oper:AFTable";
          description "Address Family (AF) table";

          list af {
            xr:xr-xml-map "ip-rib_ipv6_oper:AF";
            key "af-name";
            description "Specific AF information";

            container safs {
              xr:xr-xml-map "ip-rib_ipv6_oper:SAFTable";
              description "Subsequent Address Family (SAF) table";

              list saf {
                xr:xr-xml-map "ip-rib_ipv6_oper:SAF";
                key "saf-name";
                description "Specific SAF information";

                container ip-rib-route-table-names {
                  xr:xr-xml-map "ip-rib_ipv6_oper:IP_RIBRouteTable";
                  description "Global container of routes";

                  list ip-rib-route-table-name {
                    xr:xr-xml-map "ip-rib_ipv6_oper:IP_RIBRouteTabl"+
                      "eName";
                    key "route-table-name";
                    description
                      "IP RIB Route table name for a topology";

                    container destination-kw {
                      xr:xr-xml-map "ip-rib_ipv6_oper:DestinationKW";
                      description "Destination KW";

                      container dest-q-routes {
                        xr:xr-xml-map "ip-rib_ipv6_oper:DestQ_KW";
                        description "Quarantine";

                        list dest-q-route {
                          xr:xr-xml-map "ip-rib_ipv6_oper:DestQ_Rou"+
                            "te";
                          description
                            "Route information of a specific Backup
                            Address ";
                          leaf address {
                            xr:xr-xml-map "ip-rib_ipv6_oper:Address";
                            type inet:ipv6-address-no-zone;
                            description "Network Address ";
                          }
                          leaf prefix-length {
                            xr:xr-xml-map "ip-rib_ipv6_oper:PrefixL"+
                              "ength";
                            type xr:Ipv6-prefix-length;
                            description "Prefix Length ";
                          }
                          uses IPV6-RIB-EDM-ROUTE;
                        }
                      }

                      container dest-backup-routes {
                        xr:xr-xml-map "ip-rib_ipv6_oper:DestBackupK"+
                          "W";
                        description "Backup";

                        list dest-backup-route {
                          xr:xr-xml-map "ip-rib_ipv6_oper:DestBacku"+
                            "pRoute";
                          description
                            "Route information of a specific Backup
                            Address ";
                          leaf address {
                            xr:xr-xml-map "ip-rib_ipv6_oper:Address";
                            type inet:ipv6-address-no-zone;
                            description "Network Address ";
                          }
                          leaf prefix-length {
                            xr:xr-xml-map "ip-rib_ipv6_oper:PrefixL"+
                              "ength";
                            type xr:Ipv6-prefix-length;
                            description "Prefix Length ";
                          }
                          uses IPV6-RIB-EDM-ROUTE;
                        }
                      }

                      container dest-best-routes {
                        xr:xr-xml-map "ip-rib_ipv6_oper:DestBestKW";
                        description "Best Local";

                        list dest-best-route {
                          xr:xr-xml-map "ip-rib_ipv6_oper:DestBestR"+
                            "oute";
                          key "address";
                          description
                            "Best local route information for a
                            specific Address ";
                          leaf address {
                            xr:xr-xml-map "ip-rib_ipv6_oper:Address";
                            type inet:ipv6-address-no-zone;
                            description "Network Address ";
                          }
                          uses IPV6-RIB-EDM-ROUTE;
                        }
                      }

                      container dest-next-hop-routes {
                        xr:xr-xml-map "ip-rib_ipv6_oper:DestNextHop"+
                          "KW";
                        description "Resolving next hop";

                        list dest-next-hop-route {
                          xr:xr-xml-map "ip-rib_ipv6_oper:DestNextH"+
                            "opRoute";
                          key "address";
                          description
                            "Nexthop information for a specific
                            address";
                          leaf address {
                            xr:xr-xml-map "ip-rib_ipv6_oper:Address";
                            type inet:ipv6-address-no-zone;
                            description "Network Address ";
                          }
                          uses IPV6-RIB-EDM-ROUTE;
                        }
                      }
                    }

                    container adverts {
                      xr:xr-xml-map "ip-rib_ipv6_oper:AdvertsList";
                      description "Route advertiser information ";

                      list advert {
                        xr:xr-xml-map "ip-rib_ipv6_oper:Adverts";
                        description
                          "Route information of a specific Network
                          Address ";
                        leaf address {
                          xr:xr-xml-map "ip-rib_ipv6_oper:Address";
                          type inet:ipv6-address-no-zone;
                          description "Network Address ";
                        }
                        leaf prefix-length {
                          xr:xr-xml-map "ip-rib_ipv6_oper:PrefixLen"+
                            "gth";
                          type xr:Ipv6-prefix-length;
                          description "Prefix Length ";
                        }
                        uses IPV6-RIB-EDM-ADVERT;
                      }
                    }

                    container deleted-routes {
                      xr:xr-xml-map "ip-rib_ipv6_oper:DeletedKW";
                      description "Deleted";

                      list deleted-route {
                        xr:xr-xml-map "ip-rib_ipv6_oper:DeletedRout"+
                          "es";
                        description
                          "Route information for a specific
                          deleted address ";
                        leaf address {
                          xr:xr-xml-map "ip-rib_ipv6_oper:Address";
                          type inet:ipv6-address-no-zone;
                          description "Network Address ";
                        }
                        leaf prefix-length {
                          xr:xr-xml-map "ip-rib_ipv6_oper:PrefixLen"+
                            "gth";
                          type xr:Ipv6-prefix-length;
                          description "Prefix Length ";
                        }
                        uses IPV6-RIB-EDM-ROUTE;
                      }
                    }

                    container protocol {
                      xr:xr-xml-map "ip-rib_ipv6_oper:Protocol";
                      description
                        "Contains the classification of routes by
                        protocol";

                      container local {
                        xr:xr-xml-map "ip-rib_ipv6_oper:Local";
                        description "Local Protocol";

                        container lspv {
                          xr:xr-xml-map "ip-rib_ipv6_oper:LSPV";
                          description
                            "LSPV(Label Switched Path Verification)
                            protocol";
                          uses INFORMATION;
                          uses PROTOCOL-ROUTE-TABLE;
                        }
                        uses NON-AS;
                      }

                      container bgp {
                        xr:xr-xml-map "ip-rib_ipv6_oper:BGP";
                        description "BGP Protocol";
                        uses AS;
                      }

                      container mobile {
                        xr:xr-xml-map "ip-rib_ipv6_oper:Mobile";
                        description "Mobile Protocol";
                        uses NON-AS;
                      }

                      container eigrp {
                        xr:xr-xml-map "ip-rib_ipv6_oper:EIGRP";
                        description "EIGRP Protocol";
                        uses AS;
                      }

                      container rpl {
                        xr:xr-xml-map "ip-rib_ipv6_oper:RPL";
                        description "RPL Protocol";
                        uses AS;
                      }

                      container static {
                        xr:xr-xml-map "ip-rib_ipv6_oper:Static";
                        description "Static Protocol";
                        uses NON-AS;
                      }

                      container subscriber {
                        xr:xr-xml-map "ip-rib_ipv6_oper:Subscriber";
                        description "Subscriber Protocol";
                        uses NON-AS;
                      }

                      container ospf {
                        xr:xr-xml-map "ip-rib_ipv6_oper:OSPF";
                        description "OSPF Protocol";
                        uses AS;
                      }

                      container connected {
                        xr:xr-xml-map "ip-rib_ipv6_oper:Connected";
                        description "Connected Protocol";

                        container l2vpn {
                          xr:xr-xml-map "ip-rib_ipv6_oper:L2VPN";
                          description "L2VPN";
                          uses INFORMATION;
                          uses PROTOCOL-ROUTE-TABLE;
                        }
                        uses NON-AS;
                      }

                      container isis {
                        xr:xr-xml-map "ip-rib_ipv6_oper:ISIS";
                        description "ISIS Protocol";
                        uses AS;
                      }
                    }

                    container routes {
                      xr:xr-xml-map "ip-rib_ipv6_oper:RouteTable";
                      description "Route information ";

                      list route {
                        xr:xr-xml-map "ip-rib_ipv6_oper:Route";
                        description
                          "Route information of a specific Network
                          Address ";
                        leaf address {
                          xr:xr-xml-map "ip-rib_ipv6_oper:Address";
                          type inet:ipv6-address-no-zone;
                          description "Network Address ";
                        }
                        leaf prefix-length {
                          xr:xr-xml-map "ip-rib_ipv6_oper:PrefixLen"+
                            "gth";
                          type xr:Ipv6-prefix-length;
                          description "Prefix Length ";
                        }
                        leaf next-hop-address {
                          xr:xr-xml-map "ip-rib_ipv6_oper:NextHopAd"+
                            "dress";
                          type inet:ipv6-address-no-zone;
                          description "NextHop Address ";
                        }
                        leaf interface-name {
                          xr:xr-xml-map "ip-rib_ipv6_oper:Interface"+
                            "Name";
                          type xr:Interface-name;
                          description "Outgoing Interface ";
                        }
                        uses IPV6-RIB-EDM-ROUTE;
                      }
                    }

                    container q-routes {
                      xr:xr-xml-map "ip-rib_ipv6_oper:Q_KW";
                      description "Quarantine";

                      list q-route {
                        xr:xr-xml-map "ip-rib_ipv6_oper:Q_Route";
                        description
                          "Route information for a specific
                          quarantined address ";
                        leaf address {
                          xr:xr-xml-map "ip-rib_ipv6_oper:Address";
                          type inet:ipv6-address-no-zone;
                          description "Network Address ";
                        }
                        leaf prefix-length {
                          xr:xr-xml-map "ip-rib_ipv6_oper:PrefixLen"+
                            "gth";
                          type xr:Ipv6-prefix-length;
                          description "Prefix Length ";
                        }
                        uses IPV6-RIB-EDM-ROUTE;
                      }
                    }

                    container backup-routes {
                      xr:xr-xml-map "ip-rib_ipv6_oper:BackupKW";
                      description "Backup";

                      list backup-route {
                        xr:xr-xml-map "ip-rib_ipv6_oper:BackupRoute";
                        description
                          "Route information for a specific backup
                          address ";
                        leaf address {
                          xr:xr-xml-map "ip-rib_ipv6_oper:Address";
                          type inet:ipv6-address-no-zone;
                          description "Network Address ";
                        }
                        leaf prefix-length {
                          xr:xr-xml-map "ip-rib_ipv6_oper:PrefixLen"+
                            "gth";
                          type xr:Ipv6-prefix-length;
                          description "Prefix Length ";
                        }
                        uses IPV6-RIB-EDM-ROUTE;
                      }
                    }
                    leaf route-table-name {
                      xr:xr-xml-map "ip-rib_ipv6_oper:RouteTableNam"+
                        "e";
                      type xr:Cisco-ios-xr-string;
                      description "Name of the route table ";
                    }
                  }
                }
                leaf saf-name {
                  xr:xr-xml-map "ip-rib_ipv6_oper:SAFName";
                  type xr:Cisco-ios-xr-string;
                  description "Name of the SAF";
                }
              }
            }
            leaf af-name {
              xr:xr-xml-map "ip-rib_ipv6_oper:AFName";
              type xr:Cisco-ios-xr-string;
              description "Name of the AF - 'IPv6'";
            }
          }
        }
        leaf vrf-name {
          xr:xr-xml-map "ip-rib_ipv6_oper:VRFName";
          type xr:Cisco-ios-xr-string;
          description "Name of the VRF";
        }
      }
    }
  }

  grouping AS {
    description "Common node of bgp, ospf, isis, eigrp, rpl";

    list as {
      xr:xr-xml-map "ip-rib_ipv6_oper:AS";
      key "as";
      description "Autonomous System of protocol";
      leaf as {
        xr:xr-xml-map "ip-rib_ipv6_oper:AS";
        type xr:Cisco-ios-xr-string;
        description "Autonomous system";
      }
      uses INFORMATION;
      uses PROTOCOL-ROUTE-TABLE;
    }
  }

  grouping INFORMATION {
    description "Common node of as, non-as, l2vpn, lspv";

    container information {
      xr:xr-xml-map "ip-rib_ipv6_oper:Information";
      description "Protocol related Information";
      uses IPV6-RIB-EDM-PROTO;
    }
  }

  grouping RIB-TABLE {
    description "Common node of ipv6-rib, ipv6-rib-stdby";

    container rib-table-ids {
      xr:xr-xml-map "ip-rib_ipv6_oper:RIBTable";
      description "RIB table";

      list rib-table-id {
        xr:xr-xml-map "ip-rib_ipv6_oper:RIBTableID";
        key "tableid";
        description "Specific Table";

        container summary-protos {
          xr:xr-xml-map "ip-rib_ipv6_oper:RIBTableSummary";
          description "RIB table summary";

          list summary-proto {
            xr:xr-xml-map "ip-rib_ipv6_oper:SummaryProto";
            key "protoid";
            description
              "Route summary information for a specific
              table/protocol ";
            leaf protoid {
              xr:xr-xml-map "ip-rib_ipv6_oper:protoid";
              type int32;
              description "Proto ID";
            }
            uses RIB-EDM-PROTO-ROUTE-SUMM-DETAIL;
          }
        }

        container rib-table-itf-hndls {
          xr:xr-xml-map "ip-rib_ipv6_oper:RIBTableItf";
          description "RIB table interface";

          list rib-table-itf-hndl {
            xr:xr-xml-map "ip-rib_ipv6_oper:RIBTableItfHndl";
            key "handle";
            description "Interface handle";
            leaf handle {
              xr:xr-xml-map "ip-rib_ipv6_oper:handle";
              type int32;
              description "Itf Handle";
            }

            list itf-route {
              xr:xr-xml-map "ip-rib_ipv6_oper:ItfRoutes";
              key "address";
              description
                "Route information for a specific
                table/interface ";
              leaf address {
                xr:xr-xml-map "ip-rib_ipv6_oper:Address";
                type inet:ipv6-address-no-zone;
                description "Network Address ";
              }
              uses IPV6-RIB-EDM-ROUTE;
            }
          }
        }
        leaf tableid {
          xr:xr-xml-map "ip-rib_ipv6_oper:tableid";
          type xr:Hex-integer;
          description "Table ID";
        }
      }
    }
  }

  grouping NON-AS {
    description
      "Common node of local, connected, static,
      subscriber, mobile";

    container non-as {
      xr:xr-xml-map "ip-rib_ipv6_oper:NonAS";
      description "Non Autonomous System of protocol";
      uses INFORMATION;
      uses PROTOCOL-ROUTE-TABLE;
    }
  }

  grouping PROTOCOL-ROUTE-TABLE {
    description "Common node of as, non-as, l2vpn, lspv";

    container protocol-routes {
      xr:xr-xml-map "ip-rib_ipv6_oper:ProtocolRouteTable";
      description "Protocol specific Route";

      list protocol-route {
        xr:xr-xml-map "ip-rib_ipv6_oper:ProtocolRoute";
        description
          "Route information of a specific Network Address";
        leaf address {
          xr:xr-xml-map "ip-rib_ipv6_oper:Address";
          type inet:ipv6-address-no-zone;
          description "Network Address";
        }
        leaf prefix-length {
          xr:xr-xml-map "ip-rib_ipv6_oper:PrefixLength";
          type xr:Ipv6-prefix-length;
          description "Prefix Length ";
        }
        uses IPV6-RIB-EDM-ROUTE;
      }
    }
  }

  container ipv6-rib {
    xr:xr-xml-map "ip-rib_ipv6_oper:IPV6_RIB";
    config false;
    description "RIB operational data";
    uses RIB-TABLE;
    uses VRF-TABLE;
  }

  container ipv6-rib-stdby {
    xr:xr-xml-map "ip-rib_ipv6_oper:IPV6_RIB_STDBY";
    config false;
    description "ipv6 rib stdby";
    uses RIB-TABLE;
    uses VRF-TABLE;
  }
}
