submodule Cisco-IOS-XR-icpe-infra-oper-sub4 {

  belongs-to Cisco-IOS-XR-icpe-infra-oper {
    prefix Cisco-IOS-XR-icpe-infra-oper;
  }

  /*** LINKAGE (IMPORTS / INCLUDES) ***/

  import ietf-yang-types { prefix "yang"; }

  import Cisco-IOS-XR-types { prefix "xr"; }

  include Cisco-IOS-XR-icpe-infra-oper-sub5 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2015 by Cisco Systems, Inc.
     All rights reserved.";

  revision "2015-11-09" {
    description
      "IOS XR 6.0 revision.";
  }

  typedef Icpe-oper-topo-remote-source {
    type enumeration {
      enum icpe-oper-topo-remote-source-unknown {
        description "Unknown";
      }
      enum icpe-oper-topo-remote-source-remote-icl-id {
        description "Remote ICL ID";
      }
      enum icpe-oper-topo-remote-source-remote-satellite-mac {
        description "Remote satellite MAC";
      }
      enum icpe-oper-topo-remote-source-remote-host-mac {
        description "Remote host MAC";
      }
      enum icpe-oper-topo-remote-source-direct-satellite {
        description "Direct satellite";
      }
      enum icpe-oper-topo-remote-source-direct-host {
        description "Direct host";
      }
    }
    description "Icpe oper topo remote source";
  }

  grouping ICPE-OPER-TOPO-REMOTE-SFL-TYPE {
    description "ICPE OPER TOPO REMOTE SFL TYPE";
    leaf mac-address {
      xr:xr-xml-map "icpe_topo_oper_data_gen:MACAddress";
      type yang:mac-address;
      description "MAC address";
    }
    leaf source {
      xr:xr-xml-map "icpe_topo_oper_data_gen:Source";
      type Icpe-oper-topo-remote-source;
      description "Source";
    }
    leaf remote-is-satellite {
      xr:xr-xml-map "icpe_topo_oper_data_gen:RemoteIsSatellite";
      type boolean;
      description "Remote is satellite";
    }
    leaf remote-is-local-host {
      xr:xr-xml-map "icpe_topo_oper_data_gen:RemoteIsLocalHost";
      type boolean;
      description "Remote is local host";
    }
    leaf icl-id {
      xr:xr-xml-map "icpe_topo_oper_data_gen:ICL_ID";
      type uint32;
      description "ICL ID";
    }
    leaf interface-handle {
      xr:xr-xml-map "icpe_topo_oper_data_gen:InterfaceHandle";
      type xr:Interface-name;
      description "Interface handle";
    }
    leaf interface-name {
      xr:xr-xml-map "icpe_topo_oper_data_gen:InterfaceName";
      type Xr-yang-string;
      description "Interface name";
    }
  }

  grouping ICPE-OPER-TOPO-LOCAL-SFL-TYPE {
    description "ICPE OPER TOPO LOCAL SFL TYPE";
    leaf icl-id {
      xr:xr-xml-map "icpe_topo_oper_data_gen:ICL_ID";
      type uint32;
      description "ICL ID";
    }
    leaf interface-name {
      xr:xr-xml-map "icpe_topo_oper_data_gen:InterfaceName";
      type Xr-yang-string;
      description "Interface name";
    }
    leaf display-name {
      xr:xr-xml-map "icpe_topo_oper_data_gen:DisplayName";
      type Xr-yang-string;
      description "Display name";
    }
    leaf redundant {
      xr:xr-xml-map "icpe_topo_oper_data_gen:Redundant";
      type boolean;
      description "Redundant";
    }
    leaf active {
      xr:xr-xml-map "icpe_topo_oper_data_gen:Active";
      type boolean;
      description "Active";
    }
    leaf obsolete {
      xr:xr-xml-map "icpe_topo_oper_data_gen:Obsolete";
      type boolean;
      description "Obsolete";
    }

    list remote-device {
      description "Remote Device table";
      uses ICPE-OPER-TOPO-REMOTE-SFL-TYPE;
    }
  }

  grouping ICPE-OPER-TOPO-SATTUN-TYPE {
    description "ICPE OPER TOPO SATTUN TYPE";
    leaf mac-address {
      xr:xr-xml-map "icpe_topo_oper_data_gen:MACAddress";
      type yang:mac-address;
      description "MAC address";
    }
    leaf configured {
      xr:xr-xml-map "icpe_topo_oper_data_gen:Configured";
      type boolean;
      description "Configured";
    }
    leaf num-hops {
      xr:xr-xml-map "icpe_topo_oper_data_gen:NumHops";
      type uint16;
      description "Num hops";
    }
    leaf type {
      xr:xr-xml-map "icpe_topo_oper_data_gen:Type";
      type Xr-yang-string;
      description "Type";
    }
    leaf satellite-id {
      xr:xr-xml-map "icpe_topo_oper_data_gen:SatelliteID";
      type uint32;
      description "Satellite ID";
    }
    leaf received-serial-number {
      xr:xr-xml-map "icpe_topo_oper_data_gen:ReceivedSerialNumber";
      type Xr-yang-string;
      description "Received serial number";
    }
    leaf received-serial-number-present {
      xr:xr-xml-map "icpe_topo_oper_data_gen:ReceivedSerialNumberPr"+
        "esent";
      type boolean;
      description "Received serial number present";
    }
    leaf vlan-id {
      xr:xr-xml-map "icpe_topo_oper_data_gen:VLAN_ID";
      type uint16;
      description "VLAN ID";
    }
    leaf display-name {
      xr:xr-xml-map "icpe_topo_oper_data_gen:DisplayName";
      type Xr-yang-string;
      description "Display name";
    }
    leaf conflict-reason {
      xr:xr-xml-map "icpe_topo_oper_data_gen:ConflictReason";
      type Icpe-oper-conflict;
      description "Conflict reason";
    }
    leaf conflict-context {
      xr:xr-xml-map "icpe_topo_oper_data_gen:ConflictContext";
      type Xr-yang-string;
      description "Conflict context";
    }

    list fabric-link {
      description "Local Satellite Fabric Link table";
      uses ICPE-OPER-TOPO-LOCAL-SFL-TYPE;
    }
  }

  grouping ICPE-OPER-TOPO-DSFL-TYPE {
    description "ICPE OPER TOPO DSFL TYPE";
    leaf interface-name {
      xr:xr-xml-map "icpe_topo_oper_data_gen:InterfaceName";
      type Xr-yang-string;
      description "Interface name";
    }
    leaf interface-handle {
      xr:xr-xml-map "icpe_topo_oper_data_gen:InterfaceHandle";
      type xr:Interface-name;
      description "Interface handle";
    }
    leaf discovery-running {
      xr:xr-xml-map "icpe_topo_oper_data_gen:DiscoveryRunning";
      type boolean;
      description "Discovery running";
    }
  }

  grouping ICPE-OPER-TOPO-CSFL-TYPE {
    description "Satellite Topology Information";
    leaf interface-name-xr {
      xr:xr-xml-map "icpe_topo_oper_data_gen:interface-name-xr";
      type Xr-yang-string;
      description "Interface name";
    }
    leaf interface-handle {
      xr:xr-xml-map "icpe_topo_oper_data_gen:InterfaceHandle";
      type xr:Interface-name;
      description "Interface handle";
    }
    leaf redundancy-iccp-group {
      xr:xr-xml-map "icpe_topo_oper_data_gen:RedundancyICCPGroup";
      type uint32;
      description "Redundancy ICCP group";
    }
    leaf is-physical {
      xr:xr-xml-map "icpe_topo_oper_data_gen:IsPhysical";
      type boolean;
      description "Is physical";
    }
    leaf ring-whole {
      xr:xr-xml-map "icpe_topo_oper_data_gen:RingWhole";
      type boolean;
      description "Ring whole";
    }

    list discovered-link {
      description "Discovered Links table";
      uses ICPE-OPER-TOPO-DSFL-TYPE;
    }

    list satellite {
      description "Satellite table";
      uses ICPE-OPER-TOPO-SATTUN-TYPE;
    }
  }
}
