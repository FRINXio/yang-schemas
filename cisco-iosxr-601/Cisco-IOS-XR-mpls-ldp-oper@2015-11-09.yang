module Cisco-IOS-XR-mpls-ldp-oper {

  /*** NAMESPACE / PREFIX DEFINITION ***/

  namespace "http://cisco.com/ns/yang/Cisco-IOS-XR-mpls-ldp-oper";


  prefix "mpls-ldp-oper";

  /*** LINKAGE (IMPORTS / INCLUDES) ***/

  import ietf-inet-types { prefix "inet"; }

  import Cisco-IOS-XR-types { prefix "xr"; }

  include Cisco-IOS-XR-mpls-ldp-oper-sub2 {
    revision-date 2015-11-09;
  }

  include Cisco-IOS-XR-mpls-ldp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-ldp package operational data.

     This module contains definitions
     for the following management objects:
       mpls-ldp: MPLS LDP operational data

     Copyright (c) 2013-2015 by Cisco Systems, Inc.
     All rights reserved.";

  revision "2015-11-09" {
    description
      "IOS XR 6.0 revision.";
  }

  typedef Mpls-ldp-oper-af-name {
    type enumeration {
      enum ipv4 {
        value 1;
        description "IPv4";
      }
      enum ipv6 {
        value 2;
        description "IPv6";
      }
    }
    description "Mpls ldp oper af name";
  }

  grouping NSR-SUMMARY-ALL {
    description "Common node of active, standby, node";

    container nsr-summary-all {
      xr:xr-xml-map "mpls_ldp_oper:NSRSummaryAll";
      description "Summary information regarding LDP NSR State";
      uses LDP-NSR-SUM;
    }
  }

  grouping LDP-ID {
    description "Common node of default-vrf, vrf";

    container ldp-id {
      xr:xr-xml-map "mpls_ldp_vrf_oper:LDP_ID";
      description "Local LDP Id";
      uses LDP-LDPID-INFO;
    }
  }

  grouping CAPABILITY-TABLE {
    description "Common node of default-vrf, vrf";

    container capabilities {
      xr:xr-xml-map "mpls_ldp_vrf_oper:CapabilityTable";
      description "LDP capability database information";

      list capability {
        xr:xr-xml-map "mpls_ldp_vrf_oper:Capability";
        key "capability-type";
        description "Information on LDP capability";
        leaf capability-type {
          xr:xr-xml-map "mpls_ldp_vrf_oper:CapabilityType";
          type int32;
          description "The capability type (IANA assigned)";
        }
        uses LDP-CAP-INFO;
      }
    }
  }

  grouping NEIGHBOR-CAPABILITY-TABLE {
    description "Common node of default-vrf, vrf";

    container neighbor-capabilities {
      xr:xr-xml-map "mpls_ldp_vrf_oper:NeighborCapabilityTable";
      description "LDP Neighbors Capabilities";

      list neighbor-capability {
        xr:xr-xml-map "mpls_ldp_vrf_oper:NeighborCapability";
        description
          "Information on capabilities of a particular LDP
          neighbor";
        leaf lsr-id {
          xr:xr-xml-map "mpls_ldp_vrf_oper:LSR_ID";
          type inet:ip-address-no-zone;
          description "LSR ID of neighbor";
        }
        leaf label-space-id {
          xr:xr-xml-map "mpls_ldp_vrf_oper:LabelSpaceID";
          type uint32 {
            range "0..65535";
          }
          description "Label space ID of neighbor";
        }
        uses LDP-NBR-CAP-INFO;
      }
    }
  }

  grouping VRF-TABLE {
    description "Common node of active, standby, node";

    container vrfs {
      xr:xr-xml-map "mpls_ldp_vrf_oper:VRFTable";
      description "VRF specific operational data";

      list vrf {
        xr:xr-xml-map "mpls_ldp_vrf_oper:VRF";
        key "vrf-name";
        description "Operational data for given VRF";
        leaf vrf-name {
          xr:xr-xml-map "mpls_ldp_vrf_oper:VRFName";
          type xr:Cisco-ios-xr-string;
          description "VRF Name";
        }
        uses GRACEFUL-RESTART;
        uses CAPABILITY-TABLE;
        uses SUMMARY;
        uses AF-TABLE;
        uses NEIGHBOR-BRIEF-TABLE;
        uses BACKOFF-PARAMETERS;
        uses BACKOFF-TABLE;
        uses NSR;
        uses PARAMETERS;
        uses ISSU;
        uses NEIGHBOR-CAPABILITY-TABLE;
        uses NEIGHBOR-TABLE;
        uses LDP-ID;
        uses STATISTICS-TABLE;
      }
    }
  }

  grouping BACKOFF-PARAMETERS {
    description "Common node of default-vrf, vrf";

    container backoff-parameters {
      xr:xr-xml-map "mpls_ldp_vrf_oper:BackoffParameters";
      description "The LDP Backoff Parameters";
      uses LDP-BACKOFF-INFO;
    }
  }

  grouping HA-SUMMARY {
    description "Common node of nsr, issu";

    container ha-summary {
      xr:xr-xml-map "mpls_ldp_vrf_oper:HASummary";
      description "LDP HA Summary";
      uses LDP-NSR-SUM;
    }
  }

  grouping STATISTICS-TABLE {
    description "Common node of default-vrf, vrf";

    container statistics {
      xr:xr-xml-map "mpls_ldp_vrf_oper:StatisticsTable";
      description "The LDP Statistics";

      list statistic {
        xr:xr-xml-map "mpls_ldp_vrf_oper:Statistics";
        description
          "Statistical Information on a particular LDP
          neighbor";
        leaf lsr-id {
          xr:xr-xml-map "mpls_ldp_vrf_oper:LSR_ID";
          type inet:ip-address-no-zone;
          description "LSR ID of neighbor";
        }
        leaf label-space-id {
          xr:xr-xml-map "mpls_ldp_vrf_oper:LabelSpaceID";
          type uint32 {
            range "0..65535";
          }
          description "Label space ID of neighbor";
        }
        uses LDP-STATS-INFO;
      }
    }
  }

  grouping DISCOVERY-SUMMARY-ALL {
    description "Common node of active, standby, node";

    container discovery-summary-all {
      xr:xr-xml-map "mpls_ldp_oper:DiscoverySummaryAll";
      description "Summary information regarding LDP discovery";
      uses LDP-DISCOVERY-SUMMARY-INFO;
    }
  }

  grouping BINDINGS-SUMMARY-ALL {
    description "Common node of active, standby, node";

    container bindings-summary-all {
      xr:xr-xml-map "mpls_ldp_oper:BindingsSummaryAll";
      description
        "Aggregate VRF counters for the LDP Label
        Infomation Base (LIB)";
      uses LDP-BINDING-SUMMARY;
    }
  }

  grouping DEFAULT-VRF {
    description "Common node of active, standby, node";

    container default-vrf {
      xr:xr-xml-map "mpls_ldp_vrf_oper:DefaultVRF";
      description "DefaultVRF specific operational data";
      uses GRACEFUL-RESTART;
      uses CAPABILITY-TABLE;
      uses SUMMARY;
      uses AF-TABLE;
      uses NEIGHBOR-BRIEF-TABLE;
      uses BACKOFF-PARAMETERS;
      uses BACKOFF-TABLE;
      uses NSR;
      uses PARAMETERS;
      uses ISSU;
      uses NEIGHBOR-CAPABILITY-TABLE;
      uses NEIGHBOR-TABLE;
      uses LDP-ID;
      uses STATISTICS-TABLE;
    }
  }

  grouping NEIGHBOR-BRIEF-TABLE {
    description "Common node of default-vrf, vrf";

    container neighbor-briefs {
      xr:xr-xml-map "mpls_ldp_vrf_oper:NeighborBriefTable";
      description "The LDP Neighbors (brief)";

      list neighbor-brief {
        xr:xr-xml-map "mpls_ldp_vrf_oper:NeighborBrief";
        description
          "Brief information on a particular LDP neighbor";
        leaf lsr-id {
          xr:xr-xml-map "mpls_ldp_vrf_oper:LSR_ID";
          type inet:ip-address-no-zone;
          description "LSR ID of neighbor";
        }
        leaf label-space-id {
          xr:xr-xml-map "mpls_ldp_vrf_oper:LabelSpaceID";
          type uint32 {
            range "0..65535";
          }
          description "Label space ID of neighbor";
        }
        uses LDP-NEIGHBOR-BRIEF-INFO;
      }
    }
  }

  grouping PARAMETERS {
    description "Common node of default-vrf, vrf";

    container parameters {
      xr:xr-xml-map "mpls_ldp_vrf_oper:Parameters";
      description "LDP parameters";
      uses LDP-PARAMETERS;
    }
  }

  grouping FORWARDING-SUMMARY-ALL {
    description "Common node of active, standby, node";

    container forwarding-summary-all {
      xr:xr-xml-map "mpls_ldp_oper:ForwardingSummaryAll";
      description
        "Summary information regarding LDP forwarding
        setup";
      uses LDP-FWD-SUMM-INFO;
    }
  }

  grouping SUMMARY {
    description "Common node of default-vrf, vrf";

    container summary {
      xr:xr-xml-map "mpls_ldp_vrf_oper:Summary";
      description "LDP VRF summary";
      uses LDP-SUMMARY-VRF;
    }
  }

  grouping MPLS-LDP-OPER-SUMMARY {
    description "Common node of active, standby, node";

    container summary {
      xr:xr-xml-map "mpls_ldp_oper:Summary";
      description "LDP summary";
      uses LDP-SUMMARY;
    }
  }

  grouping HA-STATISTICS {
    description "Common node of nsr, issu";

    container ha-statistics {
      xr:xr-xml-map "mpls_ldp_vrf_oper:HAStatistics";
      description "LDP NSR Statistics related information";

      container ha-global {
        xr:xr-xml-map "mpls_ldp_vrf_oper:HAGlobal";
        description "LDP NSR Global Statistics information";
        uses LDP-NSR-GBL-STATS-INFO;
      }
      uses HA-NEIGHBOR-TABLE;
    }
  }

  grouping NSR {
    description "Common node of default-vrf, vrf";

    container nsr {
      xr:xr-xml-map "mpls_ldp_vrf_oper:NSR";
      description "LDP NSR related information";

      container nsr-pending {
        xr:xr-xml-map "mpls_ldp_vrf_oper:NSRPending";
        description "LDP NSR Pending related information";
        uses HA-NEIGHBOR-TABLE;
      }
      uses HA-SUMMARY;
      uses HA-STATISTICS;
    }
  }

  grouping GRACEFUL-RESTART {
    description "Common node of default-vrf, vrf";

    container graceful-restart {
      xr:xr-xml-map "mpls_ldp_vrf_oper:GracefulRestart";
      description "LDP Graceful Restart info";
      uses LDP-GR-GLOBAL-INFO;
    }
  }

  grouping HA-NEIGHBOR-TABLE {
    description "Common node of nsr-pending, ha-statistics";

    container ha-neighbors {
      xr:xr-xml-map "mpls_ldp_vrf_oper:HANeighborTable";
      description "The LDP HA Neighbors";

      list ha-neighbor {
        xr:xr-xml-map "mpls_ldp_vrf_oper:HANeighbor";
        description "Information on a particular LDP HA neighbor";
        leaf lsr-id {
          xr:xr-xml-map "mpls_ldp_vrf_oper:LSR_ID";
          type inet:ip-address-no-zone;
          description "LSR ID of neighbor";
        }
        leaf label-space-id {
          xr:xr-xml-map "mpls_ldp_vrf_oper:LabelSpaceID";
          type uint32 {
            range "0..65535";
          }
          description "Label space ID of neighbor";
        }
        uses LDP-NSR-STATS-NBR-INFO;
      }
    }
  }

  grouping NEIGHBOR-TABLE {
    description "Common node of default-vrf, vrf";

    container neighbors {
      xr:xr-xml-map "mpls_ldp_vrf_oper:NeighborTable";
      description "The LDP Neighbors";

      list neighbor {
        xr:xr-xml-map "mpls_ldp_vrf_oper:Neighbor";
        description "Information on a particular LDP neighbor";
        leaf lsr-id {
          xr:xr-xml-map "mpls_ldp_vrf_oper:LSR_ID";
          type inet:ip-address-no-zone;
          description "LSR ID of neighbor";
        }
        leaf label-space-id {
          xr:xr-xml-map "mpls_ldp_vrf_oper:LabelSpaceID";
          type uint32 {
            range "0..65535";
          }
          description "Label space ID of neighbor";
        }
        uses LDP-NEIGHBOR-INFO;
      }
    }
  }

  grouping ISSU {
    description "Common node of default-vrf, vrf";

    container issu {
      xr:xr-xml-map "mpls_ldp_vrf_oper:ISSU";
      description "LDP ISSU related information";
      uses HA-SUMMARY;
      uses HA-STATISTICS;
    }
  }

  grouping BACKOFF-TABLE {
    description "Common node of default-vrf, vrf";

    container backoffs {
      xr:xr-xml-map "mpls_ldp_vrf_oper:BackoffTable";
      description "The LDP backoff";

      list backoff {
        xr:xr-xml-map "mpls_ldp_vrf_oper:Backoff";
        description "LDP Backoff Information";
        leaf lsr-id {
          xr:xr-xml-map "mpls_ldp_vrf_oper:LSR_ID";
          type inet:ip-address-no-zone;
          description "LSR ID of neighbor";
        }
        leaf label-space-id {
          xr:xr-xml-map "mpls_ldp_vrf_oper:LabelSpaceID";
          type uint32 {
            range "0..65535";
          }
          description "Label space ID of neighbor";
        }
        uses LDP-BACKOFF-ENTRY-INFO;
      }
    }
  }

  grouping AF-TABLE {
    description "Common node of default-vrf, vrf";

    container afs {
      xr:xr-xml-map "mpls_ldp_vrf_oper:AFTable";
      description "Address Family specific operational data";

      list af {
        xr:xr-xml-map "mpls_ldp_vrf_oper:AF";
        key "af-name";
        description "Operational data for given Address Family";

        container interface-summary {
          xr:xr-xml-map "mpls_ldp_vrf_oper:InterfaceSummary";
          description "IPv4 interface summary information";
          uses LDP-INTF-SUM;
        }

        container bindings {
          xr:xr-xml-map "mpls_ldp_vrf_oper:BindingTable";
          description "The LDP Bindings";

          list binding {
            xr:xr-xml-map "mpls_ldp_vrf_oper:Binding";
            key "prefix";
            description "Binding Information";
            leaf prefix {
              xr:xr-xml-map "mpls_ldp_vrf_oper:Prefix";
              type inet:ip-prefix;
              description "The IP Prefix";
            }
            uses LDP-TIB-ENTRY-DETAIL;
          }
        }

        container igp {
          xr:xr-xml-map "mpls_ldp_vrf_oper:IGP";
          description "LDP IGP related information";

          container syncs {
            xr:xr-xml-map "mpls_ldp_vrf_oper:SyncTable";
            description "LDP IGP Sync related information";

            list sync {
              xr:xr-xml-map "mpls_ldp_vrf_oper:Sync";
              key "interface-name";
              description
                "LDP-IGP Synchronization related information
                for an interface";
              leaf interface-name {
                xr:xr-xml-map "mpls_ldp_vrf_oper:InterfaceName";
                type xr:Interface-name;
                description "The Interface Name";
              }
              uses LDP-IGP-SYNC-INFO;
            }
          }

          container sync-delay-restart {
            xr:xr-xml-map "mpls_ldp_vrf_oper:SyncDelayRestart";
            description
              "LDP-IGP Synchronization Delay related
              information";
            uses LDP-IGP-SYNC-DELAY-RESTART-INFO;
          }
        }

        container bindings-summary {
          xr:xr-xml-map "mpls_ldp_vrf_oper:BindingsSummary";
          description
            "Counters for the LDP Label Infomation Base
            (LIB)";
          uses LDP-BINDING-SUMMARY;
        }

        container interfaces {
          xr:xr-xml-map "mpls_ldp_vrf_oper:InterfaceTable";
          description "LDP Interface related information";

          list interface {
            xr:xr-xml-map "mpls_ldp_vrf_oper:Interface";
            key "interface-name";
            description "IPv4 interface information";
            leaf interface-name {
              xr:xr-xml-map "mpls_ldp_vrf_oper:InterfaceName";
              type xr:Interface-name;
              description "The Interface Name";
            }
            uses LDP-INTF;
          }
        }

        container discovery {
          xr:xr-xml-map "mpls_ldp_vrf_oper:Discovery";
          description "The LDP Discovery";

          container link-hellos {
            xr:xr-xml-map "mpls_ldp_vrf_oper:LinkHelloTable";
            description "The LDP Discovery link";

            list link-hello {
              xr:xr-xml-map "mpls_ldp_vrf_oper:LinkHello";
              key "interface-name";
              description "Information on LDP link discovery";
              leaf interface-name {
                xr:xr-xml-map "mpls_ldp_vrf_oper:InterfaceName";
                type xr:Interface-name;
                description "The Interface Name";
              }
              uses LDP-DISCOVERY-LINK-INFO;
            }
          }

          container summary {
            xr:xr-xml-map "mpls_ldp_vrf_oper:Summary";
            description "Summarized information on LDP discovery";
            uses LDP-DISCOVERY-SUMMARY-INFO;
          }

          container targeted-hellos {
            xr:xr-xml-map "mpls_ldp_vrf_oper:TargetedHelloTable";
            description "The LDP Discovery Targeted";

            list targeted-hello {
              xr:xr-xml-map "mpls_ldp_vrf_oper:TargetedHello";
              description "Information on LDP targeted discovery";
              leaf local-address {
                xr:xr-xml-map "mpls_ldp_vrf_oper:LocalAddress";
                type inet:ip-address-no-zone;
                description "Local IP Address";
              }
              leaf target-address {
                xr:xr-xml-map "mpls_ldp_vrf_oper:TargetAddress";
                type inet:ip-address-no-zone;
                description "The target IP Address";
              }
              uses LDP-TARGETED-HELLO-INFO;
            }
          }

          container brief {
            xr:xr-xml-map "mpls_ldp_vrf_oper:Brief";
            description "Brief information on LDP discovery";

            container link-hello-briefs {
              xr:xr-xml-map "mpls_ldp_vrf_oper:LinkHelloBriefTable";
              description
                "The LDP Discovery link brief information";

              list link-hello-brief {
                xr:xr-xml-map "mpls_ldp_vrf_oper:LinkHelloBrief";
                key "interface-name";
                description
                  "Brief information on LDP link discovery";
                leaf interface-name {
                  xr:xr-xml-map "mpls_ldp_vrf_oper:InterfaceName";
                  type xr:Interface-name;
                  description "The Interface Name";
                }
                uses LDP-DISCOVERY-LINK-BRIEF-INFO;
              }
            }

            container targeted-hello-briefs {
              xr:xr-xml-map "mpls_ldp_vrf_oper:TargetedHelloBriefTa"+
                "ble";
              description
                "The LDP Discovery Targeted brief information";

              list targeted-hello-brief {
                xr:xr-xml-map "mpls_ldp_vrf_oper:TargetedHelloBrief";
                description
                  "Brief information on LDP targeted discovery";
                leaf local-address {
                  xr:xr-xml-map "mpls_ldp_vrf_oper:LocalAddress";
                  type inet:ip-address-no-zone;
                  description "Local IP Address";
                }
                leaf target-address {
                  xr:xr-xml-map "mpls_ldp_vrf_oper:TargetAddress";
                  type inet:ip-address-no-zone;
                  description "The target IP Address";
                }
                uses LDP-TARGETED-HELLO-BRIEF-INFO;
              }
            }
          }

          container stats {
            xr:xr-xml-map "mpls_ldp_vrf_oper:StatTable";
            description "The LDP Discovery Statistics";

            list stat {
              xr:xr-xml-map "mpls_ldp_vrf_oper:Stat";
              description "Information on LDP discovery statistics";
              leaf lsr-id {
                xr:xr-xml-map "mpls_ldp_vrf_oper:LSR_ID";
                type inet:ip-address-no-zone;
                description "LSR ID of neighbor";
              }
              leaf label-space-id {
                xr:xr-xml-map "mpls_ldp_vrf_oper:LabelSpaceID";
                type uint32 {
                  range "0..65535";
                }
                description "Label space ID of neighbor";
              }
              uses LDP-DISCOVERY-ADJ-GRP-INFO;
            }
          }
        }

        container bindings-summary-all {
          xr:xr-xml-map "mpls_ldp_vrf_oper:BindingsSummaryAll";
          description
            "Aggregate VRF counters for the LDP Label
            Infomation Base (LIB)";
          uses LDP-BINDING-SUMMARY;
        }

        container forwardings {
          xr:xr-xml-map "mpls_ldp_vrf_oper:ForwardingTable";
          description "The LDP Forwarding rewrites";

          list forwarding {
            xr:xr-xml-map "mpls_ldp_vrf_oper:Forwarding";
            key "prefix";
            description
              "Information on a particular LDP forwarding
              rewrite";
            leaf prefix {
              xr:xr-xml-map "mpls_ldp_vrf_oper:Prefix";
              type inet:ip-prefix;
              description "The IP Prefix";
            }
            uses LDP-FWD-PFX-INFO;
          }
        }

        container bindings-advertise-spec {
          xr:xr-xml-map "mpls_ldp_vrf_oper:BindingsAdvertiseSpec";
          description
            "Advertisement Spec (ACL) for LDP Label
            Infomation Base (LIB)";
          uses LDP-BINDING-ADVT-SPEC;
        }

        container forwarding-summary {
          xr:xr-xml-map "mpls_ldp_vrf_oper:ForwardingSummary";
          description
            "Summary information regarding LDP forwarding
            setup";
          uses LDP-FWD-SUMM-INFO;
        }
        leaf af-name {
          xr:xr-xml-map "mpls_ldp_vrf_oper:AFName";
          type Mpls-ldp-oper-af-name;
          description "Address Family name";
        }
      }
    }
  }

  container mpls-ldp {
    xr:xr-xml-map "mpls_ldp_common_oper:MPLS_LDP";
    config false;
    description "MPLS LDP operational data";

    container global {
      xr:xr-xml-map "mpls_ldp_common_oper:Global";
      description "Global MPLS LDP operational data";

      container standby {
        xr:xr-xml-map "mpls_ldp_common_oper:Standby";
        description "Standby MPLS LDP operational data";
        uses DEFAULT-VRF;
        uses FORWARDING-SUMMARY-ALL;
        uses BINDINGS-SUMMARY-ALL;
        uses NSR-SUMMARY-ALL;
        uses MPLS-LDP-OPER-SUMMARY;
        uses VRF-TABLE;
        uses DISCOVERY-SUMMARY-ALL;
      }

      container active {
        xr:xr-xml-map "mpls_ldp_common_oper:Active";
        description "Active MPLS LDP operational data";
        uses DEFAULT-VRF;
        uses FORWARDING-SUMMARY-ALL;
        uses BINDINGS-SUMMARY-ALL;
        uses NSR-SUMMARY-ALL;
        uses MPLS-LDP-OPER-SUMMARY;
        uses VRF-TABLE;
        uses DISCOVERY-SUMMARY-ALL;
      }
    }

    container nodes {
      xr:xr-xml-map "mpls_ldp_common_oper:NodeTable";
      description "Location MPLS LDP operational data";

      list node {
        xr:xr-xml-map "mpls_ldp_common_oper:Node";
        key "node-name";
        description
          "The MPLD LDP operational data for a particular
          node";
        leaf node-name {
          xr:xr-xml-map "mpls_ldp_common_oper:NodeName";
          type xr:Node-id;
          description "The identifier for the node";
        }
        uses DEFAULT-VRF;
        uses FORWARDING-SUMMARY-ALL;
        uses BINDINGS-SUMMARY-ALL;
        uses NSR-SUMMARY-ALL;
        uses MPLS-LDP-OPER-SUMMARY;
        uses VRF-TABLE;
        uses DISCOVERY-SUMMARY-ALL;
      }
    }
  }
}
