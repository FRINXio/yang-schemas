submodule Cisco-IOS-XR-ip-udp-oper-sub3 {

  belongs-to Cisco-IOS-XR-ip-udp-oper {
    prefix Cisco-IOS-XR-ip-udp-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-udp package operational data.

     Copyright (c) 2013-2015 by Cisco Systems, Inc.
     All rights reserved.";

  revision "2015-11-09" {
    description
      "IOS XR 6.0 revision.";
  }


  grouping TRANSP-CLIENT-STATS-BAG {
    description "Aggregated statistics of a transport client";
    leaf client-jid {
      xr:xr-xml-map "ip_transport_clients:ClientJID";
      type int32;
      description "Job ID of the transport client";
    }
    leaf client-name {
      xr:xr-xml-map "ip_transport_clients:ClientName";
      type string {
        length "0..21";
      }
      description "Transport client name";
    }
    leaf ipv4-received-packets {
      xr:xr-xml-map "ip_transport_clients:IPv4ReceivedPackets";
      type uint32;
      description "Total IPv4 packets received from client";
    }
    leaf ipv4-sent-packets {
      xr:xr-xml-map "ip_transport_clients:IPv4SentPackets";
      type uint32;
      description "Total IPv4 packets sent to client";
    }
    leaf ipv6-received-packets {
      xr:xr-xml-map "ip_transport_clients:IPv6ReceivedPackets";
      type uint32;
      description "Total IPv6 packets received from app";
    }
    leaf ipv6-sent-packets {
      xr:xr-xml-map "ip_transport_clients:IPv6SentPackets";
      type uint32;
      description "Total IPv6 packets sent to app";
    }
  }
}
