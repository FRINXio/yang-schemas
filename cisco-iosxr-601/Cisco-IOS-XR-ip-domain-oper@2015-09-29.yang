module Cisco-IOS-XR-ip-domain-oper {

  /*** NAMESPACE / PREFIX DEFINITION ***/

  namespace "http://cisco.com/ns/yang/Cisco-IOS-XR-ip-domain-oper";


  prefix "ip-domain-oper";

  /*** LINKAGE (IMPORTS / INCLUDES) ***/

  import Cisco-IOS-XR-types { prefix "xr"; }

  include Cisco-IOS-XR-ip-domain-oper-sub1 {
    revision-date 2015-09-29;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-domain package operational data.

     This module contains definitions
     for the following management objects:
       ip-domain: Domain server and host data

     Copyright (c) 2013-2015 by Cisco Systems, Inc.
     All rights reserved.";

  revision "2015-09-29" {
    description
      "IOS XR 6.0.0 revision.";
  }

  revision "2015-01-07" {
    description
      "IOS XR 5.3.1 revision.";
  }


  container ip-domain {
    xr:xr-xml-map "ip_domain_oper:IPDomain";
    config false;
    description "Domain server and host data";

    container vrfs {
      xr:xr-xml-map "ip_domain_vrf_oper:VRFTable";
      description "List of VRFs";

      list vrf {
        xr:xr-xml-map "ip_domain_vrf_oper:VRF";
        key "vrf-name";
        description "VRF instance";

        container server {
          xr:xr-xml-map "ip_domain_vrf_oper:Server";
          description "Domain server data";
          uses DOMAIN-SH-SERVER-BAG;
        }

        container hosts {
          xr:xr-xml-map "ip_domain_vrf_oper:HostTable";
          description "List of domain hosts";

          list host {
            xr:xr-xml-map "ip_domain_vrf_oper:Host";
            key "host-name";
            description
              "IP domain-name, lookup style, nameservers for
              specific host";
            leaf host-name {
              xr:xr-xml-map "ip_domain_vrf_oper:Hostname";
              type string;
              description "Hostname";
            }
            uses DOMAIN-SH-HOSTS-BAG;
          }
        }
        leaf vrf-name {
          xr:xr-xml-map "ip_domain_vrf_oper:VRFName";
          type xr:Cisco-ios-xr-string;
          description "VRF name";
        }
      }
    }
  }
}
