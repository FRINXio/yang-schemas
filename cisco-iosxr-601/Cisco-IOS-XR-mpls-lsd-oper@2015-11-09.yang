module Cisco-IOS-XR-mpls-lsd-oper {

  /*** NAMESPACE / PREFIX DEFINITION ***/

  namespace "http://cisco.com/ns/yang/Cisco-IOS-XR-mpls-lsd-oper";


  prefix "mpls-lsd-oper";

  /*** LINKAGE (IMPORTS / INCLUDES) ***/

  import ietf-inet-types { prefix "inet"; }

  import Cisco-IOS-XR-types { prefix "xr"; }

  include Cisco-IOS-XR-mpls-lsd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-lsd package operational data.

     This module contains definitions
     for the following management objects:
       mpls-lsd-nodes: Location MPLS LSD operational data
       mpls-lsd: mpls lsd

     Copyright (c) 2013-2015 by Cisco Systems, Inc.
     All rights reserved.";

  revision "2015-11-09" {
    description
      "IOS XR 6.0 revision.";
  }


  grouping REWRITE-SUMMARY {
    description "Common node of mpls-lsd, mpls-lsd-node";

    container rewrite-summary {
      xr:xr-xml-map "mpls_lsd_oper:RewriteSummary";
      description "Rewrite Summary ";
      uses MPLS-LSD-RW-SUM;
    }
  }

  grouping LABEL-SUMMARY {
    description "Common node of mpls-lsd, mpls-lsd-node";

    container label-summary {
      xr:xr-xml-map "mpls_lsd_oper:LabelSummary";
      description "Dynamic label range";
      uses MPLS-LSD-LBL-SUM;
    }
  }

  grouping LABEL-TABLE {
    description "Common node of mpls-lsd, mpls-lsd-node";

    container labels {
      xr:xr-xml-map "mpls_lsd_oper:LabelTable";
      description "Table of labels";

      list label {
        xr:xr-xml-map "mpls_lsd_oper:Label";
        key "label-id";
        description "Data for label";
        leaf label-id {
          xr:xr-xml-map "mpls_lsd_oper:LabelID";
          type int32;
          description "Label value";
        }
        uses MPLS-LSD-LBL;
      }
    }
  }

  grouping FRR-DATABASE {
    description "Common node of mpls-lsd, mpls-lsd-node";

    container frr-database {
      xr:xr-xml-map "mpls_lsd_oper:FRRDatabase";
      description "FRR database";

      container tunnel-midpoints {
        xr:xr-xml-map "mpls_lsd_oper:TunnelMidpointTable";
        description
          "Table of FRR database entries - Tunnel
          midpoints";

        list tunnel-midpoint {
          xr:xr-xml-map "mpls_lsd_oper:TunnelMidpoint";
          key "label";
          description
            "Data for FRR database entry - Tunnel midpoint";
          leaf label {
            xr:xr-xml-map "mpls_lsd_oper:Label";
            type int32;
            description "Label value";
          }
          uses MPLS-LSD-FRR-DB-ENTRY;
        }
      }

      container tunnel-heads {
        xr:xr-xml-map "mpls_lsd_oper:TunnelHeadTable";
        description "Table of FRR database entries - Tunnel heads";

        list tunnel-head {
          xr:xr-xml-map "mpls_lsd_oper:TunnelHead";
          key "interface-name";
          description "Data for FRR database entry - Tunnel head";
          leaf interface-name {
            xr:xr-xml-map "mpls_lsd_oper:InterfaceName";
            type xr:Interface-name;
            description "Tunnel interface";
          }
          uses MPLS-LSD-FRR-DB-ENTRY;
        }
      }

      container tunnel-head-summary {
        xr:xr-xml-map "mpls_lsd_oper:TunnelHeadSummary";
        description
          "Summary data for FRR database entry - Tunnel
          head";
        uses MPLS-LSD-FRR-DB-SUM;
      }

      container summary-protected-interfaces {
        xr:xr-xml-map "mpls_lsd_oper:SummaryProtectedInterfacefTabl"+
          "e";
        description "Sumary table of Protected Interfaces";

        list summary-protected-interface {
          xr:xr-xml-map "mpls_lsd_oper:SummaryProtectedInterface";
          key "interface-name";
          description "Data for MPLS interface";
          leaf interface-name {
            xr:xr-xml-map "mpls_lsd_oper:InterfaceName";
            type xr:Interface-name;
            description "Interface";
          }
          uses MPLS-LSD-FRR-DB-SUM;
        }
      }

      container tunnel-summary {
        xr:xr-xml-map "mpls_lsd_oper:TunnelSummary";
        description "Summary data for FRR database entry";
        uses MPLS-LSD-FRR-DB-SUM;
      }

      container tunnel-midpoint-summary {
        xr:xr-xml-map "mpls_lsd_oper:TunnelMidpointSummary";
        description
          "Summary data for FRR database entry - Tunnel
          midpoint";
        uses MPLS-LSD-FRR-DB-SUM;
      }
    }
  }

  grouping LABEL-RANGE {
    description "Common node of mpls-lsd, mpls-lsd-node";

    container label-range {
      xr:xr-xml-map "mpls_lsd_oper:LabelRange";
      description "Label range";
      uses MPLS-LSD-LBL-RANGE;
    }
  }

  grouping CLIENT-TABLE {
    description "Common node of mpls-lsd, mpls-lsd-node";

    container clients {
      xr:xr-xml-map "mpls_lsd_oper:ClientTable";
      description "Table of MPLS clients using LSD";

      list client {
        xr:xr-xml-map "mpls_lsd_oper:Client";
        key "client-name";
        description "Data for MPLS client using LSD";
        leaf client-name {
          xr:xr-xml-map "mpls_lsd_oper:ClientName";
          type xr:Cisco-ios-xr-string;
          description
            "Client Instance name in the form of    
            'Application-<client_name>' or     
            'BCDL_Agent-<index:parent_index>'";
        }
        uses MPLS-LSD-CLIENT;
      }
    }
  }

  grouping LABEL-SUMMARY-VRF-TABLE {
    description "Common node of mpls-lsd, mpls-lsd-node";

    container label-summary-vrfs {
      xr:xr-xml-map "mpls_lsd_oper:LabelSummaryVRFTable";
      description "Dynamic label range summary by VRF";

      list label-summary-vrf {
        xr:xr-xml-map "mpls_lsd_oper:LabelSummaryVRF";
        key "vrf-name";
        description "Dynamic label range summary by VRF";
        leaf vrf-name {
          xr:xr-xml-map "mpls_lsd_oper:VRFName";
          type xr:Cisco-ios-xr-string;
          description "VRF name";
        }
        uses MPLS-LSD-LBL-SUM;
      }
    }
  }

  grouping APPLICATION-TABLE {
    description "Common node of mpls-lsd, mpls-lsd-node";

    container applications {
      xr:xr-xml-map "mpls_lsd_oper:ApplicationTable";
      description "Table of MPLS applications using LSD";

      list application {
        xr:xr-xml-map "mpls_lsd_oper:Application";
        key "application-name";
        description "Data for MPLS application using LSD";
        leaf application-name {
          xr:xr-xml-map "mpls_lsd_oper:ApplicationName";
          type xr:Cisco-ios-xr-string;
          description
            "Application Instance name in the form of
            '<app_type_name>[:<instance>]'";
        }
        uses MPLS-LSD-APP;
      }
    }
  }

  grouping REWRITE-SUMMARY-VRF-TABLE {
    description "Common node of mpls-lsd, mpls-lsd-node";

    container rewrite-summary-vrfs {
      xr:xr-xml-map "mpls_lsd_oper:RewriteSummaryVRFTable";
      description "Rewrite Summary by VRF";

      list rewrite-summary-vrf {
        xr:xr-xml-map "mpls_lsd_oper:RewriteSummaryVRF";
        key "vrf-name";
        description "Rewrite summary by VRF VRF-name";
        leaf vrf-name {
          xr:xr-xml-map "mpls_lsd_oper:VRFName";
          type xr:Cisco-ios-xr-string;
          description "VRF name";
        }
        uses MPLS-LSD-RW-SUM;
      }
    }
  }

  grouping INTERFACE-TABLE {
    description "Common node of mpls-lsd, mpls-lsd-node";

    container interfaces {
      xr:xr-xml-map "mpls_lsd_oper:InterfaceTable";
      description "Table of MPLS interfaces";

      list interface {
        xr:xr-xml-map "mpls_lsd_oper:Interface";
        key "interface-name";
        description "Data for MPLS interface";
        leaf interface-name {
          xr:xr-xml-map "mpls_lsd_oper:InterfaceName";
          type xr:Interface-name;
          description "Interface";
        }
        uses MPLS-LSD-INTF;
      }
    }
  }

  grouping REWRITE {
    description "Common node of mpls-lsd, mpls-lsd-node";

    container rewrite {
      xr:xr-xml-map "mpls_lsd_oper:Rewrite";
      description "Table of rewrites";

      container rewrite-pws {
        xr:xr-xml-map "mpls_lsd_oper:RewritePWListTable";
        description "Table of Rewrites";

        list rewrite-pw {
          xr:xr-xml-map "mpls_lsd_oper:RewritePWList";
          key "pw-list-id";
          description "FPI rewrite for PW List";
          leaf pw-list-id {
            xr:xr-xml-map "mpls_lsd_oper:PWListID";
            type int32;
            description "PW List ID";
          }
          uses MPLS-LSD-RW;
        }
      }

      container rewrite-ipv4s {
        xr:xr-xml-map "mpls_lsd_oper:RewriteIPv4Table";
        description "Table of Rewrites";

        list rewrite-ipv4 {
          xr:xr-xml-map "mpls_lsd_oper:RewriteIPv4";
          description "FPI rewrite for label";
          leaf rsi-table-name {
            xr:xr-xml-map "mpls_lsd_oper:RSITableName";
            type xr:Cisco-ios-xr-string;
            description "RSI table name";
          }
          leaf rsi-table-id {
            xr:xr-xml-map "mpls_lsd_oper:RSITableID";
            type xr:Hex-integer;
            description "RSI table ID";
          }
          leaf prefix {
            xr:xr-xml-map "mpls_lsd_oper:Prefix";
            type inet:ipv4-address-no-zone;
            description "IPv4 Prefix";
          }
          leaf prefix-length {
            xr:xr-xml-map "mpls_lsd_oper:PrefixLength";
            type int32;
            description "Prefix length";
          }
          uses MPLS-LSD-RW;
        }
      }

      container rewrite-tes {
        xr:xr-xml-map "mpls_lsd_oper:RewriteTETable";
        description "Table of Traffic Engineering Rewrites";

        list rewrite-te {
          xr:xr-xml-map "mpls_lsd_oper:RewriteTE";
          key "interface-name";
          description "FPI rewrite for TE";
          leaf interface-name {
            xr:xr-xml-map "mpls_lsd_oper:InterfaceName";
            type xr:Interface-name;
            description "Tunnel interface";
          }
          uses MPLS-LSD-RW;
        }
      }

      container rewrite-labels {
        xr:xr-xml-map "mpls_lsd_oper:RewriteLabelTable";
        description "Table of Rewrites";

        list rewrite-label {
          xr:xr-xml-map "mpls_lsd_oper:RewriteLabel";
          key "label-id";
          description "FPI rewrite for label";
          leaf label-id {
            xr:xr-xml-map "mpls_lsd_oper:LabelID";
            type int32;
            description "Label value";
          }
          uses MPLS-LSD-RW;
        }
      }
    }
  }

  container mpls-lsd-nodes {
    xr:xr-xml-map "mpls_lsd_oper:MPLS_LSDNodeTable";
    config false;
    description "Location MPLS LSD operational data";

    list mpls-lsd-node {
      xr:xr-xml-map "mpls_lsd_oper:MPLS_LSDNode";
      key "node-name";
      description
        "The MPLS LSD operational data for a particular
        node";
      leaf node-name {
        xr:xr-xml-map "mpls_lsd_oper:NodeName";
        type xr:Node-id;
        description "The identifier for the node";
      }
      uses CLIENT-TABLE;
      uses LABEL-SUMMARY;
      uses LABEL-TABLE;
      uses FRR-DATABASE;
      uses REWRITE;
      uses REWRITE-SUMMARY;
      uses APPLICATION-TABLE;
      uses LABEL-SUMMARY-VRF-TABLE;
      uses LABEL-RANGE;
      uses REWRITE-SUMMARY-VRF-TABLE;
      uses INTERFACE-TABLE;
    }
  }

  container mpls-lsd {
    xr:xr-xml-map "mpls_lsd_oper:MPLS_LSD";
    config false;
    description "mpls lsd";
    uses CLIENT-TABLE;
    uses LABEL-SUMMARY;
    uses LABEL-TABLE;
    uses FRR-DATABASE;
    uses REWRITE;
    uses REWRITE-SUMMARY;
    uses APPLICATION-TABLE;
    uses LABEL-SUMMARY-VRF-TABLE;
    uses LABEL-RANGE;
    uses REWRITE-SUMMARY-VRF-TABLE;
    uses INTERFACE-TABLE;
  }
}
