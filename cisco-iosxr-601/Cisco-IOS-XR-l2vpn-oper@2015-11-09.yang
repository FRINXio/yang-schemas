module Cisco-IOS-XR-l2vpn-oper {

  /*** NAMESPACE / PREFIX DEFINITION ***/

  namespace "http://cisco.com/ns/yang/Cisco-IOS-XR-l2vpn-oper";


  prefix "l2vpn-oper";

  /*** LINKAGE (IMPORTS / INCLUDES) ***/

  import ietf-inet-types { prefix "inet"; }

  import ietf-yang-types { prefix "yang"; }

  import Cisco-IOS-XR-types { prefix "xr"; }

  include Cisco-IOS-XR-l2vpn-oper-sub4 {
    revision-date 2015-11-09;
  }

  include Cisco-IOS-XR-l2vpn-oper-sub3 {
    revision-date 2015-11-09;
  }

  include Cisco-IOS-XR-l2vpn-oper-sub2 {
    revision-date 2015-11-09;
  }

  include Cisco-IOS-XR-l2vpn-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR l2vpn package operational data.

     This module contains definitions
     for the following management objects:
       l2vpn-forwarding: Show L2VPN forwarding
       l2vpnv2: l2vpnv2
       l2vpn: l2vpn
       generic-interface-list-v2: generic interface list v2

     Copyright (c) 2013-2015 by Cisco Systems, Inc.
     All rights reserved.";

  revision "2015-11-09" {
    description
      "IOS XR 6.0 revision.";
  }

  typedef L2vpn-service {
    type enumeration {
      enum vpws {
        value 0;
        description "VPWS service";
      }
      enum vpls {
        value 1;
        description "VPLS service";
      }
    }
    description "L2vpn service";
  }
  typedef L2vpnp2mp-ptree {
    type enumeration {
      enum rsvp-te {
        value 1;
        description "RSVPTE Type";
      }
      enum mldp {
        value 2;
        description "MLDP Type";
      }
    }
    description "L2vpnp2mp ptree";
  }
  typedef L2vpnpw {
    type enumeration {
      enum manual {
        value 1;
        description "Manual pseudowire";
      }
      enum vpls-autodiscovered {
        value 2;
        description "VPLS autodiscovered pseudowire";
      }
      enum vpws-autodiscovered {
        value 3;
        description "VPWS autodiscovered pseudowire";
      }
      enum vpls-autodiscovered-ldp {
        value 4;
        description
          "VPLS autodiscovered pseudowire with LDP
          signaling";
      }
    }
    description "L2vpnpw";
  }

  grouping G8032-SUMMARY {
    description "Common node of l2vpn, active, standby, node";

    container g8032-summary {
      xr:xr-xml-map "l2vpn_oper:G8032Summary";
      description "G8032 summary table";

      container g8032-ring-summaries {
        xr:xr-xml-map "l2vpn_oper:G8032RingSummaryTable";
        description "G8032 Ring summary table";

        list g8032-ring-summary {
          xr:xr-xml-map "l2vpn_oper:G8032RingSummary";
          key "ring-name";
          description "G8032 Ring summary table";

          container g8032-ring-summary-info {
            xr:xr-xml-map "l2vpn_oper:G8032RingSummaryInfo";
            description "G8032 Ring summary info";
            uses L2VPN-G8032-RING-SUMMARY-INFO;
          }

          container g8032-ring-instance-summaries {
            xr:xr-xml-map "l2vpn_oper:G8032RingInstanceSummaryTable";
            description "G8032 Ring Instances summary table";

            list g8032-ring-instance-summary {
              xr:xr-xml-map "l2vpn_oper:G8032RingInstanceSummary";
              key "instance";
              description "G8032 Ring summary info";
              leaf instance {
                xr:xr-xml-map "l2vpn_oper:Instance";
                type int32;
                description "Instance";
              }
              uses L2VPN-G8032-RING-INSTANCE-SUMMARY-INFO;
            }
          }
          leaf ring-name {
            xr:xr-xml-map "l2vpn_oper:RingName";
            type xr:Cisco-ios-xr-string {
              length "0..32";
            }
            description "Ring Name";
          }
        }
      }
    }
  }

  grouping XCONNECT-MP2MP-TABLE {
    description "Common node of l2vpn, active, standby, node";

    container xconnect-mp2mps {
      xr:xr-xml-map "l2vpn_oper:XConnectMP2MPTable";
      description "XConnect MP2MP Table";

      list xconnect-mp2mp {
        xr:xr-xml-map "l2vpn_oper:XConnectMP2MP";
        description "XConnect MP2MP information";
        leaf group-name {
          xr:xr-xml-map "l2vpn_oper:GroupName";
          type xr:Cisco-ios-xr-string {
            length "0..32";
          }
          description "XConnect Group";
        }
        leaf mp2-mp-name {
          xr:xr-xml-map "l2vpn_oper:Mp2MpName";
          type xr:Cisco-ios-xr-string {
            length "0..26";
          }
          description "Mp2Mp Name";
        }
        uses L2VPN-MP2MP-XC;
      }
    }
  }

  grouping DISCOVERY-SUMMARY {
    description "Common node of l2vpn, active, standby, node";

    container discovery-summary {
      xr:xr-xml-map "l2vpn_oper:DiscoverySummary";
      description "Discovery summary information";
      uses L2VPN-DISCO-SUMMARY;
    }
  }

  grouping XCONNECT-GROUP-TABLE {
    description "Common node of l2vpn, active, standby, node";

    container xconnect-groups {
      xr:xr-xml-map "l2vpn_oper:XConnectGroupTable";
      description "XConnect group Table";

      list xconnect-group {
        xr:xr-xml-map "l2vpn_oper:XConnectGroup";
        key "group-name";
        description "XConnect group information";
        leaf group-name {
          xr:xr-xml-map "l2vpn_oper:GroupName";
          type xr:Cisco-ios-xr-string {
            length "0..32";
          }
          description "XConnect Group";
        }
        uses L2VPN-GROUP;
      }
    }
  }

  grouping MSTP-PORT-TABLE {
    description "Common node of l2vpn, active, standby, node";

    container mstp-ports {
      xr:xr-xml-map "l2vpn_oper:MSTPPortTable";
      description "L2VPN MSTP Port Table";

      list mstp-port {
        xr:xr-xml-map "l2vpn_oper:MSTPPort";
        key "interface";
        description "MSTP Port information";
        leaf interface {
          xr:xr-xml-map "l2vpn_oper:Interface";
          type xr:Interface-name;
          description "Interface";
        }
        uses L2VPN-MSTP-PORT;
      }
    }
  }

  grouping PWR {
    description "Common node of l2vpn, active, standby, node";

    container pwr {
      xr:xr-xml-map "l2vpn_oper:PWR";
      description "Pseudowire Routing Table";

      container summary {
        xr:xr-xml-map "l2vpn_oper:Summary";
        description "L2VPN Pseudowire Routing Summary";
        uses L2VPN-ATOM-PWR-SUMMARY;
      }
    }
  }

  grouping GENERIC-INTERFACE-LIST-TABLE {
    description "Common node of l2vpn, active, standby, node";

    container generic-interfaces {
      xr:xr-xml-map "l2vpn_oper:GenericInterfaceListTable";
      description "L2VPN generic interface list Table";

      list generic-interface {
        xr:xr-xml-map "l2vpn_oper:GenericInterfaceList";
        key "interface-list-name";
        description "Generic Interface List information";
        leaf interface-list-name {
          xr:xr-xml-map "l2vpn_oper:InterfaceListName";
          type xr:Cisco-ios-xr-string {
            length "0..32";
          }
          description "Generic Interface List Name";
        }
        uses L2VPN-GENERIC-IF-LIST;
      }
    }
  }

  grouping MAIN-INTERFACE-TABLE {
    description "Common node of l2vpn, active, standby, node";

    container main-interfaces {
      xr:xr-xml-map "l2vpn_oper:MainInterfaceTable";
      description "Main Interface";

      list main-interface {
        xr:xr-xml-map "l2vpn_oper:MainInterface";
        key "interface-name";
        description "Main Interface Table";

        container main-interface-instances {
          xr:xr-xml-map "l2vpn_oper:MainInterfaceInstanceTable";
          description "Main Interface Instance table";

          list main-interface-instance {
            xr:xr-xml-map "l2vpn_oper:MainInterfaceInstance";
            key "instance";
            description "Main Interface Instance";

            container main-interface-instance {
              xr:xr-xml-map "l2vpn_oper:MainInterfaceInstance";
              description "Main Interface Instance info";
              uses L2VPN-MAIN-INTERFACE-INSTANCE;
            }

            container main-interface-instance-bridge-ports {
              xr:xr-xml-map "l2vpn_oper:MainInterfaceInstanceBridge"+
                "PortTable";
              description
                "Main Interface Instance Bridge Port table";

              list main-interface-instance-bridge-port {
                xr:xr-xml-map "l2vpn_oper:MainInterfaceInstanceBrid"+
                  "gePort";
                key "bridge-port";
                description "Main Interface Instance info";
                leaf bridge-port {
                  xr:xr-xml-map "l2vpn_oper:BridgePort";
                  type xr:Interface-name;
                  description "Bridge Port";
                }
                uses L2VPN-MAIN-INTERFACE-INSTANCE-BPORT;
              }
            }
            leaf instance {
              xr:xr-xml-map "l2vpn_oper:Instance";
              type int32;
              description "Instance";
            }
          }
        }

        container main-interface-info {
          xr:xr-xml-map "l2vpn_oper:MainInterfaceInfo";
          description "Main Interface info";
          uses L2VPN-MAIN-INTERFACE;
        }
        leaf interface-name {
          xr:xr-xml-map "l2vpn_oper:InterfaceName";
          type xr:Cisco-ios-xr-string {
            length "0..64";
          }
          description "Main interface";
        }
      }
    }
  }

  grouping DISCOVERY-TABLE {
    description "Common node of l2vpn, active, standby, node";

    container discoveries {
      xr:xr-xml-map "l2vpn_oper:DiscoveryTable";
      description "Discovery Table";

      list discovery {
        xr:xr-xml-map "l2vpn_oper:Discovery";
        description "VPLS Discovery information";
        leaf service-name {
          xr:xr-xml-map "l2vpn_oper:ServiceName";
          type L2vpn-service;
          description "Service type";
        }
        leaf group-name {
          xr:xr-xml-map "l2vpn_oper:GroupName";
          type xr:Cisco-ios-xr-string {
            length "0..32";
          }
          description "Group Name";
        }
        leaf vpn-name {
          xr:xr-xml-map "l2vpn_oper:VPNName";
          type xr:Cisco-ios-xr-string {
            length "0..27";
          }
          description "VPN Name";
        }
        uses L2VPN-DISCO;
      }
    }
  }

  grouping XCONNECT-BRIEF {
    description "Common node of l2vpn, active, standby, node";

    container xconnect-brief {
      xr:xr-xml-map "l2vpn_oper:XConnectBrief";
      description "XConnect brief information";
      uses L2VPN-XC-BRIEF;
    }
  }

  grouping L2FIB-EVPN-INCL-M-CAST-OLE-TABLE {
    description
      "Common node of l2fib-evpn-incl-m-cast,
      l2fib-evpn-incl-m-cast-hardware-ingress,
      l2fib-evpn-incl-m-cast-hardware-egress";

    container l2fib-evpn-incl-m-cast-oles {
      xr:xr-xml-map "l2vpn_oper:L2FIB_EVPNInclMCastOLETable";
      description "EVPN ingress mcast ole Information";

      list l2fib-evpn-incl-m-cast-ole {
        xr:xr-xml-map "l2vpn_oper:L2FIB_EVPNInclMCastOLE";
        key "next-hop-address";
        description
          "Information on a particular output path of the
          pbb-evpn/evpn ingress replication list";
        leaf next-hop-address {
          xr:xr-xml-map "l2vpn_oper:NextHopAddress";
          type inet:ip-address-no-zone;
          description "Next Hop Address";
        }
        uses L2FIB-EVPN-MCAST-OLE-INFO;
      }
    }
  }

  grouping MVRP-TABLE {
    description "Common node of l2vpn, active, standby, node";

    container mvrps {
      xr:xr-xml-map "l2vpn_oper:MVRPTable";
      description "MVRP Table";

      list mvrp {
        xr:xr-xml-map "l2vpn_oper:MVRP";
        key "main-port-interface-name";
        description "L2VPN MVRP Main Port DB Entry";

        container mvrp-main-port-info {
          xr:xr-xml-map "l2vpn_oper:MVRPMainPortInfo";
          description "L2VPN MVRP Main Port Information";
          uses L2VPN-MVRP;
        }

        container mvrp-bridge-ports {
          xr:xr-xml-map "l2vpn_oper:MVRPBridgePortTable";
          description "MVRP Bridge Port Table";

          list mvrp-bridge-port {
            xr:xr-xml-map "l2vpn_oper:MVRPBridgePort";
            key "interface-name";
            description "L2VPN MVRP Bridge Port Information";
            leaf interface-name {
              xr:xr-xml-map "l2vpn_oper:InterfaceName";
              type xr:Interface-name;
              description "Bridge Port Interface Name";
            }
            uses L2VPN-MVRP-BP;
          }
        }
        leaf main-port-interface-name {
          xr:xr-xml-map "l2vpn_oper:MainPortInterfaceName";
          type xr:Interface-name;
          description "Main Port interface";
        }
      }
    }
  }

  grouping XCONNECT-SUMMARY {
    description "Common node of l2vpn, active, standby, node";

    container xconnect-summary {
      xr:xr-xml-map "l2vpn_oper:XConnectSummary";
      description "XConnect summary information";
      uses L2VPN-XC-SUMMARY;
    }
  }

  grouping L2VPN-COLLABORATORS {
    description "Common node of l2vpn, active, standby, node";

    container l2vpn-collaborators {
      xr:xr-xml-map "l2vpn_oper:L2VPNCollaborators";
      description "L2VPN collaborator information";
      uses L2VPN-GLOBAL-INFO;
    }
  }

  grouping GLOBAL-SETTINGS {
    description "Common node of l2vpn, active, standby, node";

    container global-settings {
      xr:xr-xml-map "l2vpn_oper:GlobalSettings";
      description "L2VPN global settings";
      uses L2VPN-GLOBALS;
    }
  }

  grouping BRIDGE-SUMMARY {
    description "Common node of l2vpn, active, standby, node";

    container bridge-summary {
      xr:xr-xml-map "l2vpn_oper:BridgeSummary";
      description "Bridge Domain summary information";
      uses L2VPN-BRIDGE-SUMMARY;
    }
  }

  grouping XCONNECT-MP2MP-CE2CE-TABLE {
    description "Common node of l2vpn, active, standby, node";

    container xconnect-mp2mp-ce2ces {
      xr:xr-xml-map "l2vpn_oper:XConnectMP2MP_CE2CETable";
      description "XConnect MP2MP CE2CE Table";

      list xconnect-mp2mp-ce2ce {
        xr:xr-xml-map "l2vpn_oper:XConnectMP2MP_CE2CE";
        description "XConnect MP2MP CE2CE information";
        leaf group-name {
          xr:xr-xml-map "l2vpn_oper:GroupName";
          type xr:Cisco-ios-xr-string {
            length "0..32";
          }
          description "XConnect Group";
        }
        leaf mp2-mp-name {
          xr:xr-xml-map "l2vpn_oper:Mp2MpName";
          type xr:Cisco-ios-xr-string {
            length "0..26";
          }
          description "Mp2Mp Name";
        }
        leaf local-ceid {
          xr:xr-xml-map "l2vpn_oper:LocalCEID";
          type uint32 {
            range "1..4294967295";
          }
          description "Local CE ID";
        }
        leaf remote-ceid {
          xr:xr-xml-map "l2vpn_oper:RemoteCEID";
          type uint32 {
            range "1..4294967295";
          }
          description "Remote CE ID";
        }
        uses L2VPN-XC-CE2CE;
      }
    }
  }

  grouping L2VPN-OPER-L2VPN-RESOURCE-STATE-MP {
    description "Common node of l2vpn, active, standby, node";

    container l2vpn-resource-state {
      xr:xr-xml-map "l2vpn_oper:L2VPNResourceState";
      description "L2VPN resource state information";
      uses L2VPN-RESOURCE-STATE;
    }
  }

  grouping MSTP-VLAN-TABLE {
    description "Common node of l2vpn, active, standby, node";

    container mstp-vlans {
      xr:xr-xml-map "l2vpn_oper:MSTPVlanTable";
      description "L2VPN MSTP VLAN Table";

      list mstp-vlan {
        xr:xr-xml-map "l2vpn_oper:MSTPVlan";
        key "vlan-id";
        description "L2VPN MSTP VLAN information";
        leaf vlan-id {
          xr:xr-xml-map "l2vpn_oper:VlanID";
          type uint32 {
            range "0..4098";
          }
          description "vlan id";
        }
        uses L2VPN-MSTP-VLAN;
      }
    }
  }

  grouping GENERIC-INTERFACE-LIST-DETAIL-TABLE {
    description "Common node of l2vpn, active, standby, node";

    container generic-interface-list-details {
      xr:xr-xml-map "l2vpn_oper:GenericInterfaceListDetailTable";
      description "L2VPN generic interface list Detail Table";

      list generic-interface-list-detail {
        xr:xr-xml-map "l2vpn_oper:GenericInterfaceListDetail";
        key "interface-list-name";
        description "Generic Interface List detail information";
        leaf interface-list-name {
          xr:xr-xml-map "l2vpn_oper:InterfaceListName";
          type xr:Cisco-ios-xr-string {
            length "0..32";
          }
          description "Generic Interface List Name";
        }
        uses L2VPN-GENERIC-IF-LIST-DETAIL;
      }
    }
  }

  grouping GENERIC-INTERFACE-LIST-TABLE-V2 {
    description "Common node of active, standby, node";

    container generic-interfaces {
      xr:xr-xml-map "iflist_oper:GenericInterfaceListTableV2";
      description "Generic interface list table";

      list generic-interface {
        xr:xr-xml-map "iflist_oper:GenericInterfaceList";
        key "generic-interface-list-name";
        description "Generic Interface List";
        leaf generic-interface-list-name {
          xr:xr-xml-map "iflist_oper:GenericInterfaceListName";
          type xr:Cisco-ios-xr-string {
            length "0..32";
          }
          description "Generic Interface List Name";
        }
        uses IFLIST-IFL;
      }
    }
  }

  grouping XCONNECT-TABLE {
    description "Common node of l2vpn, active, standby, node";

    container xconnects {
      xr:xr-xml-map "l2vpn_oper:XConnectTable";
      description "XConnect Table";

      list xconnect {
        xr:xr-xml-map "l2vpn_oper:XConnect";
        description "XConnect information";
        leaf group-name {
          xr:xr-xml-map "l2vpn_oper:GroupName";
          type xr:Cisco-ios-xr-string {
            length "0..32";
          }
          description "XConnect Group";
        }
        leaf xconnect-name {
          xr:xr-xml-map "l2vpn_oper:XConnectName";
          type string {
            length "0..38";
          }
          description "XConnect Name";
        }
        uses L2VPN-XC;
      }
    }
  }

  grouping L2VPN-PBB-BSA {
    description "Common node of l2vpn, active, standby, node";

    container l2vpn-pbb-bsa {
      xr:xr-xml-map "l2vpn_oper:L2VPN_PBB_BSA";
      description "L2VPN PBB Backbone Source MAC information";
      uses L2VPN-PBB-BMAC-SA;
    }
  }

  grouping G8032-DETAIL {
    description "Common node of l2vpn, active, standby, node";

    container g8032-detail {
      xr:xr-xml-map "l2vpn_oper:G8032Detail";
      description "G8032 Detail table";

      container g8032-ring-details {
        xr:xr-xml-map "l2vpn_oper:G8032RingDetailTable";
        description "G8032 Ring Detail table";

        list g8032-ring-detail {
          xr:xr-xml-map "l2vpn_oper:G8032RingDetail";
          key "ring-name";
          description "G8032 Ring Detail table";

          container g8032-ring-detail-info {
            xr:xr-xml-map "l2vpn_oper:G8032RingDetailInfo";
            description "G8032 Ring Detail info";
            uses L2VPN-G8032-RING-DETAIL-INFO;
          }

          container g8032-ring-instance-details {
            xr:xr-xml-map "l2vpn_oper:G8032RingInstanceDetailTable";
            description "G8032 Ring Instances Detail table";

            list g8032-ring-instance-detail {
              xr:xr-xml-map "l2vpn_oper:G8032RingInstanceDetail";
              key "instance";
              description "G8032 Ring Detail info";
              leaf instance {
                xr:xr-xml-map "l2vpn_oper:Instance";
                type int32;
                description "Instance";
              }
              uses L2VPN-G8032-RING-INSTANCE-DETAIL-INFO;
            }
          }
          leaf ring-name {
            xr:xr-xml-map "l2vpn_oper:RingName";
            type xr:Cisco-ios-xr-string {
              length "0..32";
            }
            description "Ring Name";
          }
        }
      }
    }
  }

  grouping BRIDGE-DOMAIN-TABLE {
    description "Common node of l2vpn, active, standby, node";

    container bridge-domains {
      xr:xr-xml-map "l2vpn_oper:BridgeDomainTable";
      description "VPLS Bridge Domain Information";

      list bridge-domain {
        xr:xr-xml-map "l2vpn_oper:BridgeDomain";
        description "VPLS Bridge Domain Information";

        container bridge-pws {
          xr:xr-xml-map "l2vpn_oper:BridgePWTable";
          description "VPLS Bridge Domain Pseudowire Table";

          list bridge-pw {
            xr:xr-xml-map "l2vpn_oper:BridgePW";
            description "VPLS Bridge Domain Pseudowire";
            leaf neighbor {
              xr:xr-xml-map "l2vpn_oper:Neighbor";
              type inet:ipv4-address-no-zone;
              description "Neighbor IPv4 address";
            }
            leaf pw-type {
              xr:xr-xml-map "l2vpn_oper:PWType";
              type L2vpnpw;
              description "PW Type";
            }
            leaf pseudowire-id {
              xr:xr-xml-map "l2vpn_oper:PseudowireID";
              type uint32 {
                range "1..4294967295";
              }
              description "Pseudowire ID";
            }
            leaf ve-id-vpls-id-0-3 {
              xr:xr-xml-map "l2vpn_oper:VE_ID_VPLS_ID_0_3";
              type uint32 {
                range "0..4294967295";
              }
              description
                "Zero or concatenation of local and remote
                VE-ID or first 4 bytes of VPLS-ID";
            }
            leaf vpls-id-4-7 {
              xr:xr-xml-map "l2vpn_oper:VPLS_ID_4_7";
              type uint32 {
                range "0..4294967295";
              }
              description "Zero or Last 4 bytes of VPLS-ID";
            }
            uses L2VPN-BD-PW;
          }
        }

        container bridge-acs {
          xr:xr-xml-map "l2vpn_oper:BridgeACTable";
          description "VPLS Bridge Domain Attachment Circuit Table";

          list bridge-ac {
            xr:xr-xml-map "l2vpn_oper:BridgeAC";
            key "interface-name";
            description "VPLS Bridge Domain Attachment Circuit";
            leaf interface-name {
              xr:xr-xml-map "l2vpn_oper:InterfaceName";
              type xr:Interface-name;
              description "Interface Name";
            }
            uses L2VPN-BD-AC;
          }
        }

        container bridge-access-pws {
          xr:xr-xml-map "l2vpn_oper:BridgeAccessPWTable";
          description "VPLS Bridge Domain Access Pseudowire Table";

          list bridge-access-pw {
            xr:xr-xml-map "l2vpn_oper:BridgeAccessPW";
            description "VPLS Bridge Domain Access Pseudowire";
            leaf neighbor {
              xr:xr-xml-map "l2vpn_oper:Neighbor";
              type inet:ipv4-address-no-zone;
              description "Neighbor IPv4 address";
            }
            leaf pseudowire-id {
              xr:xr-xml-map "l2vpn_oper:PseudowireID";
              type uint32 {
                range "1..4294967295";
              }
              description "Pseudowire ID";
            }
            uses L2VPN-BD-PW;
          }
        }

        container bridge-domain-info {
          xr:xr-xml-map "l2vpn_oper:BridgeDomainInfo";
          description "VPLS Bridge Domain Information";
          uses L2VPN-BRIDGE;
        }
        leaf bridge-domain-group-name {
          xr:xr-xml-map "l2vpn_oper:BridgeDomainGroupName";
          type xr:Cisco-ios-xr-string {
            length "0..32";
          }
          description "Bridge Domain Group Name";
        }
        leaf bridge-domain-name {
          xr:xr-xml-map "l2vpn_oper:BridgeDomainName";
          type xr:Cisco-ios-xr-string {
            length "0..27";
          }
          description "Bridge Domain Name";
        }
      }
    }
  }

  grouping MCAST-REPLICATION-LIST {
    description
      "Common node of l2fib-evpn-incl-m-cast,
      l2fib-evpn-incl-m-cast-hardware-ingress,
      l2fib-evpn-incl-m-cast-hardware-egress";

    container mcast-replication-list {
      xr:xr-xml-map "l2vpn_oper:MCastReplicationList";
      description
        "Information of pbb-evpn/evpn ingress mcast
        replication list for a particular bridge domain";
      uses L2FIB-EVPN-MCAST-LEAF-INFO;
    }
  }

  grouping INDEX-TABLE {
    description "Common node of l2vpn, active, standby, node";

    container indexes {
      xr:xr-xml-map "l2vpn_oper:IndexTable";
      description "ID Manager Index Table";

      list index {
        xr:xr-xml-map "l2vpn_oper:Index";
        key "pool-id";
        description "ID Manager Index Pool";
        leaf pool-id {
          xr:xr-xml-map "l2vpn_oper:PoolID";
          type xr:Hex-integer;
          description "Pool ID";
        }
        uses L2VPN-INDEX-INFO;
      }
    }
  }

  grouping NSR {
    description "Common node of l2vpn, active, standby, node";

    container nsr {
      xr:xr-xml-map "l2vpn_oper:NSR";
      description "L2VPN NSR information";
      uses L2VPN-NSR-INFO;
    }
  }

  grouping PSEUDOWIRE-CLASS-TABLE {
    description "Common node of l2vpn, active, standby, node";

    container pseudowire-classes {
      xr:xr-xml-map "l2vpn_oper:PseudowireClassTable";
      description "List of pseudowire classes";

      list pseudowire-class {
        xr:xr-xml-map "l2vpn_oper:PseudowireClass";
        key "pseudowire-class-name";
        description "Pseudowire class information";
        leaf pseudowire-class-name {
          xr:xr-xml-map "l2vpn_oper:PseudowireClassName";
          type xr:Cisco-ios-xr-string {
            length "0..32";
          }
          description "Pseudowire Class Name";
        }
        uses L2VPN-PW-CLASS;
      }
    }
  }

  container l2vpn-forwarding {
    xr:xr-xml-map "l2vpn_oper:L2VPNForwarding";
    config false;
    description "Show L2VPN forwarding";

    container nodes {
      xr:xr-xml-map "l2vpn_oper:NodeTable";
      description "Per node L2VPN forwarding Operational data";

      list node {
        xr:xr-xml-map "l2vpn_oper:Node";
        key "node-id";
        description
          "The L2VPN forwarding Operational data for a
          particular node";

        container l2fibx-con-locals {
          xr:xr-xml-map "l2vpn_oper:L2FIBXConLocalTable";
          description
            "The L2VPN forwarding Local LC XConnect Detail
            Table";

          list l2fibx-con-local {
            xr:xr-xml-map "l2vpn_oper:L2FIBXConLocal";
            key "interface-name";
            description "Specify Sub Ifh";
            leaf interface-name {
              xr:xr-xml-map "l2vpn_oper:InterfaceName";
              type xr:Interface-name;
              description "Interface Name";
            }
            uses L2FIB-XCON-INFO;
          }
        }

        container l2fib-mroute-summaries {
          xr:xr-xml-map "l2vpn_oper:L2FIBMrouteSummaryTable";
          description "Mroute Summary Table";

          list l2fib-mroute-summary {
            xr:xr-xml-map "l2vpn_oper:L2FIBMrouteSummary";
            description "Multicast Summary Information";
            leaf bd-group-name {
              xr:xr-xml-map "l2vpn_oper:BDGroupName";
              type xr:Cisco-ios-xr-string {
                length "0..32";
              }
              description "Bridge Group Name";
            }
            leaf bd-name {
              xr:xr-xml-map "l2vpn_oper:BDName";
              type xr:Cisco-ios-xr-string {
                length "0..65";
              }
              description "Bridge Domain Name";
            }
            uses L2FIB-MCAST-SUMMARY-INFO;
          }
        }

        container l2fib-mroutes {
          xr:xr-xml-map "l2vpn_oper:L2FIBMrouteTable";
          description "multicast information";

          list l2fib-mroute {
            xr:xr-xml-map "l2vpn_oper:L2FIBMroute";
            description "Bridge Domain Multicast Information";
            leaf source {
              xr:xr-xml-map "l2vpn_oper:Source";
              type inet:ipv4-address-no-zone;
              description "Source IP Address";
            }
            leaf group {
              xr:xr-xml-map "l2vpn_oper:Group";
              type inet:ipv4-address-no-zone;
              description "Group IP Address";
            }
            leaf bd-group-name {
              xr:xr-xml-map "l2vpn_oper:BDGroupName";
              type xr:Cisco-ios-xr-string {
                length "0..32";
              }
              description "Bridge Group Name";
            }
            leaf bd-name {
              xr:xr-xml-map "l2vpn_oper:BDName";
              type xr:Cisco-ios-xr-string {
                length "0..65";
              }
              description "Bridge Domain Name";
            }
            uses L2FIB-MCAST-LEAF-INFO;
          }
        }

        container pbb-bmac-sa {
          xr:xr-xml-map "l2vpn_oper:PBB_BMAC_SA";
          description "PBB Backbone Source MAC information";
          uses L2FIB-PBB-BMAC-SA-INFO;
        }

        container l2fib-p2mp {
          xr:xr-xml-map "l2vpn_oper:L2FIB_P2MP";
          description "p2mp information";

          container ptrees {
            xr:xr-xml-map "l2vpn_oper:PTreeTable";
            description "ptree information";

            list ptree {
              xr:xr-xml-map "l2vpn_oper:PTree";
              description "P2MP PTree Information";
              leaf ptree-type {
                xr:xr-xml-map "l2vpn_oper:PTreeType";
                type L2vpnp2mp-ptree;
                description "PTree Type";
              }
              leaf lsm-id {
                xr:xr-xml-map "l2vpn_oper:LSM_ID";
                type int32;
                description "LSM Id";
              }
              leaf tunnel-id {
                xr:xr-xml-map "l2vpn_oper:TunnelID";
                type int32;
                description "Tunnel Id";
              }
              leaf p2mp-id {
                xr:xr-xml-map "l2vpn_oper:P2MP_ID";
                type int32;
                description "P2MP Id";
              }
              leaf extended-tunnel-id {
                xr:xr-xml-map "l2vpn_oper:ExtendedTunnelID";
                type int32;
                description "Extended Tunnel Id";
              }
              uses L2FIB-P2MP-PTREE-INFO;
            }
          }
        }

        container l2fib-evpn-incl-m-cast-hardware-egresses {
          xr:xr-xml-map "l2vpn_oper:L2FIB_EVPNInclMCastHardwareEgre"+
            "ssTable";
          description
            "L2VPN forwarding bridge-domain evpn inclusive
            multicast hardware egress Table";

          list l2fib-evpn-incl-m-cast-hardware-egress {
            xr:xr-xml-map "l2vpn_oper:L2FIB_EVPNInclMCastHardwareEg"+
              "ress";
            key "bd-name";
            description "Specify bridge domain name";
            leaf bd-name {
              xr:xr-xml-map "l2vpn_oper:BDName";
              type xr:Cisco-ios-xr-string {
                length "0..65";
              }
              description "Bridge Domain Name";
            }
            uses MCAST-REPLICATION-LIST;
            uses L2FIB-EVPN-INCL-M-CAST-OLE-TABLE;
          }
        }

        container l2fibmac-hardware-ingresses {
          xr:xr-xml-map "l2vpn_oper:L2FIBMACHardwareIngressTable";
          description "Bridge Hardware Ingress information";

          list l2fibmac-hardware-ingress {
            xr:xr-xml-map "l2vpn_oper:L2FIBMACHardwareIngress";
            description "MAC Hardware Ingress information";
            leaf address {
              xr:xr-xml-map "l2vpn_oper:Address";
              type yang:mac-address;
              description "Static MAC address";
            }
            leaf group-name {
              xr:xr-xml-map "l2vpn_oper:GroupName";
              type xr:Cisco-ios-xr-string {
                length "0..32";
              }
              description "Bridge Group Name";
            }
            leaf name {
              xr:xr-xml-map "l2vpn_oper:Name";
              type xr:Cisco-ios-xr-string {
                length "0..27";
              }
              description "Bridge Domain Name";
            }
            uses L2FIB-BRIDGE-MAC-INFO;
          }
        }

        container l2fib-pwhe-main-ports {
          xr:xr-xml-map "l2vpn_oper:L2FIB_PWHEMainPortTable";
          description "PWHE Main-port table";

          list l2fib-pwhe-main-port {
            xr:xr-xml-map "l2vpn_oper:L2FIB_PWHEMainPort";
            key "interface-name";
            description "PWHE Main-port";
            leaf interface-name {
              xr:xr-xml-map "l2vpn_oper:InterfaceName";
              type xr:Interface-name;
              description "PWHE Main-port";
            }
            uses L2FIB-PWHE-MP-SHOW-INFO;
          }
        }

        container l2fib-dhcp-binding-count {
          xr:xr-xml-map "l2vpn_oper:L2FIB_DHCPBindingCount";
          description "DHCP binding forwarding total count";
          uses L2FIB-DHCP-BINDING-COUNT-INFO;
        }

        container l2fib-bridge-domains {
          xr:xr-xml-map "l2vpn_oper:L2FIBBridgeDomainDetailTable";
          description "Bridge Domain forwarding detail";

          list l2fib-bridge-domain {
            xr:xr-xml-map "l2vpn_oper:L2FIBBridgeDomain";
            description "Specify Bridge Domain Name";
            leaf bd-group-name {
              xr:xr-xml-map "l2vpn_oper:BDGroupName";
              type xr:Cisco-ios-xr-string {
                length "0..32";
              }
              description "Name of the Bridge group";
            }
            leaf bd-name {
              xr:xr-xml-map "l2vpn_oper:BdName";
              type xr:Cisco-ios-xr-string {
                length "0..65";
              }
              description "Bridge Domain Name";
            }
            uses L2FIB-BRIDGE-INFO;
          }
        }

        container l2fib-mstp-summaries {
          xr:xr-xml-map "l2vpn_oper:L2FIB_MSTP_SummaryTable";
          description "MSTP Summary Table";

          list l2fib-mstp-summary {
            xr:xr-xml-map "l2vpn_oper:L2FIB_MSTP_Summary";
            description "MSTP Summary information";
            leaf parent-interface {
              xr:xr-xml-map "l2vpn_oper:ParentInterface";
              type xr:Interface-name;
              description "Parent interface context";
            }
            leaf msti {
              xr:xr-xml-map "l2vpn_oper:MSTI";
              type int32;
              description "MSTI context";
            }
            uses L2FIB-MAIN-PORT-MSTP-SUMMARY-INFO;
          }
        }

        container l2fibmac-hardware-egresses {
          xr:xr-xml-map "l2vpn_oper:L2FIBMACHardwareEgressTable";
          description "Bridge Hardware Egress information";

          list l2fibmac-hardware-egress {
            xr:xr-xml-map "l2vpn_oper:L2FIBMACHardwareEgress";
            description "MAC Hardware Egress information";
            leaf address {
              xr:xr-xml-map "l2vpn_oper:Address";
              type yang:mac-address;
              description "Static MAC address";
            }
            leaf group-name {
              xr:xr-xml-map "l2vpn_oper:GroupName";
              type xr:Cisco-ios-xr-string {
                length "0..32";
              }
              description "Bridge Group Name";
            }
            leaf name {
              xr:xr-xml-map "l2vpn_oper:Name";
              type xr:Cisco-ios-xr-string {
                length "0..27";
              }
              description "Bridge Domain Name";
            }
            uses L2FIB-BRIDGE-MAC-INFO;
          }
        }

        container l2fib-g8032-detail {
          xr:xr-xml-map "l2vpn_oper:L2FIB_G8032Detail";
          description "G8032 Detail table";

          container l2fib-g8032-ring-detail-tables {
            xr:xr-xml-map "l2vpn_oper:L2FIB_G8032RingDetail";
            description "G8032 Ring Detail table";

            list l2fib-g8032-ring-detail-table {
              xr:xr-xml-map "l2vpn_oper:L2FIB_G8032RingDetailTable";
              key "ring-name";
              description "G8032 Ring Detail table";

              container l2fib-g8032-ring-detail-info {
                xr:xr-xml-map "l2vpn_oper:L2FIB_G8032RingDetailInfo";
                description "G8032 Ring Detail info";
                uses L2FIB-G8032-RING-DETAIL-INFO;
              }

              container l2fib-g8032-ring-instance-details {
                xr:xr-xml-map "l2vpn_oper:L2FIB_G8032RingInstanceDe"+
                  "tailTable";
                description "G8032 Ring Instances Detail table";

                list l2fib-g8032-ring-instance-detail {
                  xr:xr-xml-map "l2vpn_oper:L2FIB_G8032RingInstance"+
                    "Detail";
                  key "instance";
                  description "G8032 Ring Detail info";
                  leaf instance {
                    xr:xr-xml-map "l2vpn_oper:Instance";
                    type int32;
                    description "Instance";
                  }
                  uses L2FIB-G8032-RING-INSTANCE-DETAIL-INFO;
                }
              }
              leaf ring-name {
                xr:xr-xml-map "l2vpn_oper:RingName";
                type xr:Cisco-ios-xr-string {
                  length "0..32";
                }
                description "Ring Name";
              }
            }
          }
        }

        container l2fib-main-interface-detail-tables {
          xr:xr-xml-map "l2vpn_oper:L2FIBMainInterfaceDetail";
          description "Main Interface detail table";

          list l2fib-main-interface-detail-table {
            xr:xr-xml-map "l2vpn_oper:L2FIBMainInterfaceDetailTable";
            key "main-interface";
            description "Main Interface detail DB entry";

            container l2fib-main-interface-instance-detail-tables {
              xr:xr-xml-map "l2vpn_oper:L2FIBMainInterfaceInstanceD"+
                "etail";
              description "Main Interface Instance Detail table";

              list l2fib-main-interface-instance-detail-table {
                xr:xr-xml-map "l2vpn_oper:L2FIBMainInterfaceInstanc"+
                  "eDetailTable";
                key "instance";
                description
                  "Main Interface Instance Detail DB entry";

                container "l2fib-main-interface-instance-detail"+
                  "-info" {
                  xr:xr-xml-map "l2vpn_oper:L2FIBMainInterfaceInsta"+
                    "nceDetailInfo";
                  description
                    "Main Interface Instance Detail DB entry
                    info";
                  uses L2FIB-MAIN-INTERFACE-INSTANCE-DETAIL-INFO;
                }

                container "l2fib-main-interface-instance-bridge"+
                  "-port-details" {
                  xr:xr-xml-map "l2vpn_oper:L2FIBMainInterfaceInsta"+
                    "nceBridgePortDetailTable";
                  description
                    "Main Interface Instance Detail Bridge Port
                    detail table";

                  list "l2fib-main-interface-instance-bridge-port"+
                    "-detail" {
                    xr:xr-xml-map "l2vpn_oper:L2FIBMainInterfaceIns"+
                      "tanceBridgePortDetail";
                    key "bridge-port";
                    description
                      "Main Interface Instance Detail Bridge
                      Port DB entry";
                    leaf bridge-port {
                      xr:xr-xml-map "l2vpn_oper:BridgePort";
                      type xr:Interface-name;
                      description "Bridge Port";
                    }
                    uses "L2FIB-MAIN-INTERFACE"+
                      "-INSTANCE-BPORT-DETAIL-INFO";
                  }
                }
                leaf instance {
                  xr:xr-xml-map "l2vpn_oper:Instance";
                  type int32;
                  description "Instance";
                }
              }
            }

            container l2fib-main-interface-detail-info {
              xr:xr-xml-map "l2vpn_oper:L2FIBMainInterfaceDetailInf"+
                "o";
              description "Main Interface detail DB entry info";
              uses L2FIB-MAIN-INTERFACE-DETAIL-INFO;
            }
            leaf main-interface {
              xr:xr-xml-map "l2vpn_oper:MainInterface";
              type xr:Interface-name;
              description "Main interface";
            }
          }
        }

        container l2fibx-con-l2tpv2s {
          xr:xr-xml-map "l2vpn_oper:L2FIBXConL2TPV2Table";
          description
            "The L2VPN forwarding XConnect L2TPv2 Detail
            Table";

          list l2fibx-con-l2tpv2 {
            xr:xr-xml-map "l2vpn_oper:L2FIBXConL2TPV2";
            key "interface-name";
            description "Specify Sub Ifh";
            leaf interface-name {
              xr:xr-xml-map "l2vpn_oper:InterfaceName";
              type xr:Interface-name;
              description "Interface Name";
            }
            uses L2FIB-XCON-INFO;
          }
        }

        container l2fib-mroute-ipv6s {
          xr:xr-xml-map "l2vpn_oper:L2FIBMrouteIPv6Table";
          description "multicast information";

          list l2fib-mroute-ipv6 {
            xr:xr-xml-map "l2vpn_oper:L2FIBMrouteIPv6";
            description "Bridge Domain Multicast Information";
            leaf source {
              xr:xr-xml-map "l2vpn_oper:Source";
              type xr:Cisco-ios-xr-string {
                length "0..128";
              }
              description "Source IPv6 Address";
            }
            leaf group {
              xr:xr-xml-map "l2vpn_oper:Group";
              type xr:Cisco-ios-xr-string {
                length "0..128";
              }
              description "Group IPv6 Address";
            }
            leaf bd-group-name {
              xr:xr-xml-map "l2vpn_oper:BDGroupName";
              type xr:Cisco-ios-xr-string {
                length "0..32";
              }
              description "Bridge Group Name";
            }
            leaf bd-name {
              xr:xr-xml-map "l2vpn_oper:BDName";
              type xr:Cisco-ios-xr-string {
                length "0..65";
              }
              description "Bridge Domain Name";
            }
            uses L2FIB-MCAST-LEAF-INFO;
          }
        }

        container l2fib-mon-sess-x-cons {
          xr:xr-xml-map "l2vpn_oper:L2FIBMonSessXConTable";
          description
            "The L2VPN forwarding Monitor Session XConnect
            Information";

          list l2fib-mon-sess-x-con {
            xr:xr-xml-map "l2vpn_oper:L2FIBMonSessXCon";
            key "monitor-session-name";
            description "Specify Monitor Session Name";
            leaf monitor-session-name {
              xr:xr-xml-map "l2vpn_oper:MonitorSessionName";
              type xr:Cisco-ios-xr-string {
                length "0..64";
              }
              description "Monitor Session Name";
            }
            uses L2FIB-XCON-INFO;
          }
        }

        container l2fib-mmrp-summaries {
          xr:xr-xml-map "l2vpn_oper:L2FIBMmrpSummaryTable";
          description "Mmrp Summary Table";

          list l2fib-mmrp-summary {
            xr:xr-xml-map "l2vpn_oper:L2FIBMmrpSummary";
            description "Mmrp Summary Information";
            leaf bd-group-name {
              xr:xr-xml-map "l2vpn_oper:BDGroupName";
              type xr:Cisco-ios-xr-string {
                length "0..32";
              }
              description "Bridge Group Name";
            }
            leaf bd-name {
              xr:xr-xml-map "l2vpn_oper:BDName";
              type xr:Cisco-ios-xr-string {
                length "0..65";
              }
              description "Bridge Domain Name";
            }
            uses L2FIB-MCAST-SUMMARY-INFO;
          }
        }

        container l2fib-pw-groups {
          xr:xr-xml-map "l2vpn_oper:L2FIB_PWGroupTable";
          description "PW Group Table Information";

          list l2fib-pw-group {
            xr:xr-xml-map "l2vpn_oper:L2FIB_PWGroup";
            description "PW Group Information";
            leaf peer-address {
              xr:xr-xml-map "l2vpn_oper:PeerAddress";
              type inet:ipv4-address-no-zone;
              description "Peer IP Address";
            }
            leaf group-id {
              xr:xr-xml-map "l2vpn_oper:GroupID";
              type int32;
              description "Group Id";
            }
            leaf tunnel-if-handle {
              xr:xr-xml-map "l2vpn_oper:TunnelIFHandle";
              type int32;
              description "Tunnel Interface Handle";
            }
            uses L2FIB-PWGROUP-INFO;
          }
        }

        container l2fib-evpn-incl-m-cast-hardware-ingresses {
          xr:xr-xml-map "l2vpn_oper:L2FIB_EVPNInclMCastHardwareIngr"+
            "essTable";
          description
            "L2VPN forwarding bridge-domain evpn inclusive
            multicast hardware ingress Table";

          list l2fib-evpn-incl-m-cast-hardware-ingress {
            xr:xr-xml-map "l2vpn_oper:L2FIB_EVPNInclMCastHardwareIn"+
              "gress";
            key "bd-name";
            description "Specify bridge domain name";
            leaf bd-name {
              xr:xr-xml-map "l2vpn_oper:BDName";
              type xr:Cisco-ios-xr-string {
                length "0..65";
              }
              description "Bridge Domain Name";
            }
            uses MCAST-REPLICATION-LIST;
            uses L2FIB-EVPN-INCL-M-CAST-OLE-TABLE;
          }
        }

        container l2fib-dhcp-binding-details {
          xr:xr-xml-map "l2vpn_oper:L2FIB_DHCPBindingDetailTable";
          description "DHCP binding forwarding detail";

          list l2fib-dhcp-binding-detail {
            xr:xr-xml-map "l2vpn_oper:L2FIB_DHCPBindingDetail";
            description "Specify DHCP binding detail";
            leaf xcid {
              xr:xr-xml-map "l2vpn_oper:XCID";
              type xr:Hex-integer;
              description "XConnect ID";
            }
            leaf neighbor-address {
              xr:xr-xml-map "l2vpn_oper:NeighborAddress";
              type inet:ipv4-address-no-zone;
              description "Neighbor IPv4 address";
            }
            leaf address {
              xr:xr-xml-map "l2vpn_oper:Address";
              type yang:mac-address;
              description "MAC address";
            }
            uses L2FIB-DHCP-BINDING-DETAIL-INFO;
          }
        }

        container l2fibx-cons {
          xr:xr-xml-map "l2vpn_oper:L2FIBXConTable";
          description "The L2VPN forwarding XConnect Detail Table";

          list l2fibx-con {
            xr:xr-xml-map "l2vpn_oper:L2FIBXCon";
            key "xcid";
            description "Specify XConnect ID";
            leaf xcid {
              xr:xr-xml-map "l2vpn_oper:XCID";
              type xr:Hex-integer;
              description "XC ID";
            }
            uses L2FIB-XCON-INFO;
          }
        }

        container l2fib-mstp-details {
          xr:xr-xml-map "l2vpn_oper:L2FIB_MSTP_DetailTable";
          description "MSTP Detail Table";

          list l2fib-mstp-detail {
            xr:xr-xml-map "l2vpn_oper:L2FIB_MSTP_Detail";
            description "MSTP Detail information";
            leaf parent-interface {
              xr:xr-xml-map "l2vpn_oper:ParentInterface";
              type xr:Interface-name;
              description "Parent interface context";
            }
            leaf msti {
              xr:xr-xml-map "l2vpn_oper:MSTI";
              type int32;
              description "MSTI context";
            }
            uses L2FIB-MAIN-PORT-MSTP-DETAIL-INFO;
          }
        }

        container l2fib-l2tp {
          xr:xr-xml-map "l2vpn_oper:L2FIB_L2TP";
          description "L2TP";

          container l2tpv3-sessions {
            xr:xr-xml-map "l2vpn_oper:L2TPV3SessionTable";
            description "L2TPV3 Session table";

            list l2tpv3-session {
              xr:xr-xml-map "l2vpn_oper:L2TPV3Session";
              key "session-id";
              description "L2TPV3 Session";
              leaf session-id {
                xr:xr-xml-map "l2vpn_oper:SessionID";
                type int32;
                description "SessionID";
              }
              uses L2FIB-L2TP-DISP-INFO;
            }
          }

          container l2tpv2-sessions {
            xr:xr-xml-map "l2vpn_oper:L2TPV2SessionTable";
            description "L2TPV2 Session table";

            list l2tpv2-session {
              xr:xr-xml-map "l2vpn_oper:L2TPV2Session";
              description "L2TPV2 Session";
              leaf session-id {
                xr:xr-xml-map "l2vpn_oper:SessionID";
                type int32;
                description "SessionID";
              }
              leaf tunnel-id {
                xr:xr-xml-map "l2vpn_oper:TunnelID";
                type int32;
                description "TunnelID";
              }
              uses L2FIB-L2TP-DISP-INFO;
            }
          }
        }

        container l2fib-bridge-ports {
          xr:xr-xml-map "l2vpn_oper:L2FIBBridgeDomainPortTable";
          description "Bridge Port forwarding detail";

          list l2fib-bridge-port {
            xr:xr-xml-map "l2vpn_oper:L2FIBBridgePort";
            description "Specify Bridge Domain Name and XC ID";
            leaf group-name {
              xr:xr-xml-map "l2vpn_oper:GroupName";
              type xr:Cisco-ios-xr-string {
                length "0..32";
              }
              description "Bridge Group Name";
            }
            leaf bd-name {
              xr:xr-xml-map "l2vpn_oper:BDName";
              type xr:Cisco-ios-xr-string {
                length "0..65";
              }
              description "Bridge Domain Name";
            }
            leaf xc-uint-id {
              xr:xr-xml-map "l2vpn_oper:XCUintID";
              type xr:Hex-integer;
              description "XC ID";
            }
            uses L2FIB-BRIDGE-PORT-DETAIL-INFO;
          }
        }

        container l2fibmac-details {
          xr:xr-xml-map "l2vpn_oper:L2FIBMACDetailTable";
          description "Bridge MAC detail information";

          list l2fibmac-detail {
            xr:xr-xml-map "l2vpn_oper:L2FIBMACDetail";
            description "MAC Detail information";
            leaf address {
              xr:xr-xml-map "l2vpn_oper:Address";
              type yang:mac-address;
              description "Static MAC address";
            }
            leaf group-name {
              xr:xr-xml-map "l2vpn_oper:GroupName";
              type xr:Cisco-ios-xr-string {
                length "0..32";
              }
              description "Bridge Group Name";
            }
            leaf name {
              xr:xr-xml-map "l2vpn_oper:Name";
              type xr:Cisco-ios-xr-string {
                length "0..65";
              }
              description "Bridge Domain Name";
            }
            uses L2FIB-BRIDGE-MAC-INFO;
          }
        }

        container l2fib-bridge-domain-names {
          xr:xr-xml-map "l2vpn_oper:L2FIBBridgeDomainNameTable";
          description "Bridge Domain forwarding detail";

          list l2fib-bridge-domain-name {
            xr:xr-xml-map "l2vpn_oper:L2FIBBridgeDomainName";
            description "Specify Bridge Domain Name";
            leaf bd-group-name {
              xr:xr-xml-map "l2vpn_oper:BDGroupName";
              type xr:Cisco-ios-xr-string {
                length "0..32";
              }
              description "Name of the Bridge group";
            }
            leaf name {
              xr:xr-xml-map "l2vpn_oper:Name";
              type xr:Cisco-ios-xr-string {
                length "0..65";
              }
              description "Bridge Domain Name";
            }
            uses L2FIB-BRIDGE-SUMMARY-INFO;
          }
        }

        container l2fib-mroute-ports {
          xr:xr-xml-map "l2vpn_oper:L2FIBMroutePortTable";
          description "multicast bridge port information ";

          list l2fib-mroute-port {
            xr:xr-xml-map "l2vpn_oper:L2FIBMroutePort";
            description "Multicast Port Information";
            leaf bd-name {
              xr:xr-xml-map "l2vpn_oper:BDName";
              type xr:Cisco-ios-xr-string {
                length "0..65";
              }
              description "Bridge Domain Name";
            }
            leaf xcid {
              xr:xr-xml-map "l2vpn_oper:XCID";
              type xr:Hex-integer;
              description "XConnect ID";
            }
            leaf source {
              xr:xr-xml-map "l2vpn_oper:Source";
              type inet:ipv4-address-no-zone;
              description "Source IP Address";
            }
            leaf group {
              xr:xr-xml-map "l2vpn_oper:Group";
              type inet:ipv4-address-no-zone;
              description "Group IP Address";
            }
            uses L2FIB-MCAST-XID-INFO;
          }
        }

        container l2fib-main-interface-summary-tables {
          xr:xr-xml-map "l2vpn_oper:L2FIBMainInterfaceSummary";
          description "Main Interface summary table";

          list l2fib-main-interface-summary-table {
            xr:xr-xml-map "l2vpn_oper:L2FIBMainInterfaceSummaryTabl"+
              "e";
            key "main-interface";
            description "Main Interface DB entry";

            container l2fib-main-interface-instance-summary-tables {
              xr:xr-xml-map "l2vpn_oper:L2FIBMainInterfaceInstanceS"+
                "ummary";
              description "Main Interface Instances summary table";

              list l2fib-main-interface-instance-summary-table {
                xr:xr-xml-map "l2vpn_oper:L2FIBMainInterfaceInstanc"+
                  "eSummaryTable";
                key "instance";
                description "Main Interface Instance DB entry";

                container "l2fib-main-interface-instance-bridge"+
                  "-port-summaries" {
                  xr:xr-xml-map "l2vpn_oper:L2FIBMainInterfaceInsta"+
                    "nceBridgePortSummaryTable";
                  description
                    "Main Interface Instances Bridge Port
                    summary table";

                  list "l2fib-main-interface-instance-bridge-port"+
                    "-summary" {
                    xr:xr-xml-map "l2vpn_oper:L2FIBMainInterfaceIns"+
                      "tanceBridgePortSummary";
                    key "bridge-port";
                    description
                      "Main Interface Instances Bridge Port DB
                      entry";
                    leaf bridge-port {
                      xr:xr-xml-map "l2vpn_oper:BridgePort";
                      type xr:Interface-name;
                      description "Bridge Port";
                    }
                    uses "L2FIB-MAIN-INTERFACE"+
                      "-INSTANCE-BPORT-SUMMARY-INFO";
                  }
                }

                container "l2fib-main-interface-instance-summary"+
                  "-info" {
                  xr:xr-xml-map "l2vpn_oper:L2FIBMainInterfaceInsta"+
                    "nceSummaryInfo";
                  description
                    "Main Interface Instances summary info";
                  uses L2FIB-MAIN-INTERFACE-INSTANCE-SUMMARY-INFO;
                }
                leaf instance {
                  xr:xr-xml-map "l2vpn_oper:Instance";
                  type int32;
                  description "Instance";
                }
                uses L2FIB-MAIN-INTERFACE-INSTANCE-SUMMARY-INFO;
              }
            }

            container l2fib-main-interface-summary-info {
              xr:xr-xml-map "l2vpn_oper:L2FIBMainInterfaceSummaryIn"+
                "fo";
              description "Main Interface info";
              uses L2FIB-MAIN-INTERFACE-SUMMARY-INFO;
            }
            leaf main-interface {
              xr:xr-xml-map "l2vpn_oper:MainInterface";
              type xr:Interface-name;
              description "Main interface";
            }
          }
        }

        container l2fib-g8032-summary {
          xr:xr-xml-map "l2vpn_oper:L2FIB_G8032Summary";
          description "G8032 summary table";

          container l2fib-g8032-ring-summary-tables {
            xr:xr-xml-map "l2vpn_oper:L2FIB_G8032RingSummary";
            description "G8032 Ring summary table";

            list l2fib-g8032-ring-summary-table {
              xr:xr-xml-map "l2vpn_oper:L2FIB_G8032RingSummaryTable";
              key "ring-name";
              description "G8032 Ring summary table";

              container l2fib-g8032-ring-instance-summaries {
                xr:xr-xml-map "l2vpn_oper:L2FIB_G8032RingInstanceSu"+
                  "mmaryTable";
                description "G8032 Ring Instances summary table";

                list l2fib-g8032-ring-instance-summary {
                  xr:xr-xml-map "l2vpn_oper:L2FIB_G8032RingInstance"+
                    "Summary";
                  key "instance";
                  description "G8032 Ring summary info";
                  leaf instance {
                    xr:xr-xml-map "l2vpn_oper:Instance";
                    type int32;
                    description "Instance";
                  }
                  uses L2FIB-G8032-RING-INSTANCE-SUMMARY-INFO;
                }
              }

              container l2fib-g8032-ring-summary-info {
                xr:xr-xml-map "l2vpn_oper:L2FIB_G8032RingSummaryInf"+
                  "o";
                description "G8032 Ring summary info";
                uses L2FIB-G8032-RING-SUMMARY-INFO;
              }
              leaf ring-name {
                xr:xr-xml-map "l2vpn_oper:RingName";
                type xr:Cisco-ios-xr-string {
                  length "0..32";
                }
                description "Ring Name";
              }
            }
          }
        }

        container l2fib-summary {
          xr:xr-xml-map "l2vpn_oper:L2FIBSummary";
          description "L2FIB Summary information";
          uses L2FIB-SUMMARY-INFO;
        }

        container l2fib-nve-peers {
          xr:xr-xml-map "l2vpn_oper:L2FIB_NVEPeerTable";
          description "NVE Peer Table";

          list l2fib-nve-peer {
            xr:xr-xml-map "l2vpn_oper:L2FIB_NVEPeer";
            description "The attributes for a particular NVE Peer";
            leaf xc-uint-id {
              xr:xr-xml-map "l2vpn_oper:XCUintID";
              type xr:Hex-integer;
              description "XC ID";
            }
            leaf vniid {
              xr:xr-xml-map "l2vpn_oper:VNIID";
              type xr:Hex-integer;
              description "VNI ID";
            }
            leaf vtep-address {
              xr:xr-xml-map "l2vpn_oper:VtepAddress";
              type inet:ipv4-address-no-zone;
              description "VTEP IP Address";
            }
            uses L2FIB-VTEP-INFO;
          }
        }

        container l2fib-mmrps {
          xr:xr-xml-map "l2vpn_oper:L2FIBMmrpTable";
          description "mmmrp information";

          list l2fib-mmrp {
            xr:xr-xml-map "l2vpn_oper:L2FIBMmrp";
            description "Bridge Domain Mmrp Information";
            leaf source {
              xr:xr-xml-map "l2vpn_oper:Source";
              type string {
                length "0..15";
              }
              description "src Mac Address";
            }
            leaf group {
              xr:xr-xml-map "l2vpn_oper:Group";
              type string {
                length "0..15";
              }
              description "Group Mac Address";
            }
            leaf bd-group-name {
              xr:xr-xml-map "l2vpn_oper:BDGroupName";
              type xr:Cisco-ios-xr-string {
                length "0..32";
              }
              description "Bridge Group Name";
            }
            leaf bd-name {
              xr:xr-xml-map "l2vpn_oper:BDName";
              type xr:Cisco-ios-xr-string {
                length "0..65";
              }
              description "Bridge Domain Name";
            }
            uses L2FIB-MCAST-LEAF-INFO;
          }
        }

        container l2fib-dhcp-binding-summaries {
          xr:xr-xml-map "l2vpn_oper:L2FIB_DHCPBindingSummaryTable";
          description "DHCP binding forwarding summary";

          list l2fib-dhcp-binding-summary {
            xr:xr-xml-map "l2vpn_oper:L2FIB_DHCPBindingSummary";
            key "xcid";
            description "Specify DHCP binding summary";
            leaf xcid {
              xr:xr-xml-map "l2vpn_oper:XCID";
              type xr:Hex-integer;
              description "XConnect ID";
            }
            uses L2FIB-DHCP-BINDING-SUMMARY-INFO;
          }
        }

        container l2fib-evpn-incl-m-casts {
          xr:xr-xml-map "l2vpn_oper:L2FIB_EVPNInclMCastTable";
          description
            "L2VPN forwarding bridge-domain evpn inclusive
            multicast Table";

          list l2fib-evpn-incl-m-cast {
            xr:xr-xml-map "l2vpn_oper:L2FIB_EVPNInclMCast";
            key "bd-name";
            description "Specify bridge domain name";
            leaf bd-name {
              xr:xr-xml-map "l2vpn_oper:BDName";
              type xr:Cisco-ios-xr-string {
                length "0..65";
              }
              description "Bridge Domain Name";
            }
            uses MCAST-REPLICATION-LIST;
            uses L2FIB-EVPN-INCL-M-CAST-OLE-TABLE;
          }
        }
        leaf node-id {
          xr:xr-xml-map "l2vpn_oper:NodeID";
          type xr:Node-id;
          description "The identifier for the node";
        }
      }
    }
  }

  container l2vpnv2 {
    xr:xr-xml-map "l2vpn_v2_oper:L2VPNv2";
    config false;
    description "l2vpnv2";

    container standby {
      xr:xr-xml-map "l2vpn_v2_oper:Standby";
      description "Standby L2VPN operational data";
      uses DISCOVERY-TABLE;
      uses MAIN-INTERFACE-TABLE;
      uses G8032-SUMMARY;
      uses BRIDGE-SUMMARY;
      uses NSR;
      uses GLOBAL-SETTINGS;
      uses PWR;
      uses XCONNECT-MP2MP-CE2CE-TABLE;
      uses XCONNECT-TABLE;
      uses XCONNECT-GROUP-TABLE;
      uses XCONNECT-MP2MP-TABLE;
      uses G8032-DETAIL;
      uses INDEX-TABLE;
      uses XCONNECT-SUMMARY;
      uses MVRP-TABLE;
      uses MSTP-PORT-TABLE;
      uses GENERIC-INTERFACE-LIST-DETAIL-TABLE;
      uses L2VPN-OPER-L2VPN-RESOURCE-STATE-MP;
      uses BRIDGE-DOMAIN-TABLE;
      uses DISCOVERY-SUMMARY;
      uses PSEUDOWIRE-CLASS-TABLE;
      uses L2VPN-COLLABORATORS;
      uses GENERIC-INTERFACE-LIST-TABLE;
      uses MSTP-VLAN-TABLE;
      uses L2VPN-PBB-BSA;
      uses XCONNECT-BRIEF;
    }

    container active {
      xr:xr-xml-map "l2vpn_v2_oper:Active";
      description "Active L2VPN operational data";
      uses DISCOVERY-TABLE;
      uses MAIN-INTERFACE-TABLE;
      uses G8032-SUMMARY;
      uses BRIDGE-SUMMARY;
      uses NSR;
      uses GLOBAL-SETTINGS;
      uses PWR;
      uses XCONNECT-MP2MP-CE2CE-TABLE;
      uses XCONNECT-TABLE;
      uses XCONNECT-GROUP-TABLE;
      uses XCONNECT-MP2MP-TABLE;
      uses G8032-DETAIL;
      uses INDEX-TABLE;
      uses XCONNECT-SUMMARY;
      uses MVRP-TABLE;
      uses MSTP-PORT-TABLE;
      uses GENERIC-INTERFACE-LIST-DETAIL-TABLE;
      uses L2VPN-OPER-L2VPN-RESOURCE-STATE-MP;
      uses BRIDGE-DOMAIN-TABLE;
      uses DISCOVERY-SUMMARY;
      uses PSEUDOWIRE-CLASS-TABLE;
      uses L2VPN-COLLABORATORS;
      uses GENERIC-INTERFACE-LIST-TABLE;
      uses MSTP-VLAN-TABLE;
      uses L2VPN-PBB-BSA;
      uses XCONNECT-BRIEF;
    }

    container nodes {
      xr:xr-xml-map "l2vpn_v2_oper:NodeTable";
      description
        "Table of L2VPN operational data for a particular
        node";

      list node {
        xr:xr-xml-map "l2vpn_v2_oper:Node";
        key "node-id";
        description "L2VPN operational data for a particular node";
        leaf node-id {
          xr:xr-xml-map "l2vpn_v2_oper:NodeID";
          type xr:Node-id;
          description "Location";
        }
        uses DISCOVERY-TABLE;
        uses MAIN-INTERFACE-TABLE;
        uses G8032-SUMMARY;
        uses BRIDGE-SUMMARY;
        uses NSR;
        uses GLOBAL-SETTINGS;
        uses PWR;
        uses XCONNECT-MP2MP-CE2CE-TABLE;
        uses XCONNECT-TABLE;
        uses XCONNECT-GROUP-TABLE;
        uses XCONNECT-MP2MP-TABLE;
        uses G8032-DETAIL;
        uses INDEX-TABLE;
        uses XCONNECT-SUMMARY;
        uses MVRP-TABLE;
        uses MSTP-PORT-TABLE;
        uses GENERIC-INTERFACE-LIST-DETAIL-TABLE;
        uses L2VPN-OPER-L2VPN-RESOURCE-STATE-MP;
        uses BRIDGE-DOMAIN-TABLE;
        uses DISCOVERY-SUMMARY;
        uses PSEUDOWIRE-CLASS-TABLE;
        uses L2VPN-COLLABORATORS;
        uses GENERIC-INTERFACE-LIST-TABLE;
        uses MSTP-VLAN-TABLE;
        uses L2VPN-PBB-BSA;
        uses XCONNECT-BRIEF;
      }
    }
  }

  container l2vpn {
    xr:xr-xml-map "l2vpn_oper:L2VPN";
    config false;
    description "l2vpn";

    container pseudowire-headend {
      xr:xr-xml-map "l2vpn_oper:PseudowireHeadend";
      description "Pseudowire Headend related operational data";

      container detail-interfaces {
        xr:xr-xml-map "l2vpn_oper:DetailInterfaceTable";
        description "PW-HE Interfaces";

        list detail-interface {
          xr:xr-xml-map "l2vpn_oper:DetailInterface";
          key "interface-name";
          description "PW-HE Interface detail";
          leaf interface-name {
            xr:xr-xml-map "l2vpn_oper:InterfaceName";
            type xr:Cisco-ios-xr-string {
              length "0..64";
            }
            description "PWHE Interface name";
          }
          uses L2VPN-PWHE-DETAIL;
        }
      }

      container summary {
        xr:xr-xml-map "l2vpn_oper:Summary";
        description "PW-HE interface summary";
        uses L2VPN-PWHE-SUMMARY;
      }
    }
    uses DISCOVERY-TABLE;
    uses MAIN-INTERFACE-TABLE;
    uses G8032-SUMMARY;
    uses BRIDGE-SUMMARY;
    uses NSR;
    uses GLOBAL-SETTINGS;
    uses PWR;
    uses XCONNECT-MP2MP-CE2CE-TABLE;
    uses XCONNECT-TABLE;
    uses XCONNECT-GROUP-TABLE;
    uses XCONNECT-MP2MP-TABLE;
    uses G8032-DETAIL;
    uses INDEX-TABLE;
    uses XCONNECT-SUMMARY;
    uses MVRP-TABLE;
    uses MSTP-PORT-TABLE;
    uses GENERIC-INTERFACE-LIST-DETAIL-TABLE;
    uses L2VPN-OPER-L2VPN-RESOURCE-STATE-MP;
    uses BRIDGE-DOMAIN-TABLE;
    uses DISCOVERY-SUMMARY;
    uses PSEUDOWIRE-CLASS-TABLE;
    uses L2VPN-COLLABORATORS;
    uses GENERIC-INTERFACE-LIST-TABLE;
    uses MSTP-VLAN-TABLE;
    uses L2VPN-PBB-BSA;
    uses XCONNECT-BRIEF;
  }

  container generic-interface-list-v2 {
    xr:xr-xml-map "iflist_oper:GenericInterfaceListV2";
    config false;
    description "generic interface list v2";

    container nodes {
      xr:xr-xml-map "iflist_oper:NodeTable";
      description
        "Table of generic interface list operational data
        for a particular node";

      list node {
        xr:xr-xml-map "iflist_oper:Node";
        key "node-id";
        description
          "Generic interface list operational data for a
          particular node";
        leaf node-id {
          xr:xr-xml-map "iflist_oper:NodeID";
          type xr:Node-id;
          description "Location";
        }
        uses GENERIC-INTERFACE-LIST-TABLE-V2;
      }
    }

    container standby {
      xr:xr-xml-map "iflist_oper:Standby";
      description "Standby generic interface list operational data";
      uses GENERIC-INTERFACE-LIST-TABLE-V2;
    }

    container active {
      xr:xr-xml-map "iflist_oper:Active";
      description "Active generic interface list operational data";
      uses GENERIC-INTERFACE-LIST-TABLE-V2;
    }
  }
}
