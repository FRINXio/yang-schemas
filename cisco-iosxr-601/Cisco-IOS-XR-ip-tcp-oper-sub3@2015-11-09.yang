submodule Cisco-IOS-XR-ip-tcp-oper-sub3 {

  belongs-to Cisco-IOS-XR-ip-tcp-oper {
    prefix Cisco-IOS-XR-ip-tcp-oper;
  }

  /*** LINKAGE (IMPORTS / INCLUDES) ***/

  import ietf-inet-types { prefix "inet"; }

  import Cisco-IOS-XR-types { prefix "xr"; }

  include Cisco-IOS-XR-ip-tcp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-tcp package operational data.

     Copyright (c) 2013-2015 by Cisco Systems, Inc.
     All rights reserved.";

  revision "2015-11-09" {
    description
      "IOS XR 6.0 revision.";
  }

  typedef Tcp-timer {
    type enumeration {
      enum retransmission-timer {
        value 0;
        description "Retransmission timer";
      }
      enum window-probe-timer {
        value 1;
        description "Send Window Probe timer";
      }
      enum timewait-state-timer {
        value 2;
        description "TIMEWAIT state timer";
      }
      enum ack-hold-timer {
        value 3;
        description "ACK Hold timer";
      }
      enum keep-alive-timer {
        value 4;
        description "Keep Alive timer";
      }
      enum pmtu-ager-timer {
        value 5;
        description "PMTU Ager Timer";
      }
      enum retransmission-giveup-timer {
        value 6;
        description "Retransmission Giveup timer";
      }
      enum throttle-timer {
        value 7;
        description "Throttle (for PAW/xipc) timer";
      }
    }
    description "TCP Timer Type";
  }
  typedef Pak-prio {
    type enumeration {
      enum unspecified-packet {
        value 0;
        description "Unspecified";
      }
      enum normal-packet {
        value 1;
        description
          "Normal: all traffic routed via this router,
          Telnet/FTP traffic generated from within this
          router";
      }
      enum medium-packet {
        value 2;
        description
          "Medium: Packets with low drop probability e.g.
          Routing updates & requests";
      }
      enum high-packet {
        value 3;
        description
          "High: Packets with very low drop probability
          and normal delivery e.g. L3 Keepalives like
          OSPF/ISIS Hellos";
      }
      enum crucial-packet {
        value 4;
        description
          "Crucial: Packets with very low drop probability
          and expedited delivery e.g L2 keepalives, HDLC
          Keepalives";
      }
    }
    description "Packet Priority Types";
  }
  typedef Tcp-conn-state {
    type enumeration {
      enum closed {
        value 0;
        description "Closed";
      }
      enum listen {
        value 1;
        description "Listen";
      }
      enum syn-sent {
        value 2;
        description "Syn sent";
      }
      enum syn-received {
        value 3;
        description "Syn received";
      }
      enum established {
        value 4;
        description "Established";
      }
      enum close-wait {
        value 5;
        description "Close wait";
      }
      enum fin-wait1 {
        value 6;
        description "FIN Wait1";
      }
      enum closing {
        value 7;
        description "Closing";
      }
      enum last-ack {
        value 8;
        description "Last ack";
      }
      enum fin-wait2 {
        value 9;
        description "FIN Wait2";
      }
      enum time-wait {
        value 10;
        description "Time wait";
      }
    }
    description "TCP Connection State";
  }

  grouping TCP-SH-BRIEF-BAG {
    description "Summary information about a TCP connection";
    leaf address-family {
      xr:xr-xml-map "tcp_types:AddressFamily";
      type Addr-family;
      description "Address family";
    }
    leaf pcb {
      xr:xr-xml-map "tcp_types:PCB";
      type uint64;
      description "PCB Address";
    }
    leaf connection-state {
      xr:xr-xml-map "tcp_types:ConnectionState";
      type Tcp-conn-state;
      description "Connection state";
    }
    leaf local-pid {
      xr:xr-xml-map "tcp_types:LocalPid";
      type uint32;
      description "Id of the local process";
    }
    leaf local-port {
      xr:xr-xml-map "tcp_types:LocalPort";
      type uint16;
      description "Local port";
    }
    leaf foreign-port {
      xr:xr-xml-map "tcp_types:ForeignPort";
      type uint16;
      description "Foreign port";
    }
    leaf current-receive-queue-size {
      xr:xr-xml-map "tcp_types:CurrentReceiveQueueSize";
      type uint32;
      units "byte";
      description "Current receive queue size in bytes";
    }
    leaf current-send-queue-size {
      xr:xr-xml-map "tcp_types:CurrentSendQueueSize";
      type uint32;
      units "byte";
      description "Current send queue size in bytes";
    }
    leaf vrf-id {
      xr:xr-xml-map "tcp_types:VRF_ID";
      type uint32;
      description "VRF ID";
    }
    leaf-list local-address {
      xr:xr-xml-map "tcp_types:LocalAddress";
      type inet:ipv4-address;
      max-elements "4";
      description "Local address";
    }
    leaf-list foreign-address {
      xr:xr-xml-map "tcp_types:ForeignAddress";
      type inet:ipv4-address;
      max-elements "4";
      description "Foreign address";
    }
  }

  grouping TCP-SOCKBUF-STATES-BAG {
    description "TCP Socket Buffer State Flags";
    leaf locked {
      xr:xr-xml-map "tcp_types:Locked";
      type boolean;
      description "Lock on data queue (so_rcv only)";
    }
    leaf waiting-for-lock {
      xr:xr-xml-map "tcp_types:WaitingForLock";
      type boolean;
      description "Someone is waiting to lock";
    }
    leaf waiting-for-data {
      xr:xr-xml-map "tcp_types:WaitingForData";
      type boolean;
      description "Someone is waiting for data/space";
    }
    leaf input-select {
      xr:xr-xml-map "tcp_types:InputSelect";
      type boolean;
      description "Buffer is selected for INPUT";
    }
    leaf async-io {
      xr:xr-xml-map "tcp_types:AsyncIO";
      type boolean;
      description "Async I/O";
    }
    leaf not-interruptible {
      xr:xr-xml-map "tcp_types:NotInterruptible";
      type boolean;
      description "Not interruptible";
    }
    leaf io-timer-set {
      xr:xr-xml-map "tcp_types:IOTimerSet";
      type boolean;
      description "Read/write timer set";
    }
    leaf delayed-wakeup {
      xr:xr-xml-map "tcp_types:DelayedWakeup";
      type boolean;
      description "Want delayed wakeups";
    }
    leaf wakeup {
      xr:xr-xml-map "tcp_types:Wakeup";
      type boolean;
      description "Read/write wakeup pending";
    }
    leaf connect-wakeup {
      xr:xr-xml-map "tcp_types:ConnectWakeup";
      type boolean;
      description "Connect wakeup pending";
    }
    leaf output-select {
      xr:xr-xml-map "tcp_types:OutputSelect";
      type boolean;
      description "Buffer is selected for OUTPUT";
    }
    leaf out-of-band-select {
      xr:xr-xml-map "tcp_types:OutOfBandSelect";
      type boolean;
      description "Buffer is selected for OBAND";
    }
  }

  grouping SACKHOLE-BAG {
    description "Sack send hole entry";
    leaf start {
      xr:xr-xml-map "tcp_types:Start";
      type uint32;
      description "Start seq no. of hole";
    }
    leaf end {
      xr:xr-xml-map "tcp_types:End";
      type uint32;
      description "End   seq no. of hole";
    }
    leaf duplicated-ack {
      xr:xr-xml-map "tcp_types:DuplicatedACK";
      type uint32;
      description "Number of dup (s)acks for this hole";
    }
    leaf retransmitted {
      xr:xr-xml-map "tcp_types:Retransmitted";
      type uint32;
      description "Next seq. no in hole to be retransmitted";
    }
  }

  grouping SACKBLK-BAG {
    description "Sack block entry";
    leaf start {
      xr:xr-xml-map "tcp_types:Start";
      type uint32;
      description "Start seq no. of sack block";
    }
    leaf end {
      xr:xr-xml-map "tcp_types:End";
      type uint32;
      description "End   seq no. of sack block";
    }
  }

  grouping TCP-CONN-STATES-BAG {
    description "TCP Connection states";
    leaf nagle-wait {
      xr:xr-xml-map "tcp_types:NagleWait";
      type boolean;
      description "Nagle has delayed output";
    }
    leaf ack-needed {
      xr:xr-xml-map "tcp_types:AckNeeded";
      type boolean;
      description "Send an ACK";
    }
    leaf fin-sent {
      xr:xr-xml-map "tcp_types:FINSent";
      type boolean;
      description "FIN has been sent";
    }
    leaf probing {
      xr:xr-xml-map "tcp_types:Probing";
      type boolean;
      description "Probing a closed window";
    }
    leaf need-push {
      xr:xr-xml-map "tcp_types:NeedPush";
      type boolean;
      description "Need to push data out";
    }
    leaf pushed {
      xr:xr-xml-map "tcp_types:Pushed";
      type boolean;
      description "A segment is pushed due to MSG_PUSH";
    }
    leaf in-syn-cache {
      xr:xr-xml-map "tcp_types:InSYNCache";
      type boolean;
      description "Connection is in SYN cache";
    }
    leaf path-mtu-ager {
      xr:xr-xml-map "tcp_types:PathMTUAger";
      type boolean;
      description "Path MTU aging timer is running";
    }
  }

  grouping TCP-CONN-FEATURES-BAG {
    description "TCP Connection features";
    leaf selective-ack {
      xr:xr-xml-map "tcp_types:SelectiveACK";
      type boolean;
      description "Selective ack on?";
    }
    leaf md5 {
      xr:xr-xml-map "tcp_types:MD5";
      type boolean;
      description "MD5 option on?";
    }
    leaf timestamps {
      xr:xr-xml-map "tcp_types:Timestamps";
      type boolean;
      description "Timestamps on?";
    }
    leaf window-scaling {
      xr:xr-xml-map "tcp_types:WindowScaling";
      type boolean;
      description "Window-scaling on?";
    }
    leaf nagle {
      xr:xr-xml-map "tcp_types:Nagle";
      type boolean;
      description "Nagle algorithm on?";
    }
    leaf giveup-timer {
      xr:xr-xml-map "tcp_types:GiveupTimer";
      type boolean;
      description "Giveup timer is on?";
    }
    leaf connection-keep-alive-timer {
      xr:xr-xml-map "tcp_types:ConnectionKeepAliveTimer";
      type boolean;
      description "Keepalive timer is on?";
    }
    leaf path-mtu-discovery {
      xr:xr-xml-map "tcp_types:PathMTUDiscovery";
      type boolean;
      description "Path MTU Discovery feature is on?";
    }
    leaf mss-cisco {
      xr:xr-xml-map "tcp_types:MSS_cisco";
      type boolean;
      description "tcp mss feature is on?";
    }
  }

  grouping TCP-SOCK-STATES-BAG {
    description "TCP Socket State Flags";
    leaf no-file-descriptor-reference {
      xr:xr-xml-map "tcp_types:NoFileDescriptorReference";
      type boolean;
      description "No file descriptor ref";
    }
    leaf is-connected {
      xr:xr-xml-map "tcp_types:IsConnected";
      type boolean;
      description "Socket is connected to peer";
    }
    leaf is-connecting {
      xr:xr-xml-map "tcp_types:IsConnecting";
      type boolean;
      description "Connecting in progress";
    }
    leaf is-disconnecting {
      xr:xr-xml-map "tcp_types:IsDisconnecting";
      type boolean;
      description "Disconnecting in progress";
    }
    leaf cant-send-more {
      xr:xr-xml-map "tcp_types:CantSendMore";
      type boolean;
      description "Can't send more data to peer";
    }
    leaf cant-receive-more {
      xr:xr-xml-map "tcp_types:CantReceiveMore";
      type boolean;
      description "Can't recv more data from peer";
    }
    leaf received-at-mark {
      xr:xr-xml-map "tcp_types:ReceivedAtMark";
      type boolean;
      description "At mark on input";
    }
    leaf privileged {
      xr:xr-xml-map "tcp_types:Privileged";
      type boolean;
      description "Privileged for broadcast, raw...";
    }
    leaf block-close {
      xr:xr-xml-map "tcp_types:BlockClose";
      type boolean;
      description
        "Close is blocked (i.e. socket is a replicated
        socket on a standby node";
    }
    leaf async-io-notify {
      xr:xr-xml-map "tcp_types:AsyncIONotify";
      type boolean;
      description "Async i/o notify";
    }
    leaf is-confirming {
      xr:xr-xml-map "tcp_types:IsConfirming";
      type boolean;
      description "Deciding to accept connection req";
    }
    leaf is-solock {
      xr:xr-xml-map "tcp_types:IsSolock";
      type boolean;
      description "Mutex acquired by solock()";
    }
    leaf is-detached {
      xr:xr-xml-map "tcp_types:IsDetached";
      type boolean;
      description "PCB and socket are detached";
    }
    leaf block-receive {
      xr:xr-xml-map "tcp_types:BlockReceive";
      type boolean;
      description
        "Socket is blocked for receive - while going
        through SSO initial sync";
    }
    leaf block-send {
      xr:xr-xml-map "tcp_types:BlockSend";
      type boolean;
      description
        "Socket is blocked for send (if it is a
        replicated socket on a standby node)";
    }
  }

  grouping TCP-SOCK-OPTIONS-BAG {
    description "TCP Socket Option Flags ";
    leaf debug {
      xr:xr-xml-map "tcp_types:Debug";
      type boolean;
      description "Turn on debugging info recording";
    }
    leaf accept-connection {
      xr:xr-xml-map "tcp_types:AcceptConnection";
      type boolean;
      description "Socket has had listen()";
    }
    leaf reuse-address {
      xr:xr-xml-map "tcp_types:ReuseAddress";
      type boolean;
      description "Allow local address reuse";
    }
    leaf keep-alive {
      xr:xr-xml-map "tcp_types:KeepAlive";
      type boolean;
      description "Keep connections alive";
    }
    leaf dont-route {
      xr:xr-xml-map "tcp_types:DontRoute";
      type boolean;
      description "Just use interface addresses";
    }
    leaf broadcast {
      xr:xr-xml-map "tcp_types:Broadcast";
      type boolean;
      description "Permit sending of broadcast msgs";
    }
    leaf use-loopback {
      xr:xr-xml-map "tcp_types:UseLoopback";
      type boolean;
      description "Bypass hardware when possible";
    }
    leaf linger {
      xr:xr-xml-map "tcp_types:Linger";
      type boolean;
      description "Linger on close if data present";
    }
    leaf out-of-band-inline {
      xr:xr-xml-map "tcp_types:OutOfBandInline";
      type boolean;
      description "Leave received Out-of-band data inline";
    }
    leaf reuse-port {
      xr:xr-xml-map "tcp_types:ReusePort";
      type boolean;
      description "Allow local address & port reuse";
    }
    leaf nonblocking-io {
      xr:xr-xml-map "tcp_types:NonblockingIO";
      type boolean;
      description "Nonblocking socket I/O operation";
    }
  }

  grouping TCP-TIMER-BAG {
    description "TCP Timer Info";
    leaf timer-type {
      xr:xr-xml-map "tcp_types:TimerType";
      type Tcp-timer;
      description "Timer Type";
    }
    leaf timer-activations {
      xr:xr-xml-map "tcp_types:TimerActivations";
      type uint32;
      description "Count of timer activations";
    }
    leaf timer-expirations {
      xr:xr-xml-map "tcp_types:TimerExpirations";
      type uint32;
      description "Count of timer expirations";
    }
    leaf timer-next-activation {
      xr:xr-xml-map "tcp_types:TimerNextActivation";
      type uint32;
      description "Timer next activation (msec)";
    }
  }

  grouping TCP-SH-TABLE-BAG {
    description "Detailed information about a TCP connection";

    container socket-option-flags {
      description "Socket option flags";
      uses TCP-SOCK-OPTIONS-BAG;
    }

    container socket-state-flags {
      description "Socket state flags";
      uses TCP-SOCK-STATES-BAG;
    }

    container feature-flags {
      description "Connection feature flags";
      uses TCP-CONN-FEATURES-BAG;
    }

    container state-flags {
      description "Connection state flags";
      uses TCP-CONN-STATES-BAG;
    }

    container request-flags {
      description "Connection request flags";
      uses TCP-CONN-FEATURES-BAG;
    }

    container receive-buf-state-flags {
      description "Receive buffer state flags";
      uses TCP-SOCKBUF-STATES-BAG;
    }

    container send-buf-state-flags {
      description "Send buffer state flags";
      uses TCP-SOCKBUF-STATES-BAG;
    }
    leaf address-family {
      xr:xr-xml-map "tcp_types:AddressFamily";
      type Addr-family;
      description "Address Family";
    }
    leaf pcb {
      xr:xr-xml-map "tcp_types:PCB";
      type uint64;
      description "PCB Address";
    }
    leaf so {
      xr:xr-xml-map "tcp_types:SO";
      type uint64;
      description "Socket Address";
    }
    leaf tcpcb {
      xr:xr-xml-map "tcp_types:TCPCB";
      type uint64;
      description "TCPCB Address";
    }
    leaf vrf-id {
      xr:xr-xml-map "tcp_types:VRF_ID";
      type uint32;
      description "VRF Id";
    }
    leaf connection-state {
      xr:xr-xml-map "tcp_types:ConnectionState";
      type Tcp-conn-state;
      description "Connection state";
    }
    leaf established-time {
      xr:xr-xml-map "tcp_types:EstablishedTime";
      type uint32;
      description "Time at which connection is established";
    }
    leaf local-pid {
      xr:xr-xml-map "tcp_types:LocalPid";
      type uint32;
      description "Id of the local process";
    }
    leaf local-port {
      xr:xr-xml-map "tcp_types:LocalPort";
      type uint16;
      description "Local port";
    }
    leaf foreign-port {
      xr:xr-xml-map "tcp_types:ForeignPort";
      type uint16;
      description "Foreign port";
    }
    leaf packet-priority {
      xr:xr-xml-map "tcp_types:PacketPriority";
      type Pak-prio;
      description "Priority given to packets on this socket";
    }
    leaf packet-tos {
      xr:xr-xml-map "tcp_types:PacketTOS";
      type uint16;
      description
        "Type of Service value to be applied to
        transmistted packets";
    }
    leaf packet-ttl {
      xr:xr-xml-map "tcp_types:PacketTTL";
      type uint16;
      description "TTL to be applied to transmited packets";
    }
    leaf hash-index {
      xr:xr-xml-map "tcp_types:HashIndex";
      type uint32;
      description "Index of the Hash Bucket";
    }
    leaf current-receive-queue-size {
      xr:xr-xml-map "tcp_types:CurrentReceiveQueueSize";
      type uint32;
      units "byte";
      description "Current receive queue size in bytes";
    }
    leaf max-receive-queue-size {
      xr:xr-xml-map "tcp_types:MaxReceiveQueueSize";
      type uint32;
      units "byte";
      description "Max receive queue size in bytes";
    }
    leaf current-send-queue-size {
      xr:xr-xml-map "tcp_types:CurrentSendQueueSize";
      type uint32;
      units "byte";
      description "Current send queue size in bytes";
    }
    leaf max-send-queue-size {
      xr:xr-xml-map "tcp_types:MaxSendQueueSize";
      type uint32;
      units "byte";
      description "Max send queue size in bytes";
    }
    leaf current-receive-queue-packet-size {
      xr:xr-xml-map "tcp_types:CurrentReceiveQueuePacketSize";
      type uint32;
      description "Current receive queue size in packets";
    }
    leaf max-receive-queue-packet-size {
      xr:xr-xml-map "tcp_types:MaxReceiveQueuePacketSize";
      type uint32;
      description "Max receive queue size in packets";
    }
    leaf save-queue-size {
      xr:xr-xml-map "tcp_types:SaveQueueSize";
      type uint32;
      units "byte";
      description "Save queue (out-of seq data) size in bytes";
    }
    leaf send-initial-sequence-num {
      xr:xr-xml-map "tcp_types:SendInitialSequenceNum";
      type uint32;
      description "Initial send sequence number";
    }
    leaf send-unack-sequence-num {
      xr:xr-xml-map "tcp_types:SendUnackSequenceNum";
      type uint32;
      description "Sequence number of unacked data";
    }
    leaf send-next-sequence-num {
      xr:xr-xml-map "tcp_types:SendNextSequenceNum";
      type uint32;
      description "Sequence number of next data to be sent";
    }
    leaf send-max-sequence-num {
      xr:xr-xml-map "tcp_types:SendMaxSequenceNum";
      type uint32;
      description "Highest sequence number sent";
    }
    leaf send-window-size {
      xr:xr-xml-map "tcp_types:SendWindowSize";
      type uint32;
      units "byte";
      description "Send window size in bytes";
    }
    leaf send-congestion-window-size {
      xr:xr-xml-map "tcp_types:SendCongestionWindowSize";
      type uint32;
      units "byte";
      description "Send congestion window size in bytes";
    }
    leaf receive-initial-sequence-num {
      xr:xr-xml-map "tcp_types:ReceiveInitialSequenceNum";
      type uint32;
      description "Initial receive sequence number";
    }
    leaf receive-next-sequence-num {
      xr:xr-xml-map "tcp_types:ReceiveNextSequenceNum";
      type uint32;
      description "Next sequence number expected";
    }
    leaf receive-adv-window-size {
      xr:xr-xml-map "tcp_types:ReceiveAdvWindowSize";
      type uint32;
      units "byte";
      description "Receive advertised window size in bytes";
    }
    leaf receive-window-size {
      xr:xr-xml-map "tcp_types:ReceiveWindowSize";
      type uint32;
      units "byte";
      description "Receive window size in bytes";
    }
    leaf mss {
      xr:xr-xml-map "tcp_types:MSS";
      type uint32;
      units "byte";
      description "Max segment size calculated in bytes";
    }
    leaf peer-mss {
      xr:xr-xml-map "tcp_types:PeerMSS";
      type uint32;
      units "byte";
      description "Max segment size offered by the peer in bytes";
    }
    leaf srtt {
      xr:xr-xml-map "tcp_types:SRTT";
      type uint32;
      description "Smoothed round trip time * 8 (msec)";
    }
    leaf rtto {
      xr:xr-xml-map "tcp_types:RTTO";
      type uint32;
      description "Round trip timeout (msec)";
    }
    leaf krtt {
      xr:xr-xml-map "tcp_types:KRTT";
      type uint32;
      description "Round trip time (karn algorithm) (msec)";
    }
    leaf srtv {
      xr:xr-xml-map "tcp_types:SRTV";
      type uint32;
      description "Smoothed round trip time variance * 4 (msec)";
    }
    leaf min-rtt {
      xr:xr-xml-map "tcp_types:MinRTT";
      type uint32;
      description "Min RTT (msec)";
    }
    leaf max-rtt {
      xr:xr-xml-map "tcp_types:MaxRTT";
      type uint32;
      description "Max RTT (msec)";
    }
    leaf retries {
      xr:xr-xml-map "tcp_types:Retries";
      type uint32;
      description "Number of retries";
    }
    leaf ack-hold-time {
      xr:xr-xml-map "tcp_types:AckHoldTime";
      type uint32;
      description "ACK hold time (msec)";
    }
    leaf giveup-time {
      xr:xr-xml-map "tcp_types:GiveupTime";
      type uint32;
      description "Giveup time (msec)";
    }
    leaf keep-alive-time {
      xr:xr-xml-map "tcp_types:KeepAliveTime";
      type uint32;
      description "Keepalive time (msec)";
    }
    leaf syn-wait-time {
      xr:xr-xml-map "tcp_types:SYNWaitTime";
      type uint32;
      description "SYN wait time (msec)";
    }
    leaf rxsy-naclname {
      xr:xr-xml-map "tcp_types:RXSYNaclname";
      type string {
        length "0..64";
      }
      description "RX Syn acl name";
    }
    leaf soft-error {
      xr:xr-xml-map "tcp_types:SoftError";
      type int32;
      description "Error code from ICMP Notify";
    }
    leaf sock-error {
      xr:xr-xml-map "tcp_types:SockError";
      type int32;
      description "Socket error code";
    }
    leaf is-retrans-forever {
      xr:xr-xml-map "tcp_types:IsRetransForever";
      type boolean;
      description "Retransimit forever?";
    }
    leaf min-mss {
      xr:xr-xml-map "tcp_types:MinMSS";
      type uint32;
      description "Lowest MSS ever used";
    }
    leaf max-mss {
      xr:xr-xml-map "tcp_types:MaxMSS";
      type uint32;
      description "Highest MSS ever used";
    }
    leaf connect-retries {
      xr:xr-xml-map "tcp_types:ConnectRetries";
      type uint16;
      description "Number of times connect will be retried?";
    }
    leaf connect-retry-interval {
      xr:xr-xml-map "tcp_types:ConnectRetryInterval";
      type uint16;
      units "second";
      description "Connect retry interval in seconds";
    }
    leaf receive-window-scale {
      xr:xr-xml-map "tcp_types:ReceiveWindowScale";
      type uint32;
      description "Window scaling for receive window";
    }
    leaf send-window-scale {
      xr:xr-xml-map "tcp_types:SendWindowScale";
      type uint32;
      description "Window scaling for send window";
    }
    leaf request-receive-window-scale {
      xr:xr-xml-map "tcp_types:RequestReceiveWindowScale";
      type uint32;
      description "Requested receive window scale";
    }
    leaf rqst-send-wnd-scale {
      xr:xr-xml-map "tcp_types:RqstSendWndScale";
      type uint32;
      description "Requested send window scale";
    }
    leaf time-stamp-recent {
      xr:xr-xml-map "tcp_types:TimeStampRecent";
      type uint32;
      description "Timestamp from remote host";
    }
    leaf time-stamp-recent-age {
      xr:xr-xml-map "tcp_types:TimeStampRecentAge";
      type uint32;
      description "Timestamp when last updated";
    }
    leaf last-ack-sent {
      xr:xr-xml-map "tcp_types:LastACKSent";
      type uint32;
      description "ACK number of a sent segment";
    }
    leaf sendbuf-lowwat {
      xr:xr-xml-map "tcp_types:SendbufLowwat";
      type uint32;
      description "Send buffer's low water mark";
    }
    leaf recvbuf-lowwat {
      xr:xr-xml-map "tcp_types:RecvbufLowwat";
      type uint32;
      description "Receive buffer's low water mark";
    }
    leaf sendbuf-hiwat {
      xr:xr-xml-map "tcp_types:SendbufHiwat";
      type uint32;
      description "Send buffer's high water mark";
    }
    leaf recvbuf-hiwat {
      xr:xr-xml-map "tcp_types:RecvbufHiwat";
      type uint32;
      description "Receive buffer's high water mark";
    }
    leaf sendbuf-notify-thresh {
      xr:xr-xml-map "tcp_types:SendbufNotifyThresh";
      type uint32;
      description "Send buffer's notify threshold";
    }
    leaf send-pdu-count {
      xr:xr-xml-map "tcp_types:SendPDUCount";
      type uint32;
      description "# of PDU's in Send Buffer";
    }
    leaf output-ifhandle {
      xr:xr-xml-map "tcp_types:OutputIfhandle";
      type uint32;
      description "Cached Outgoing interface  handle";
    }
    leaf fib-pd-ctx-size {
      xr:xr-xml-map "tcp_types:FibPdCtxSize";
      type uint32;
      description "Cached fib pd context size";
    }
    leaf num-labels {
      xr:xr-xml-map "tcp_types:NumLabels";
      type uint32;
      description "Number of labels returned by fib lookup";
    }
    leaf-list local-address {
      xr:xr-xml-map "tcp_types:LocalAddress";
      type inet:ipv4-address;
      max-elements "4";
      description "Local address";
    }
    leaf-list foreign-address {
      xr:xr-xml-map "tcp_types:ForeignAddress";
      type inet:ipv4-address;
      max-elements "4";
      description "Foreign address";
    }
    leaf-list fib-pd-ctx {
      xr:xr-xml-map "tcp_types:FibPdCtx";
      type uint32;
      max-elements "4";
      description "Cached fib pd context";
    }
    leaf-list fib-label-output {
      xr:xr-xml-map "tcp_types:FibLabelOutput";
      type uint32;
      max-elements "7";
      description "Cached Label stack";
    }

    list timer {
      max-elements "8";
      description "Timers";
      uses TCP-TIMER-BAG;
    }

    list sack-blk {
      max-elements "6";
      description "Seq nos. of sack blocks";
      uses SACKBLK-BAG;
    }

    list send-sack-hole {
      max-elements "6";
      description "Sorted list of sack holes";
      uses SACKHOLE-BAG;
    }
  }

  grouping TCP-SH-STATS-BAG {
    description "TCP Statistics";
    leaf syn-cache-count {
      xr:xr-xml-map "tcp_types:SYNCacheCount";
      type uint32;
      description "Current number of SYN cache entries";
    }
    leaf num-open-sockets {
      xr:xr-xml-map "tcp_types:NumOpenSockets";
      type uint32;
      description "Number of Open sockets";
    }
    leaf total-pakets-sent {
      xr:xr-xml-map "tcp_types:TotalPaketsSent";
      type uint32;
      description "Total packets sent";
    }
    leaf send-packets-dropped {
      xr:xr-xml-map "tcp_types:SendPacketsDropped";
      type uint32;
      description
        "Total transmit packets dropped due to general
        failures";
    }
    leaf send-auth-packets-dropped {
      xr:xr-xml-map "tcp_types:SendAuthPacketsDropped";
      type uint32;
      description
        "Total transmit packets dropped due to
        authentication failures";
    }
    leaf data-pakets-sent {
      xr:xr-xml-map "tcp_types:DataPaketsSent";
      type uint32;
      description "Data packets sent";
    }
    leaf data-bytes-sent {
      xr:xr-xml-map "tcp_types:DataBytesSent";
      type uint32;
      units "byte";
      description "Data bytes sent";
    }
    leaf packets-retransmitted {
      xr:xr-xml-map "tcp_types:PacketsRetransmitted";
      type uint32;
      description "Data packets retransmitted";
    }
    leaf bytes-retransmitted {
      xr:xr-xml-map "tcp_types:BytesRetransmitted";
      type uint32;
      units "byte";
      description "Data bytes retransmitted";
    }
    leaf ack-only-packets-sent {
      xr:xr-xml-map "tcp_types:ACKOnlyPacketsSent";
      type uint32;
      description "Ack only packets sent (incl. delay)";
    }
    leaf delay-ack-packets-sent {
      xr:xr-xml-map "tcp_types:DelayACKPacketsSent";
      type uint32;
      description "Delay ack packets sent";
    }
    leaf urgent-only-packets-sent {
      xr:xr-xml-map "tcp_types:UrgentOnlyPacketsSent";
      type uint32;
      description "Urgent only packets sent";
    }
    leaf window-probe-packets-sent {
      xr:xr-xml-map "tcp_types:WindowProbePacketsSent";
      type uint32;
      description "Window probe packets sent";
    }
    leaf window-update-packets-sent {
      xr:xr-xml-map "tcp_types:WindowUpdatePacketsSent";
      type uint32;
      description "Window update packets sent";
    }
    leaf control-packets-sent {
      xr:xr-xml-map "tcp_types:ControlPacketsSent";
      type uint32;
      description "Control (SYN|FIN|RST) packets sent";
    }
    leaf rst-packets-sent {
      xr:xr-xml-map "tcp_types:RSTPacketsSent";
      type uint32;
      description "RST packets sent";
    }
    leaf total-packets-received {
      xr:xr-xml-map "tcp_types:TotalPacketsReceived";
      type uint32;
      description "Total packets received";
    }
    leaf received-packets-dropped {
      xr:xr-xml-map "tcp_types:ReceivedPacketsDropped";
      type uint32;
      description
        "Received packets dropped due to general failures";
    }
    leaf synacl-match-pkts-dropped {
      xr:xr-xml-map "tcp_types:SYNACLMatchPktsDropped";
      type uint32;
      description
        "Received packets dropped     due to ACL DENY on
        SYN pkts";
    }
    leaf received-packets-dropped-stale-c-hdr {
      xr:xr-xml-map "tcp_types:ReceivedPacketsDroppedStaleCHdr";
      type uint32;
      description
        "Received packets dropped due to stale cached
        header";
    }
    leaf received-auth-packets-dropped {
      xr:xr-xml-map "tcp_types:ReceivedAuthPacketsDropped";
      type uint32;
      description
        "Received packets dropped due to authentication
        failures";
    }
    leaf ack-packets-received {
      xr:xr-xml-map "tcp_types:ACKPacketsReceived";
      type uint32;
      description "Ack packets received";
    }
    leaf ackbytes-received {
      xr:xr-xml-map "tcp_types:ACKBytesReceived";
      type uint32;
      units "byte";
      description "Bytes acked by ack packets";
    }
    leaf duplicated-ack-packets-received {
      xr:xr-xml-map "tcp_types:DuplicatedACKPacketsReceived";
      type uint32;
      description "Duplicate ack packets";
    }
    leaf ack-packets-for-unsent-received {
      xr:xr-xml-map "tcp_types:ACKPacketsForUnsentReceived";
      type uint32;
      description "Ack packets for unsent data";
    }
    leaf data-packets-received-in-sequence {
      xr:xr-xml-map "tcp_types:DataPacketsReceivedInSequence";
      type uint32;
      description "Data packets received in sequence";
    }
    leaf data-bytes-received-in-sequence {
      xr:xr-xml-map "tcp_types:DataBytesReceivedInSequence";
      type uint32;
      units "byte";
      description "Data bytes received in sequence";
    }
    leaf duplicate-packets-received {
      xr:xr-xml-map "tcp_types:DuplicatePacketsReceived";
      type uint32;
      description "Duplicate packets received";
    }
    leaf duplicate-bytes-received {
      xr:xr-xml-map "tcp_types:DuplicateBytesReceived";
      type uint32;
      units "byte";
      description "Duplicate bytes received";
    }
    leaf partial-duplicate-ack-received {
      xr:xr-xml-map "tcp_types:PartialDuplicateACKReceived";
      type uint32;
      description "Packets with partial dup data";
    }
    leaf partial-duplicate-bytes-received {
      xr:xr-xml-map "tcp_types:PartialDuplicateBytesReceived";
      type uint32;
      units "byte";
      description "Bytes with partial dup data";
    }
    leaf out-of-order-packets-received {
      xr:xr-xml-map "tcp_types:OutOfOrderPacketsReceived";
      type uint32;
      description "Out-of-order packets received";
    }
    leaf out-of-order-bytes-received {
      xr:xr-xml-map "tcp_types:OutOfOrderBytesReceived";
      type uint32;
      units "byte";
      description "Out-of-order bytes received";
    }
    leaf after-window-packets-received {
      xr:xr-xml-map "tcp_types:AfterWindowPacketsReceived";
      type uint32;
      description "After-window packets received";
    }
    leaf after-window-bytes-received {
      xr:xr-xml-map "tcp_types:AfterWindowBytesReceived";
      type uint32;
      units "byte";
      description "After-window bytes received";
    }
    leaf window-probe-packets-received {
      xr:xr-xml-map "tcp_types:WindowProbePacketsReceived";
      type uint32;
      description "Window probe packets received";
    }
    leaf window-update-packets-received {
      xr:xr-xml-map "tcp_types:WindowUpdatePacketsReceived";
      type uint32;
      description "Window update packets received";
    }
    leaf packets-received-after-close-packet {
      xr:xr-xml-map "tcp_types:PacketsReceivedAfterClosePacket";
      type uint32;
      description "Packets received after close";
    }
    leaf bad-checksum-packets-received {
      xr:xr-xml-map "tcp_types:BadChecksumPacketsReceived";
      type uint32;
      description "Packets received with bad checksum";
    }
    leaf too-short-packets-received {
      xr:xr-xml-map "tcp_types:TooShortPacketsReceived";
      type uint32;
      description "Packets received with too short size";
    }
    leaf malformed-packets-received {
      xr:xr-xml-map "tcp_types:MalformedPacketsReceived";
      type uint32;
      description "Packets received with malformed header";
    }
    leaf no-port-packets-received {
      xr:xr-xml-map "tcp_types:NoPortPacketsReceived";
      type uint32;
      description "Packets rcceived with no wild listener";
    }
    leaf connections-requested {
      xr:xr-xml-map "tcp_types:ConnectionsRequested";
      type uint32;
      description "Connection requests sent";
    }
    leaf connections-accepted {
      xr:xr-xml-map "tcp_types:ConnectionsAccepted";
      type uint32;
      description "Connection requests accepted";
    }
    leaf connections-established {
      xr:xr-xml-map "tcp_types:ConnectionsEstablished";
      type uint32;
      description "Connections established";
    }
    leaf connections-forcibly-closed {
      xr:xr-xml-map "tcp_types:ConnectionsForciblyClosed";
      type uint32;
      description "Connections forcibly closed";
    }
    leaf connections-closed {
      xr:xr-xml-map "tcp_types:ConnectionsClosed";
      type uint32;
      description "connections closed (incl. drops)";
    }
    leaf connections-dropped {
      xr:xr-xml-map "tcp_types:ConnectionsDropped";
      type uint32;
      description "connections dropped";
    }
    leaf embryonic-connection-dropped {
      xr:xr-xml-map "tcp_types:EmbryonicConnectionDropped";
      type uint32;
      description "Embryonic connections dropped";
    }
    leaf connections-failed {
      xr:xr-xml-map "tcp_types:ConnectionsFailed";
      type uint32;
      description "Connections failed";
    }
    leaf established-connections-reset {
      xr:xr-xml-map "tcp_types:EstablishedConnectionsReset";
      type uint32;
      description "Established connections reset";
    }
    leaf retransmit-timeouts {
      xr:xr-xml-map "tcp_types:RetransmitTimeouts";
      type uint32;
      description "Retransmit timeouts (incl. data packets)";
    }
    leaf retransmit-dropped {
      xr:xr-xml-map "tcp_types:RetransmitDropped";
      type uint32;
      description "Connection drops during retransmit timeouts";
    }
    leaf keep-alive-timeouts {
      xr:xr-xml-map "tcp_types:KeepAliveTimeouts";
      type uint32;
      description "Keepalive timeouts";
    }
    leaf keep-alive-dropped {
      xr:xr-xml-map "tcp_types:KeepAliveDropped";
      type uint32;
      description "Connection drops due to keepalive timeouts";
    }
    leaf keep-alive-probes {
      xr:xr-xml-map "tcp_types:KeepAliveProbes";
      type uint32;
      description "Keepalive probes sent";
    }
    leaf paws-dropped {
      xr:xr-xml-map "tcp_types:PAWSDropped";
      type uint32;
      description "Segments dropped due to PAWS";
    }
    leaf persist-dropped {
      xr:xr-xml-map "tcp_types:PersistDropped";
      type uint32;
      description "Segments dropped due to window probe";
    }
    leaf try-lock-dropped {
      xr:xr-xml-map "tcp_types:TryLockDropped";
      type uint32;
      description "Segments dropped due to trylock fail";
    }
    leaf connection-rate-limited {
      xr:xr-xml-map "tcp_types:ConnectionRateLimited";
      type uint32;
      description "Connections rate-limited";
    }
    leaf syn-cache-added {
      xr:xr-xml-map "tcp_types:SYNCacheAdded";
      type uint32;
      description "SYN Cache entries added";
    }
    leaf syn-cache-completed {
      xr:xr-xml-map "tcp_types:SYNCacheCompleted";
      type uint32;
      description "SYN Cache connections completed";
    }
    leaf syn-cache-timed-out {
      xr:xr-xml-map "tcp_types:SYNCacheTimedOut";
      type uint32;
      description "SYN Cache entries timed out";
    }
    leaf syn-cache-overflow {
      xr:xr-xml-map "tcp_types:SYNCacheOverflow";
      type uint32;
      description "SYN Cache entries dropped due to overflow";
    }
    leaf syn-cache-reset {
      xr:xr-xml-map "tcp_types:SYNCacheReset";
      type uint32;
      description "SYN Cache entries dropped due to RST";
    }
    leaf syn-cache-unreach {
      xr:xr-xml-map "tcp_types:SYNCacheUnreach";
      type uint32;
      description "SYN Cache entries dropped due to ICMP unreach";
    }
    leaf syn-cache-bucket-oflow {
      xr:xr-xml-map "tcp_types:SYNCacheBucketOflow";
      type uint32;
      description
        "SYN Cache entries dropped due to bucket overflow";
    }
    leaf syn-cache-aborted {
      xr:xr-xml-map "tcp_types:SYNCacheAborted";
      type uint32;
      description "SYN Cache entries aborted (no mem)";
    }
    leaf syn-cache-duplicate-sy-ns {
      xr:xr-xml-map "tcp_types:SYNCacheDuplicateSYNs";
      type uint32;
      description "SYN Cache duplicate SYNs received";
    }
    leaf syn-cache-dropped {
      xr:xr-xml-map "tcp_types:SYNCacheDropped";
      type uint32;
      description "SYN Cache entries dropped (no route/mem)";
    }
    leaf pulse-errors {
      xr:xr-xml-map "tcp_types:PulseErrors";
      type uint32;
      description "Punt (down to ip) failures";
    }
    leaf socket-layer-packets {
      xr:xr-xml-map "tcp_types:SocketLayerPackets";
      type uint32;
      description "Packets owned by the socket layer";
    }
    leaf reassembly-packets {
      xr:xr-xml-map "tcp_types:ReassemblyPackets";
      type uint32;
      description "Packets owned by TCP reassembly";
    }
    leaf recovered-packets {
      xr:xr-xml-map "tcp_types:RecoveredPackets";
      type uint32;
      description "Packets freed after starvation";
    }
    leaf packet-failures {
      xr:xr-xml-map "tcp_types:PacketFailures";
      type uint32;
      description "Packet allocation errors";
    }
    leaf mss-up {
      xr:xr-xml-map "tcp_types:MSSUp";
      type uint32;
      description "Number of times MSS was increased";
    }
    leaf mss-down {
      xr:xr-xml-map "tcp_types:MSSDown";
      type uint32;
      description "Number of times MSS was decreased";
    }
    leaf truncated-write-iov {
      xr:xr-xml-map "tcp_types:TruncatedWriteIOV";
      type uint32;
      description
        "Segments truncated due to insufficient Write I/O
        vectors";
    }
    leaf no-throttle {
      xr:xr-xml-map "tcp_types:NoThrottle";
      type uint32;
      description "Number of times throttle mode was off";
    }
    leaf low-water-mark-throttle {
      xr:xr-xml-map "tcp_types:LowWaterMarkThrottle";
      type uint32;
      description "Number of times low water mark throttle was on";
    }
    leaf high-water-mark-throttle {
      xr:xr-xml-map "tcp_types:HighWaterMarkThrottle";
      type uint32;
      description "Number of times high water mark throttle was on";
    }
    leaf stalled-timer-tickle-count {
      xr:xr-xml-map "tcp_types:StalledTimerTickleCount";
      type uint32;
      description "Number of times a stalled tcp timer was tickled";
    }
    leaf stalled-timer-tickle-time {
      xr:xr-xml-map "tcp_types:StalledTimerTickleTime";
      type uint32;
      description
        "Last timestamp when a stalled tcp timer was
        tickled";
    }
    leaf iq-sock-writes {
      xr:xr-xml-map "tcp_types:IQSockWrites";
      type uint32;
      description
        "Number of write attempts from socket-lib into an
        IQ";
    }
    leaf iq-sock-retries {
      xr:xr-xml-map "tcp_types:IQSockRetries";
      type uint32;
      description "Number of retried write attempts";
    }
    leaf iq-sock-aborts {
      xr:xr-xml-map "tcp_types:IQSockAborts";
      type uint32;
      description "Number of aborted socket-lib writes";
    }
  }

  grouping TCP-ASYNC-SESSION-STATS-BAG {
    description "TCP Async Session Statistic";
    leaf async-session {
      xr:xr-xml-map "tcp_types:AsyncSession";
      type boolean;
      description "Flag of async session";
    }
    leaf-list data-write-success-num {
      xr:xr-xml-map "tcp_types:DataWriteSuccessNum";
      type uint32;
      max-elements "2";
      description "Number of successful data write to XIPC";
    }
    leaf-list data-read-success-num {
      xr:xr-xml-map "tcp_types:DataReadSuccessNum";
      type uint32;
      max-elements "2";
      description "Number of successful data read from XIPC";
    }
    leaf-list data-write-error-num {
      xr:xr-xml-map "tcp_types:DataWriteErrorNum";
      type uint32;
      max-elements "2";
      description "Number of failed data write to XIPC";
    }
    leaf-list data-read-error-num {
      xr:xr-xml-map "tcp_types:DataReadErrorNum";
      type uint32;
      max-elements "2";
      description "Number of failed data read from XIPC";
    }
    leaf-list control-write-success-num {
      xr:xr-xml-map "tcp_types:ControlWriteSuccessNum";
      type uint32;
      max-elements "5";
      description "Number of successful control write to XIPC";
    }
    leaf-list control-read-success-num {
      xr:xr-xml-map "tcp_types:ControlReadSuccessNum";
      type uint32;
      max-elements "5";
      description "Number of successful control read to XIPC";
    }
    leaf-list control-write-error-num {
      xr:xr-xml-map "tcp_types:ControlWriteErrorNum";
      type uint32;
      max-elements "5";
      description "Number of failed control write to XIPC";
    }
    leaf-list control-read-error-num {
      xr:xr-xml-map "tcp_types:ControlReadErrorNum";
      type uint32;
      max-elements "5";
      description "Number of failed control read from XIPC";
    }
    leaf-list data-write-byte {
      xr:xr-xml-map "tcp_types:DataWriteBytes";
      type uint64;
      units "byte";
      max-elements "2";
      description "Number of bytes data has been written";
    }
    leaf-list data-read-byte {
      xr:xr-xml-map "tcp_types:DataReadBytes";
      type uint64;
      units "byte";
      max-elements "2";
      description "Number of bytes data has been read";
    }
  }

  grouping TCP-IO-COUNTS-BAG {
    description "Counts of I/O events";
    leaf io-count {
      xr:xr-xml-map "tcp_types:IOCount";
      type uint32;
      description "Number of I/O operations done by application";
    }
    leaf arm-count {
      xr:xr-xml-map "tcp_types:ArmCount";
      type uint32;
      description "How many times socket was armed by application";
    }
    leaf unarm-count {
      xr:xr-xml-map "tcp_types:UnarmCount";
      type uint32;
      description
        "How many times socket was unarmed by application";
    }
    leaf autoarm-count {
      xr:xr-xml-map "tcp_types:AutoarmCount";
      type uint32;
      description "How many times socket was auto-armed by TCP";
    }
  }

  grouping TCP-SH-PCB-STATS-BAG {
    description "TCP PCB Statistics";

    container read-io-counts {
      description "Read  I/O counts";
      uses TCP-IO-COUNTS-BAG;
    }

    container write-io-counts {
      description "Write I/O counts";
      uses TCP-IO-COUNTS-BAG;
    }

    container async-session-stats {
      description "Statistics of Async TCP Sessions";
      uses TCP-ASYNC-SESSION-STATS-BAG;
    }
    leaf pcb {
      xr:xr-xml-map "tcp_types:PCB";
      type uint64;
      description "PCB Address";
    }
    leaf vrf-id {
      xr:xr-xml-map "tcp_types:VRF_ID";
      type uint32;
      description "VRF Id";
    }
    leaf packets-sent {
      xr:xr-xml-map "tcp_types:PacketsSent";
      type uint64;
      description "Packets received from application";
    }
    leaf xipc-pulse-received {
      xr:xr-xml-map "tcp_types:XIPCPulseReceived";
      type uint64;
      description "XIPC pulses received from application";
    }
    leaf segment-instruction-received {
      xr:xr-xml-map "tcp_types:SegmentInstructionReceived";
      type uint32;
      description "Segment Instruction received from partner node";
    }
    leaf send-packets-queued {
      xr:xr-xml-map "tcp_types:SendPacketsQueued";
      type uint64;
      description "Packets queued to v4/v6 IO";
    }
    leaf send-packets-queued-net-io {
      xr:xr-xml-map "tcp_types:SendPacketsQueuedNetIO";
      type uint64;
      description "Packets queued to NetIO";
    }
    leaf send-queue-failed {
      xr:xr-xml-map "tcp_types:SendQueueFailed";
      type uint32;
      description "Packets failed to be queued to v4/v6 IO";
    }
    leaf send-queue-net-io-failed {
      xr:xr-xml-map "tcp_types:SendQueueNetIOFailed";
      type uint32;
      description "Packets failed to be queued to NetIO";
    }
    leaf packets-received {
      xr:xr-xml-map "tcp_types:PacketsReceived";
      type uint64;
      description "Packets received from network";
    }
    leaf receive-queue-failed {
      xr:xr-xml-map "tcp_types:ReceiveQueueFailed";
      type uint32;
      description
        "Received packets failed to be queued to
        application";
    }
    leaf received-packets-queued {
      xr:xr-xml-map "tcp_types:ReceivedPacketsQueued";
      type uint64;
      description "Received packets queued to application";
    }
    leaf send-window-shrink-ignored {
      xr:xr-xml-map "tcp_types:SendWindowShrinkIgnored";
      type uint32;
      description
        "No. of times send window shrinkage by peer was
        ignored";
    }
    leaf is-paw-socket {
      xr:xr-xml-map "tcp_types:IsPAWSocket";
      type boolean;
      description "PAW or non-PAW socket?";
    }
    leaf read-io-time {
      xr:xr-xml-map "tcp_types:ReadIoTime";
      type uint32;
      description "Time at which receive buffer was last read from";
    }
    leaf write-io-time {
      xr:xr-xml-map "tcp_types:WriteIoTime";
      type uint32;
      description "Time at which send buffer was last written to";
    }
  }
}
