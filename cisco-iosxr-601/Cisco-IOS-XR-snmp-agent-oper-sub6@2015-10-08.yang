submodule Cisco-IOS-XR-snmp-agent-oper-sub6 {

  belongs-to Cisco-IOS-XR-snmp-agent-oper {
    prefix Cisco-IOS-XR-snmp-agent-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2015 by Cisco Systems, Inc.
     All rights reserved.";

  revision "2015-10-08" {
    description
      "IOS XR 5.3.2 revision.";
  }

  revision "2015-01-07" {
    description
      "IOS XR 5.3.1 revision.";
  }


  grouping SNMP-TRAP-STATS {
    description "SNMP Trap statistics";
    leaf number-of-pkts-in-trap-q {
      xr:xr-xml-map "udpsnmp:NumberOfPktsInTrapQ";
      type uint32;
      description "No. of trap packets in trapQ";
    }
    leaf max-q-length-of-trap-q {
      xr:xr-xml-map "udpsnmp:MaxQLengthOfTrapQ";
      type uint32;
      description "Maximum Queue length of trapQ";
    }
    leaf number-of-pkts-sent {
      xr:xr-xml-map "udpsnmp:NumberOfPktsSent";
      type uint32;
      description "No. of trap packets sent";
    }
    leaf number-of-pkts-dropped {
      xr:xr-xml-map "udpsnmp:NumberOfPktsDropped";
      type uint32;
      description "No. of trap packets dropped";
    }
  }
}
