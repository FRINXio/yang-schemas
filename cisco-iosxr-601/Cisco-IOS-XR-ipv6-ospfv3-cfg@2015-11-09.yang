module Cisco-IOS-XR-ipv6-ospfv3-cfg {

  /*** NAMESPACE / PREFIX DEFINITION ***/

  namespace "http://cisco.com/ns/yang/Cisco-IOS-XR-ipv6-ospfv3-cfg";


  prefix "ipv6-ospfv3-cfg";

  /*** LINKAGE (IMPORTS / INCLUDES) ***/

  import ietf-inet-types { prefix "inet"; }

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-ospfv3 package configuration.

     This module contains definitions
     for the following management objects:
       ospfv3: OSPFv3 configuration

     This YANG module augments the
       Cisco-IOS-XR-snmp-agent-cfg
     module with configuration data.

     Copyright (c) 2013-2015 by Cisco Systems, Inc.
     All rights reserved.";

  revision "2015-11-09" {
    description
      "IOS XR 6.0 revision.";
  }

  typedef Trace-buf-size {
    type enumeration {
      enum disable {
        value 0;
        description "Disable trace";
      }
      enum one {
        value 256;
        description "trace buffer size 256";
      }
      enum two {
        value 512;
        description "trace buffer size 512";
      }
      enum three {
        value 1024;
        description "trace buffer size 1024";
      }
      enum four {
        value 2048;
        description "trace buffer size 2048";
      }
      enum five {
        value 4096;
        description "trace buffer size 4096";
      }
      enum six {
        value 8192;
        description "trace buffer size 8192";
      }
      enum seven {
        value 16384;
        description "trace buffer size 16384";
      }
      enum eight {
        value 32768;
        description "trace buffer size 32768";
      }
      enum nine {
        value 65536;
        description "trace buffer size 65536";
      }
    }
    description "Trace buf size";
  }
  typedef Ospfv3-protocol {
    type enumeration {
      enum all {
        value 0;
        description "All";
      }
      enum connected {
        value 1;
        description "Connected";
      }
      enum static {
        value 3;
        description "Static";
      }
      enum bgp {
        value 4;
        description "BGP";
      }
      enum isis {
        value 6;
        description "ISIS";
      }
      enum ospfv3 {
        value 7;
        description "OSPFv3";
      }
      enum eigrp {
        value 8;
        description "EIGRP";
      }
    }
    description "Ospfv3 protocol";
  }
  typedef Ospfv3-fast-reroute-tiebreakers {
    type enumeration {
      enum downstream {
        value 0;
        description "Downstream";
      }
      enum line-card-disjoint {
        value 1;
        description "LC Disjoint";
      }
      enum lowest-metric {
        value 2;
        description "Lowest metric";
      }
      enum node-protect {
        value 3;
        description "Node protection";
      }
      enum primary-path {
        value 4;
        description "Primary path";
      }
      enum secondary-path {
        value 5;
        description "Secondar path";
      }
      enum srlg-disjoint {
        value 6;
        description "SRLG";
      }
    }
    description "Ospfv3 fast reroute tiebreakers";
  }
  typedef Ospfv3isis-route {
    type enumeration {
      enum level1 {
        value 64;
        description "IS-IS level-1 routes";
      }
      enum level2 {
        value 128;
        description "IS-IS level-2 routes";
      }
      enum level1-and2 {
        value 192;
        description "IS-IS level-1 and level-2 routes";
      }
    }
    description "Ospfv3isis route";
  }
  typedef Ospfv3bfd-enable-mode {
    type enumeration {
      enum disable {
        value 0;
        description "Disable Mode - Prevent inheritance";
      }
      enum default {
        value 1;
        description "Default Mode - Default BFD behavior";
      }
      enum strict {
        value 2;
        description
          "Strict Mode - Hold down adj until BFD sesion up";
      }
    }
    description "Ospfv3bfd enable mode";
  }
  typedef Ospfv3-log-adj {
    type enumeration {
      enum suppress {
        value 0;
        description "No output";
      }
      enum brief {
        value 1;
        description "Limited output";
      }
      enum detail {
        value 2;
        description "Verbose output";
      }
    }
    description "Ospfv3 log adj";
  }
  typedef Ospfv3-protocol-type2 {
    type enumeration {
      enum connected {
        value 1;
        description "Connected";
      }
      enum static {
        value 3;
        description "Static";
      }
      enum bgp {
        value 4;
        description "BGP";
      }
      enum isis {
        value 6;
        description "ISIS";
      }
      enum ospfv3 {
        value 7;
        description "OSPFv3";
      }
      enum eigrp {
        value 8;
        description "EIGRP";
      }
      enum subscriber {
        value 9;
        description "Subscriber";
      }
      enum application {
        value 10;
        description "Application";
      }
      enum mobile {
        value 11;
        description "Mobile";
      }
    }
    description "Ospfv3 protocol type2";
  }
  typedef Ospfv3-metric {
    type enumeration {
      enum type1 {
        value 1;
        description "OSPFv3 external type 1 metrics";
      }
      enum type2 {
        value 2;
        description "OSPFv3 external type 2 metrics";
      }
    }
    description "Ospfv3 metric";
  }
  typedef Ospfv3-external-route {
    type enumeration {
      enum external1 {
        value 8;
        description "External type 1 routes";
      }
      enum external2 {
        value 16;
        description "External type 2 routes";
      }
      enum external {
        value 24;
        description "External (type 1 and 2) routes";
      }
    }
    description "Ospfv3 external route";
  }
  typedef Ospfv3-subsequent-address-family {
    type enumeration {
      enum unicast {
        value 1;
        description "Unicast subsequent address family";
      }
    }
    description "Ospfv3 subsequent address family";
  }
  typedef Ospfv3-internal-route {
    type enumeration {
      enum internal {
        value 6;
        description "OSPFv3 internal routes";
      }
    }
    description "Ospfv3 internal route";
  }
  typedef Ospfv3-fast-reroute {
    type enumeration {
      enum none {
        value 0;
        description "Disable";
      }
      enum per-link {
        value 1;
        description "Per link";
      }
      enum per-prefix {
        value 2;
        description "Per prefix";
      }
    }
    description "Ospfv3 fast reroute";
  }
  typedef Ospfv3-domain-id {
    type enumeration {
      enum type0005 {
        value 5;
        description "Type 0x0005";
      }
      enum type0105 {
        value 261;
        description "Type 0x0105";
      }
      enum type0205 {
        value 517;
        description "Type 0x0205";
      }
      enum type8005 {
        value 32773;
        description "Type 0x8005";
      }
    }
    description "Ospfv3 domain id";
  }
  typedef Ospfv3-authentication-type2 {
    type enumeration {
      enum null {
        value 0;
        description "NULL authentication";
      }
      enum md5 {
        value 1;
        description "MD5 algorithm";
      }
      enum sha1 {
        value 2;
        description "SHA1 algorithm";
      }
    }
    description "Ospfv3 authentication type2";
  }
  typedef Ospfv3-address-family {
    type enumeration {
      enum ipv6 {
        value 1;
        description "IPv6 address family";
      }
    }
    description "Ospfv3 address family";
  }
  typedef Ospfv3-authentication {
    type enumeration {
      enum md5 {
        value 1;
        description "MD5 algorithm";
      }
      enum sha1 {
        value 2;
        description "SHA1 algorithm";
      }
    }
    description "Ospfv3 authentication";
  }
  typedef Ospfv3-encryption-algorithm {
    type enumeration {
      enum null {
        value 0;
        description "Use NULL encryption";
      }
      enum des {
        value 1;
        description "Use the DES algorithm";
      }
      enum 3des {
        value 2;
        description "Use the triple DES algorithm";
      }
      enum aes {
        value 3;
        description "Use the AES algorithm";
      }
      enum aes192 {
        value 4;
        description "Use the 192-bit AES algorithm";
      }
      enum aes256 {
        value 5;
        description "Use the 256-bit AES algorithm";
      }
    }
    description "Ospfv3 encryption algorithm";
  }
  typedef Ospfv3nsr {
    type enumeration {
      enum true {
        value 1;
        description "Enable non-stop routing";
      }
      enum false {
        value 2;
        description "Disable non-stop routing";
      }
    }
    description "Ospfv3nsr";
  }
  typedef Ospfv3nssa-external-route {
    type enumeration {
      enum external1 {
        value 4096;
        description "NSSA external type 1 routes";
      }
      enum external2 {
        value 8192;
        description "NSSA external type 2 routes";
      }
      enum external {
        value 12288;
        description "NSSA external (type 1 and 2) routes";
      }
    }
    description "Ospfv3nssa external route";
  }
  typedef Ospfv3-eigrp-route {
    type enumeration {
      enum internal {
        value 16384;
        description "EIGRP internal routes";
      }
      enum external {
        value 32768;
        description "EIGRP external routes";
      }
    }
    description "Ospfv3 eigrp route";
  }
  typedef Ospfv3-fast-reroute-priority {
    type enumeration {
      enum critical {
        value 0;
        description "Critical";
      }
      enum high {
        value 1;
        description "High";
      }
      enum medium {
        value 2;
        description "Medium";
      }
      enum low {
        value 3;
        description "Low";
      }
    }
    description "Ospfv3 fast reroute priority";
  }
  typedef Ospfv3-network {
    type enumeration {
      enum broadcast {
        value 1;
        description "Broadcast multi-access network";
      }
      enum non-broadcast {
        value 2;
        description "Non-broadcast multi-access network";
      }
      enum point-to-point {
        value 3;
        description "Point-to-point network";
      }
      enum point-to-multipoint {
        value 4;
        description "Point-to-multipoint network";
      }
      enum non-broadcast-point-to-multipoint {
        value 5;
        description "Non-broadcast point-to-multipoint network";
      }
    }
    description "Ospfv3 network";
  }

  grouping REDISTRIBUTE-TABLE {
    description "Common node of default-vrf, vrf";

    container redistributes {
      xr:xr-xml-map "ipv6_ospfv3_cfg:RedistributeTable";
      description
        "Redistribute information from another routing
        protocol";

      list redistribute {
        xr:xr-xml-map "ipv6_ospfv3_cfg:Redistribute";
        must "connected-or-static-or-subscriber-or-mobile or bgp or"+
          " ospfv3-or-isis-or-application or eigrp" {
          description
            "Connected-or-Static-or-Subscriber-or-Mobile or
            BGP or OSPFv3-or-ISIS-or-Application or EIGRP
            must be present.";
        }
        key "protocol-name";
        description
          "Redistribute information from another routing
          protocol";

        grouping REDISTRIBUTE-CONTENT {
          description "REDISTRIBUTE CONTENT";
          leaf internal-route-type {
            xr:xr-xml-map "ipv6_ospfv3_cfg:InternalRouteType";
            type Ospfv3-internal-route;
            description "Redistribute OSPFv3 routes";
          }
          leaf default-metric {
            xr:xr-xml-map "ipv6_ospfv3_cfg:DefaultMetric";
            type uint32 {
              range "0..16777214";
            }
            description "OSPFv3 default metric";
          }
          leaf metric-type {
            xr:xr-xml-map "ipv6_ospfv3_cfg:MetricType";
            type Ospfv3-metric;
            description
              "OSPFv3 exterior metric type for redistributed
              routes";
          }
          leaf tag {
            xr:xr-xml-map "ipv6_ospfv3_cfg:Tag";
            type int32;
            description "Tag for routes redistributed into OSPFv3";
          }
          leaf route-policy-name {
            xr:xr-xml-map "ipv6_ospfv3_cfg:RoutePolicyName";
            type string;
            description "Route policy to redistribution";
          }
          leaf external-route-type {
            xr:xr-xml-map "ipv6_ospfv3_cfg:ExternalRouteType";
            type Ospfv3-external-route;
            description "Redistribute OSPFv3 external routes";
          }
          leaf nssa-external-route-type {
            xr:xr-xml-map "ipv6_ospfv3_cfg:NSSAExternalRouteType";
            type Ospfv3nssa-external-route;
            description "Redistribute OSPFv3 NSSA external routes";
          }
          leaf redistribute-route {
            xr:xr-xml-map "ipv6_ospfv3_cfg:RedistributeRoute";
            type boolean;
            description "Redistribution of OSPFv3 routes";
          }
          leaf isis-route-type {
            xr:xr-xml-map "ipv6_ospfv3_cfg:ISISRouteType";
            type Ospfv3isis-route;
            description "ISIS route type";
          }
          leaf eigrp-route-type {
            xr:xr-xml-map "ipv6_ospfv3_cfg:EIGRPRouteType";
            type Ospfv3-eigrp-route;
            description "EIGRP route type";
          }
          leaf preserve-med {
            xr:xr-xml-map "ipv6_ospfv3_cfg:PreserveMED";
            type empty;
            description
              "Preserve (Multi-Exit Discriminator) of BGP
              routes";
          }
          leaf preserve-med-info {
            xr:xr-xml-map "ipv6_ospfv3_cfg:PreserveMEDInfo";
            type empty;
            description
              "Preserve Information (Multi-Exit
              Discriminator) of BGP routes";
          }
        }

        container connected-or-static-or-subscriber-or-mobile {
          xr:xr-cli-map "(ipv6 router ospf)|(router (ospfv3)|(ospf6"+
            ")) <string> vrf <string> redistribute (connected [metr"+
            "ic <number>|metric-type <enum>|tag <number>|(policy (<"+
            "string>)|(<text>))|(route-policy (<string>)|(<text>))]"+
            ")|(static [metric <number>|metric-type <enum>|tag <num"+
            "ber>|(policy (<string>)|(<text>))|(route-policy (<stri"+
            "ng>)|(<text>))])|(subscriber [metric <number>|metric-t"+
            "ype <enum>|tag <number>|(policy (<string>)|(<text>))|("+
            "route-policy (<string>)|(<text>))])|(mobile [metric <n"+
            "umber>|metric-type <enum>|tag <number>|(policy (<strin"+
            "g>)|(<text>))|(route-policy (<string>)|(<text>))])|(ap"+
            "plication <string> [metric <number>|metric-type <enum>"+
            "|tag <number>|(policy (<string>)|(<text>))|(route-poli"+
            "cy (<string>)|(<text>))])|(bgp (<number>)|(<number>)|("+
            "<number> <number>) [preserve-med|preserve-bgp-default-"+
            "info|metric <number>|metric-type <enum>|tag <number>|("+
            "policy (<string>)|(<text>))|(route-policy (<string>)|("+
            "<text>))])|(eigrp <number> [match (internal)|(external"+
            ")|metric <number>|metric-type <enum>|tag <number>|(pol"+
            "icy (<string>)|(<text>))|(route-policy (<string>)|(<te"+
            "xt>))])|(isis <string> [[level-1]|level-1-2|level-2|me"+
            "tric <number>|metric-type <enum>|tag <number>|(policy "+
            "(<string>)|(<text>))|(route-policy (<string>)|(<text>)"+
            ")])|(ospfv3 <string> [match (internal)|((external (1)|"+
            "(2))|(external))|((nssa-external (1)|(2))|(nssa-extern"+
            "al))|metric <number>|metric-type <enum>|tag <number>|("+
            "policy (<string>)|(<text>))|(route-policy (<string>)|("+
            "<text>))])|((ipv6 router ospf)|(router (ospfv3)|(ospf6"+
            ")) <string> vrf <string> maximum-prefix <number> [<num"+
            "ber>|warning-only]) ";
          when "../protocol-name = 'connected' or"+
            " ../protocol-name = 'static' or ../protocol-name ="+
            " 'subscriber' or ../protocol-name = 'mobile'" {
              description
                "../ProtocolName = Connected or .
                ./ProtocolName = Static or ../ProtocolName =
                Subscriber or ../ProtocolName = Mobile";
          }
          presence "Indicates that this node is configured.";
          description "connected or static or subscriber or mobile";
          uses REDISTRIBUTE-CONTENT;
        }
        leaf protocol-name {
          xr:xr-xml-map "ipv6_ospfv3_cfg:ProtocolName";
          type Ospfv3-protocol-type2;
          description "Protocol";
        }

        list bgp {
          xr:xr-cli-map "(ipv6 router ospf)|(router (ospfv3)|(ospf6"+
            ")) <string> vrf <string> redistribute (connected [metr"+
            "ic <number>|metric-type <enum>|tag <number>|(policy (<"+
            "string>)|(<text>))|(route-policy (<string>)|(<text>))]"+
            ")|(static [metric <number>|metric-type <enum>|tag <num"+
            "ber>|(policy (<string>)|(<text>))|(route-policy (<stri"+
            "ng>)|(<text>))])|(subscriber [metric <number>|metric-t"+
            "ype <enum>|tag <number>|(policy (<string>)|(<text>))|("+
            "route-policy (<string>)|(<text>))])|(mobile [metric <n"+
            "umber>|metric-type <enum>|tag <number>|(policy (<strin"+
            "g>)|(<text>))|(route-policy (<string>)|(<text>))])|(ap"+
            "plication <string> [metric <number>|metric-type <enum>"+
            "|tag <number>|(policy (<string>)|(<text>))|(route-poli"+
            "cy (<string>)|(<text>))])|(bgp (<number>)|(<number>)|("+
            "<number> <number>) [preserve-med|preserve-bgp-default-"+
            "info|metric <number>|metric-type <enum>|tag <number>|("+
            "policy (<string>)|(<text>))|(route-policy (<string>)|("+
            "<text>))])|(eigrp <number> [match (internal)|(external"+
            ")|metric <number>|metric-type <enum>|tag <number>|(pol"+
            "icy (<string>)|(<text>))|(route-policy (<string>)|(<te"+
            "xt>))])|(isis <string> [[level-1]|level-1-2|level-2|me"+
            "tric <number>|metric-type <enum>|tag <number>|(policy "+
            "(<string>)|(<text>))|(route-policy (<string>)|(<text>)"+
            ")])|(ospfv3 <string> [match (internal)|((external (1)|"+
            "(2))|(external))|((nssa-external (1)|(2))|(nssa-extern"+
            "al))|metric <number>|metric-type <enum>|tag <number>|("+
            "policy (<string>)|(<text>))|(route-policy (<string>)|("+
            "<text>))])|((ipv6 router ospf)|(router (ospfv3)|(ospf6"+
            ")) <string> vrf <string> maximum-prefix <number> [<num"+
            "ber>|warning-only]) ";
          when "../protocol-name = 'bgp'" {
            description "../ProtocolName = BGP";
          }
          key "as-xx as-yy";
          description "bgp";
          leaf as-xx {
            xr:xr-xml-map "ipv6_ospfv3_cfg:AS_XX";
            type uint32 {
              range "0..65535";
            }
            description
              "4-byte AS number in asdot (X.Y) format -
              first half (X)";
          }
          leaf as-yy {
            xr:xr-xml-map "ipv6_ospfv3_cfg:AS_YY";
            type uint32 {
              range "0..4294967295";
            }
            description
              "4-byte AS number in asdot (X.Y) format -
              second half (Y), or 2-byte AS number, or
              4-byte AS number in asplain format";
          }
          uses REDISTRIBUTE-CONTENT;
        }

        list ospfv3-or-isis-or-application {
          xr:xr-cli-map "(ipv6 router ospf)|(router (ospfv3)|(ospf6"+
            ")) <string> vrf <string> redistribute (connected [metr"+
            "ic <number>|metric-type <enum>|tag <number>|(policy (<"+
            "string>)|(<text>))|(route-policy (<string>)|(<text>))]"+
            ")|(static [metric <number>|metric-type <enum>|tag <num"+
            "ber>|(policy (<string>)|(<text>))|(route-policy (<stri"+
            "ng>)|(<text>))])|(subscriber [metric <number>|metric-t"+
            "ype <enum>|tag <number>|(policy (<string>)|(<text>))|("+
            "route-policy (<string>)|(<text>))])|(mobile [metric <n"+
            "umber>|metric-type <enum>|tag <number>|(policy (<strin"+
            "g>)|(<text>))|(route-policy (<string>)|(<text>))])|(ap"+
            "plication <string> [metric <number>|metric-type <enum>"+
            "|tag <number>|(policy (<string>)|(<text>))|(route-poli"+
            "cy (<string>)|(<text>))])|(bgp (<number>)|(<number>)|("+
            "<number> <number>) [preserve-med|preserve-bgp-default-"+
            "info|metric <number>|metric-type <enum>|tag <number>|("+
            "policy (<string>)|(<text>))|(route-policy (<string>)|("+
            "<text>))])|(eigrp <number> [match (internal)|(external"+
            ")|metric <number>|metric-type <enum>|tag <number>|(pol"+
            "icy (<string>)|(<text>))|(route-policy (<string>)|(<te"+
            "xt>))])|(isis <string> [[level-1]|level-1-2|level-2|me"+
            "tric <number>|metric-type <enum>|tag <number>|(policy "+
            "(<string>)|(<text>))|(route-policy (<string>)|(<text>)"+
            ")])|(ospfv3 <string> [match (internal)|((external (1)|"+
            "(2))|(external))|((nssa-external (1)|(2))|(nssa-extern"+
            "al))|metric <number>|metric-type <enum>|tag <number>|("+
            "policy (<string>)|(<text>))|(route-policy (<string>)|("+
            "<text>))])|((ipv6 router ospf)|(router (ospfv3)|(ospf6"+
            ")) <string> vrf <string> maximum-prefix <number> [<num"+
            "ber>|warning-only]) ";
          when "../protocol-name = 'ospfv3' or ../protocol-name ="+
            " 'isis' or ../protocol-name = 'application'" {
              description
                "../ProtocolName = OSPFv3 or ../ProtocolName
                = ISIS or ../ProtocolName = Application";
          }
          key "process-name";
          description "ospfv3 or isis or application";
          leaf process-name {
            xr:xr-xml-map "ipv6_ospfv3_cfg:ProcessName";
            type xr:Cisco-ios-xr-string;
            description
              "ISIS process name if protocol is ISIS, or
              OSPFv3 process name if protocol is OSPFv3";
          }
          uses REDISTRIBUTE-CONTENT;
        }

        list eigrp {
          xr:xr-cli-map "(ipv6 router ospf)|(router (ospfv3)|(ospf6"+
            ")) <string> vrf <string> redistribute (connected [metr"+
            "ic <number>|metric-type <enum>|tag <number>|(policy (<"+
            "string>)|(<text>))|(route-policy (<string>)|(<text>))]"+
            ")|(static [metric <number>|metric-type <enum>|tag <num"+
            "ber>|(policy (<string>)|(<text>))|(route-policy (<stri"+
            "ng>)|(<text>))])|(subscriber [metric <number>|metric-t"+
            "ype <enum>|tag <number>|(policy (<string>)|(<text>))|("+
            "route-policy (<string>)|(<text>))])|(mobile [metric <n"+
            "umber>|metric-type <enum>|tag <number>|(policy (<strin"+
            "g>)|(<text>))|(route-policy (<string>)|(<text>))])|(ap"+
            "plication <string> [metric <number>|metric-type <enum>"+
            "|tag <number>|(policy (<string>)|(<text>))|(route-poli"+
            "cy (<string>)|(<text>))])|(bgp (<number>)|(<number>)|("+
            "<number> <number>) [preserve-med|preserve-bgp-default-"+
            "info|metric <number>|metric-type <enum>|tag <number>|("+
            "policy (<string>)|(<text>))|(route-policy (<string>)|("+
            "<text>))])|(eigrp <number> [match (internal)|(external"+
            ")|metric <number>|metric-type <enum>|tag <number>|(pol"+
            "icy (<string>)|(<text>))|(route-policy (<string>)|(<te"+
            "xt>))])|(isis <string> [[level-1]|level-1-2|level-2|me"+
            "tric <number>|metric-type <enum>|tag <number>|(policy "+
            "(<string>)|(<text>))|(route-policy (<string>)|(<text>)"+
            ")])|(ospfv3 <string> [match (internal)|((external (1)|"+
            "(2))|(external))|((nssa-external (1)|(2))|(nssa-extern"+
            "al))|metric <number>|metric-type <enum>|tag <number>|("+
            "policy (<string>)|(<text>))|(route-policy (<string>)|("+
            "<text>))])|((ipv6 router ospf)|(router (ospfv3)|(ospf6"+
            ")) <string> vrf <string> maximum-prefix <number> [<num"+
            "ber>|warning-only]) ";
          when "../protocol-name = 'eigrp'" {
            description "../ProtocolName = EIGRP";
          }
          key "as-xx";
          description "eigrp";
          leaf as-xx {
            xr:xr-xml-map "ipv6_ospfv3_cfg:AS_XX";
            type uint32 {
              range "0..65535";
            }
            description
              "4-byte AS number in asdot (X.Y) format -
              first half (X)";
          }
          uses REDISTRIBUTE-CONTENT;
        }
      }
    }
  }

  grouping DISTANCE {
    description "Common node of default-vrf, vrf";

    container distance {
      xr:xr-xml-map "ipv6_ospfv3_cfg:Distance";
      description "Define an administrative distance";

      container ospfv3 {
        xr:xr-xml-map "ipv6_ospfv3_cfg:OSPFv3";
        description "OSPFv3 administrative distance";
        leaf intra-area {
          xr:xr-xml-map "ipv6_ospfv3_cfg:IntraArea";
          type uint32 {
            range "1..255";
          }
          description "Distance for intra-area routes";
        }
        leaf inter-area {
          xr:xr-xml-map "ipv6_ospfv3_cfg:InterArea";
          type uint32 {
            range "1..255";
          }
          description "Distance for inter-area routes";
        }
        leaf external {
          xr:xr-xml-map "ipv6_ospfv3_cfg:External";
          type uint32 {
            range "1..255";
          }
          description
            "Distance for external type 5 and type 7 routes";
        }
      }
      leaf administrative {
        xr:xr-xml-map "ipv6_ospfv3_cfg:Administrative";
        xr:xr-cli-map "(ipv6 router ospf)|(router (ospfv3)|(ospf6))"+
          " <string> vrf <string> distance <number> ";
        type uint32 {
          range "1..255";
        }
        description "Define an administrative distance";
      }
    }
  }

  grouping DEMAND-CIRCUIT {
    description "Common node of default-vrf, vrf";
    leaf demand-circuit {
      xr:xr-xml-map "ipv6_ospfv3_cfg:DemandCircuit";
      xr:xr-cli-map "(ipv6 router ospf)|(router (ospfv3)|(ospf6)) <"+
        "string> vrf <string> demand-circuit enable ";
      type boolean;
      description "Enable/disable demand circuit operation";
    }
  }

  grouping ON-PROC-RESTART {
    description "Common node of rbit, v6bit, max-metric";
    leaf on-proc-restart {
      xr:xr-xml-map "ipv6_ospfv3_cfg:OnProcRestart";
      type uint32 {
        range "5..86400";
      }
      units "second";
      description
        "Time (in seconds) to stay in stub router
        operational state";
    }
  }

  grouping EXCLUDE-INTERFACE-TABLE {
    description "Common node of per-link, per-prefix";

    container exclude-interfaces {
      xr:xr-xml-map "ipv6_ospfv3_intfobj_cfg:ExcludeInterfaceTable";
      description
        "Fast-reroute per-link/per-prefix exclude
        interface configuration";

      list exclude-interface {
        xr:xr-xml-map "ipv6_ospfv3_intfobj_cfg:ExcludeInterface";
        xr:xr-cli-map "(ipv6 router ospf)|(router (ospfv3)|(ospf6))"+
          " <string> vrf <string> fast-reroute per-link exclude int"+
          "erface <interface> ";
        xr:xr-cli-map "(ipv6 router ospf)|(router (ospfv3)|(ospf6))"+
          " <string> vrf <string> fast-reroute per-prefix exclude i"+
          "nterface <interface> ";
        key "interface-name";
        description "Exclude an interface from becoming a backup";
        leaf interface-name {
          xr:xr-xml-map "ipv6_ospfv3_intfobj_cfg:InterfaceName";
          type xr:Interface-name;
          description "Interface";
        }
      }
    }
  }

  grouping TRANSMIT-DELAY {
    description "Common node of default-vrf, vrf";
    leaf transmit-delay {
      xr:xr-xml-map "ipv6_ospfv3_cfg:TransmitDelay";
      xr:xr-cli-map "(ipv6 router ospf)|(router (ospfv3)|(ospf6)) <"+
        "string> vrf <string> transmit-delay <number> ";
      type uint32 {
        range "1..65535";
      }
      units "second";
      description "Specify the transmit delay in seconds";
    }
  }

  grouping PASSIVE {
    description "Common node of default-vrf, vrf";
    leaf passive {
      xr:xr-xml-map "ipv6_ospfv3_cfg:Passive";
      xr:xr-cli-map "(ipv6 router ospf)|(router (ospfv3)|(ospf6)) <"+
        "string> vrf <string> passive enable ";
      type boolean;
      description "Enable/disable routing updates on an interface";
    }
  }

  grouping ALWAYS {
    description "Common node of rbit, v6bit, max-metric";
    leaf always {
      xr:xr-xml-map "ipv6_ospfv3_cfg:Always";
      type empty;
      description
        "Unconditionally enter stub router operational
        state";
    }
  }

  grouping AREA-TABLE {
    description "Common node of default-vrf, vrf";

    container area-addresses {
      xr:xr-xml-map "ipv6_ospfv3_area_cfg:AreaTable";
      description "Area configuration";

      grouping AREA-CONTENT {
        description "AREA CONTENT";

        container authentication {
          xr:xr-xml-map "ipv6_ospfv3_area_cfg:Authentication";
          description "Authenticate OSPFv3 packets";
          leaf enable {
            xr:xr-xml-map "ipv6_ospfv3_area_cfg:Enable";
            type boolean;
            description "Authenticate packets";
          }
          leaf spi {
            xr:xr-xml-map "ipv6_ospfv3_area_cfg:SPI";
            type uint32 {
              range "256..4294967295";
            }
            description
              "Use IPSec AH authentication. Specify the
              Security Parameter Index (SPI) value";
          }
          leaf algorithm {
            xr:xr-xml-map "ipv6_ospfv3_area_cfg:Algorithm";
            type Ospfv3-authentication;
            description "Use the MD5 or SHA1 algorithm";
          }
          leaf password {
            xr:xr-xml-map "ipv6_ospfv3_area_cfg:Password";
            type xr:Proprietary-password;
            description "Specify MD5 or SHA1 password";
          }
        }

        container bfd {
          xr:xr-xml-map "ipv6_ospfv3_area_cfg:BFD";
          description "Configure BFD parameters";
          leaf detection-multiplier {
            xr:xr-xml-map "ipv6_ospfv3_area_cfg:DetectionMultiplier";
            type uint32 {
              range "2..50";
            }
            description "Detect multiplier";
          }
          leaf interval {
            xr:xr-xml-map "ipv6_ospfv3_area_cfg:Interval";
            type uint32 {
              range "3..30000";
            }
            units "millisecond";
            description "Hello interval in milli-seconds";
          }
          leaf fast-detect-mode {
            xr:xr-xml-map "ipv6_ospfv3_area_cfg:FastDetectMode";
            type Ospfv3bfd-enable-mode;
            description "Enable or disable BFD fast detection";
          }
        }

        container ranges {
          xr:xr-xml-map "ipv6_ospfv3_area_cfg:RangeTable";
          description "Range configuration";

          list range {
            xr:xr-xml-map "ipv6_ospfv3_area_cfg:Range";
            key "prefix prefix-length";
            description
              "Summarize inter-area routes matching
              prefix/length";
            leaf prefix {
              xr:xr-xml-map "ipv6_ospfv3_area_cfg:Prefix";
              type inet:ipv6-address-no-zone;
              description "IPv6 prefix format";
            }
            leaf prefix-length {
              xr:xr-xml-map "ipv6_ospfv3_area_cfg:PrefixLength";
              type xr:Ipv6-prefix-length;
              description "IPV6 prefix length";
            }
            leaf not-advertise {
              xr:xr-xml-map "ipv6_ospfv3_area_cfg:NotAdvertise";
              type boolean;
              default "false";
              description "Do not advertise address range";
            }
            leaf cost {
              xr:xr-xml-map "ipv6_ospfv3_area_cfg:Cost";
              type uint32 {
                range "1..16777214";
              }
              description "Specified metric for this range";
            }
          }
        }

        container encryption {
          xr:xr-xml-map "ipv6_ospfv3_area_cfg:Encryption";
          description "Encrypt and authenticate OSPFv3 packets";
          leaf enable {
            xr:xr-xml-map "ipv6_ospfv3_area_cfg:Enable";
            type boolean;
            description "Authenticate packets";
          }
          leaf spi {
            xr:xr-xml-map "ipv6_ospfv3_area_cfg:SPI";
            type uint32 {
              range "256..4294967295";
            }
            description
              "Use IPSec ESP authentication. Specify the
              Security Parameter Index (SPI) value";
          }
          leaf encryption-algorithm {
            xr:xr-xml-map "ipv6_ospfv3_area_cfg:EncryptionAlgorithm";
            type Ospfv3-encryption-algorithm;
            description "Specify the encryption algorithm";
          }
          leaf encryption-password {
            xr:xr-xml-map "ipv6_ospfv3_area_cfg:EncryptionPassword";
            type xr:Proprietary-password;
            description "Encryption password";
          }
          leaf authentication-algorithm {
            xr:xr-xml-map "ipv6_ospfv3_area_cfg:AuthenticationAlgor"+
              "ithm";
            type Ospfv3-authentication-type2;
            description "Use the NULL, MD5 or SHA1 algorithm";
          }
          leaf authentication-password {
            xr:xr-xml-map "ipv6_ospfv3_area_cfg:AuthenticationPassw"+
              "ord";
            type xr:Proprietary-password;
            description "Specify MD5 or SHA1 password";
          }
        }

        container nssa {
          xr:xr-xml-map "ipv6_ospfv3_area_cfg:NSSA";
          description
            "Specify area as a NSSA area.  Allowed only in
            non-backbone areas";
          leaf no-redistribution {
            xr:xr-xml-map "ipv6_ospfv3_area_cfg:NoRedistribution";
            type boolean;
            default "false";
            description "No redistribution into this NSSA area";
          }
          leaf default-info-originate {
            xr:xr-xml-map "ipv6_ospfv3_area_cfg:DefaultInfoOriginat"+
              "e";
            type boolean;
            default "false";
            description "Originate Type 7 default into NSSA area";
          }
          leaf metric {
            xr:xr-xml-map "ipv6_ospfv3_area_cfg:Metric";
            type uint32 {
              range "0..16777214";
            }
            description "Only valid with DefaultInfoOriginate";
          }
          leaf metric-type {
            xr:xr-xml-map "ipv6_ospfv3_area_cfg:MetricType";
            type Ospfv3-metric;
            description "Only valid with DefaultInfoOriginate";
          }
          leaf no-summary {
            xr:xr-xml-map "ipv6_ospfv3_area_cfg:NoSummary";
            type empty;
            description "Do not send summary LSA into NSSA";
          }
        }

        container database-filter {
          xr:xr-xml-map "ipv6_ospfv3_area_cfg:DatabaseFilter";
          description "Database filter";

          container all {
            xr:xr-xml-map "ipv6_ospfv3_area_cfg:All";
            description "All";
            leaf out {
              xr:xr-xml-map "ipv6_ospfv3_area_cfg:Out";
              type boolean;
              description "Enable or disable database-filter";
            }
          }
        }

        container distribute-list {
          xr:xr-xml-map "ipv6_ospfv3_area_cfg:DistributeList";
          description "Filter prefixes to/from RIB";

          container in {
            xr:xr-xml-map "ipv6_ospfv3_area_cfg:In";
            description "Filter prefixes installed to RIB";
            leaf prefix-list {
              xr:xr-xml-map "ipv6_ospfv3_area_cfg:PrefixList";
              type string;
              description
                "Filter prefixes based on an IPv6 prefix-list";
            }
          }
        }

        container interfaces {
          xr:xr-xml-map "ipv6_ospfv3_interface_cfg:InterfaceTable";
          description "OSPFv3 interfaces";

          list interface {
            xr:xr-xml-map "ipv6_ospfv3_interface_cfg:Interface";
            key "interface-name";
            description "OSPFv3 interface";

            container authentication {
              xr:xr-xml-map "ipv6_ospfv3_interface_cfg:Authenticati"+
                "on";
              description "Authenticate OSPFv3 packets";
              leaf enable {
                xr:xr-xml-map "ipv6_ospfv3_interface_cfg:Enable";
                type boolean;
                description "Authenticate packets";
              }
              leaf spi {
                xr:xr-xml-map "ipv6_ospfv3_interface_cfg:SPI";
                type uint32 {
                  range "256..4294967295";
                }
                description
                  "Use IPSec AH authentication. Specify the
                  Security Parameter Index (SPI) value";
              }
              leaf algorithm {
                xr:xr-xml-map "ipv6_ospfv3_interface_cfg:Algorithm";
                type Ospfv3-authentication;
                description "Use the MD5 or SHA1 algorithm";
              }
              leaf password {
                xr:xr-xml-map "ipv6_ospfv3_interface_cfg:Password";
                type xr:Proprietary-password;
                description "Specify MD5 or SHA1 password";
              }
            }

            container neighbors {
              xr:xr-xml-map "ipv6_ospfv3_interface_cfg:NeighborTabl"+
                "e";
              description "Specify a neighbor router";

              list neighbor {
                xr:xr-xml-map "ipv6_ospfv3_interface_cfg:Neighbor";
                key "neighbor-address";
                description "IPv6 address";
                leaf neighbor-address {
                  xr:xr-xml-map "ipv6_ospfv3_interface_cfg:Neighbor"+
                    "Address";
                  type xr:Cisco-ios-xr-string;
                  description "IPV6 address";
                }
                leaf priority {
                  xr:xr-xml-map "ipv6_ospfv3_interface_cfg:Priority";
                  type uint32 {
                    range "0..255";
                  }
                  description
                    "OSPFv3 priority of non-broadcast neighbor";
                }
                leaf poll-interval {
                  xr:xr-xml-map "ipv6_ospfv3_interface_cfg:PollInte"+
                    "rval";
                  type uint32 {
                    range "0..65535";
                  }
                  units "second";
                  description
                    "OSPFv3 dead-router polling interval (in
                    seconds)";
                }
                leaf cost {
                  xr:xr-xml-map "ipv6_ospfv3_interface_cfg:Cost";
                  type uint32 {
                    range "1..65535";
                  }
                  description
                    "OSPFv3 cost for point-to-multipoint
                    neighbor";
                }
                leaf database-filter {
                  xr:xr-xml-map "ipv6_ospfv3_interface_cfg:Database"+
                    "Filter";
                  type boolean;
                  description
                    "Filter OSPFv3 LSA during synchronization
                    and flooding for point-to-multipoint
                    neighbor";
                }
                leaf zone {
                  xr:xr-xml-map "ipv6_ospfv3_interface_cfg:Zone";
                  type string;
                  description "Zone";
                }
              }
            }

            container encryption {
              xr:xr-xml-map "ipv6_ospfv3_interface_cfg:Encryption";
              description "Encrypt and authenticate OSPFv3 packets";
              leaf enable {
                xr:xr-xml-map "ipv6_ospfv3_interface_cfg:Enable";
                type boolean;
                description "Authenticate packets";
              }
              leaf spi {
                xr:xr-xml-map "ipv6_ospfv3_interface_cfg:SPI";
                type uint32 {
                  range "256..4294967295";
                }
                description
                  "Use IPSec ESP authentication. Specify the
                  Security Parameter Index (SPI) value";
              }
              leaf encryption-algorithm {
                xr:xr-xml-map "ipv6_ospfv3_interface_cfg:Encryption"+
                  "Algorithm";
                type Ospfv3-encryption-algorithm;
                description "Specify the encryption algorithm";
              }
              leaf encryption-password {
                xr:xr-xml-map "ipv6_ospfv3_interface_cfg:Encryption"+
                  "Password";
                type xr:Proprietary-password;
                description "Encryption password";
              }
              leaf authentication-algorithm {
                xr:xr-xml-map "ipv6_ospfv3_interface_cfg:Authentica"+
                  "tionAlgorithm";
                type Ospfv3-authentication-type2;
                description "Use the NULL, MD5 or SHA1 algorithm";
              }
              leaf authentication-password {
                xr:xr-xml-map "ipv6_ospfv3_interface_cfg:Authentica"+
                  "tionPassword";
                type xr:Proprietary-password;
                description "Specify MD5 or SHA1 password";
              }
            }

            container bfd {
              xr:xr-xml-map "ipv6_ospfv3_interface_cfg:BFD";
              description "Configure BFD parameters";
              leaf interval {
                xr:xr-xml-map "ipv6_ospfv3_interface_cfg:Interval";
                type uint32 {
                  range "3..30000";
                }
                units "millisecond";
                description "Hello interval in milli-seconds";
              }
              leaf fast-detect-mode {
                xr:xr-xml-map "ipv6_ospfv3_interface_cfg:FastDetect"+
                  "Mode";
                type Ospfv3bfd-enable-mode;
                description "Enable or disable BFD fast detection";
              }
              leaf detection-multiplier {
                xr:xr-xml-map "ipv6_ospfv3_interface_cfg:DetectionM"+
                  "ultiplier";
                type uint32 {
                  range "2..50";
                }
                description "Detect multiplier";
              }
            }

            container database-filter {
              xr:xr-xml-map "ipv6_ospfv3_interface_cfg:DatabaseFilt"+
                "er";
              description "Database filter";

              container all {
                xr:xr-xml-map "ipv6_ospfv3_interface_cfg:All";
                description "All";
                leaf out {
                  xr:xr-xml-map "ipv6_ospfv3_interface_cfg:Out";
                  type boolean;
                  description "Enable or disable database-filter";
                }
              }
            }

            container distribute-list {
              xr:xr-xml-map "ipv6_ospfv3_interface_cfg:DistributeLi"+
                "st";
              description "Filter prefixes to/from RIB";

              container in {
                xr:xr-xml-map "ipv6_ospfv3_interface_cfg:In";
                description "Filter prefixes installed to RIB";
                leaf prefix-list {
                  xr:xr-xml-map "ipv6_ospfv3_interface_cfg:PrefixLi"+
                    "st";
                  type string;
                  description
                    "Filter prefixes based on an IPv6
                    prefix-list";
                }
              }
            }
            leaf enable {
              xr:xr-xml-map "ipv6_ospfv3_interface_cfg:Enable";
              type empty;
              description "Enable OSPFv3 interface";
            }
            leaf dead-interval {
              xr:xr-xml-map "ipv6_ospfv3_interface_cfg:DeadInterval";
              type uint32 {
                range "1..65535";
              }
              units "second";
              description
                "Interval after which a neighbor is declared
                dead (in seconds)";
            }
            leaf flood-reduction {
              xr:xr-xml-map "ipv6_ospfv3_interface_cfg:FloodReducti"+
                "on";
              type boolean;
              description "Enable/disable flood reduction";
            }
            leaf cost {
              xr:xr-xml-map "ipv6_ospfv3_interface_cfg:Cost";
              type uint32 {
                range "1..65535";
              }
              description "Interface cost";
            }
            leaf transmit-delay {
              xr:xr-xml-map "ipv6_ospfv3_interface_cfg:TransmitDela"+
                "y";
              type uint32 {
                range "1..65535";
              }
              units "second";
              description "Specify the transmit delay in seconds";
            }
            leaf instance {
              xr:xr-xml-map "ipv6_ospfv3_interface_cfg:Instance";
              type uint32 {
                range "0..255";
              }
              description "Instance ID";
            }
            leaf ldp-sync {
              xr:xr-xml-map "ipv6_ospfv3_interface_cfg:LDPSync";
              type boolean;
              description "Enable/Disable MPLS LDP sync";
            }
            leaf mtu-ignore {
              xr:xr-xml-map "ipv6_ospfv3_interface_cfg:MTUIgnore";
              type boolean;
              description
                "Enable/disable ignoring of MTU in DBD
                packets";
            }
            leaf retransmit-interval {
              xr:xr-xml-map "ipv6_ospfv3_interface_cfg:RetransmitIn"+
                "terval";
              type uint32 {
                range "1..65535";
              }
              units "second";
              description
                "Specify the transmit interval in seconds";
            }
            leaf hello-interval {
              xr:xr-xml-map "ipv6_ospfv3_interface_cfg:HelloInterva"+
                "l";
              type uint32 {
                range "1..65535";
              }
              units "second";
              description "Time between HELLO packets";
            }
            leaf passive {
              xr:xr-xml-map "ipv6_ospfv3_interface_cfg:Passive";
              type boolean;
              description
                "Enable/disable routing updates on an
                interface";
            }
            leaf packet-size {
              xr:xr-xml-map "ipv6_ospfv3_interface_cfg:PacketSize";
              type uint32 {
                range "256..10000";
              }
              description "Limit size of OSPFv3 packets";
            }
            leaf priority {
              xr:xr-xml-map "ipv6_ospfv3_interface_cfg:Priority";
              type uint32 {
                range "0..255";
              }
              description "Specify router priority";
            }
            leaf network {
              xr:xr-xml-map "ipv6_ospfv3_interface_cfg:Network";
              type Ospfv3-network;
              description "Specify network type";
            }
            leaf demand-circuit {
              xr:xr-xml-map "ipv6_ospfv3_interface_cfg:DemandCircui"+
                "t";
              type boolean;
              description "Enable/disable demand circuit operation";
            }
            leaf interface-name {
              xr:xr-xml-map "ipv6_ospfv3_interface_cfg:InterfaceNam"+
                "e";
              type xr:Interface-name;
              description "Interface to configure";
            }
            uses IPV6-OSPFV3-INTFOBJ-CFG-FAST-REROUTE;
          }
        }

        container area-scope {
          xr:xr-xml-map "ipv6_ospfv3_area_cfg:AreaScope";
          description "Area Scope Configuration";
          uses IPV6-OSPFV3-INTFOBJ-CFG-FAST-REROUTE;
        }

        container sham-links {
          xr:xr-xml-map "ipv6_ospfv3_area_cfg:ShamLinkTable";
          description "Sham Link sub-mode";

          list sham-link {
            xr:xr-xml-map "ipv6_ospfv3_area_cfg:ShamLink";
            key "source-address destination-address";
            description "ShamLink local and remote endpoints";

            container authentication {
              xr:xr-xml-map "ipv6_ospfv3_area_cfg:Authentication";
              description "Authenticate OSPFv3 packets";
              leaf enable {
                xr:xr-xml-map "ipv6_ospfv3_area_cfg:Enable";
                type boolean;
                description "Authenticate packets";
              }
              leaf spi {
                xr:xr-xml-map "ipv6_ospfv3_area_cfg:SPI";
                type uint32 {
                  range "256..4294967295";
                }
                description
                  "Use IPSec AH authentication. Specify the
                  Security Parameter Index (SPI) value";
              }
              leaf algorithm {
                xr:xr-xml-map "ipv6_ospfv3_area_cfg:Algorithm";
                type Ospfv3-authentication;
                description "Use the MD5 or SHA1 algorithm";
              }
              leaf password {
                xr:xr-xml-map "ipv6_ospfv3_area_cfg:Password";
                type xr:Proprietary-password;
                description "Specify MD5 or SHA1 password";
              }
            }

            container encryption {
              xr:xr-xml-map "ipv6_ospfv3_area_cfg:Encryption";
              description "Encrypt and authenticate OSPFv3 packets";
              leaf enable {
                xr:xr-xml-map "ipv6_ospfv3_area_cfg:Enable";
                type boolean;
                description "Authenticate packets";
              }
              leaf spi {
                xr:xr-xml-map "ipv6_ospfv3_area_cfg:SPI";
                type uint32 {
                  range "256..4294967295";
                }
                description
                  "Use IPSec ESP authentication. Specify the
                  Security Parameter Index (SPI) value";
              }
              leaf encryption-algorithm {
                xr:xr-xml-map "ipv6_ospfv3_area_cfg:EncryptionAlgor"+
                  "ithm";
                type Ospfv3-encryption-algorithm;
                description "Specify the encryption algorithm";
              }
              leaf encryption-password {
                xr:xr-xml-map "ipv6_ospfv3_area_cfg:EncryptionPassw"+
                  "ord";
                type xr:Proprietary-password;
                description "Encryption password";
              }
              leaf authentication-algorithm {
                xr:xr-xml-map "ipv6_ospfv3_area_cfg:AuthenticationA"+
                  "lgorithm";
                type Ospfv3-authentication-type2;
                description "Use the NULL, MD5 or SHA1 algorithm";
              }
              leaf authentication-password {
                xr:xr-xml-map "ipv6_ospfv3_area_cfg:AuthenticationP"+
                  "assword";
                type xr:Proprietary-password;
                description "Specify MD5 or SHA1 password";
              }
            }
            leaf enable {
              xr:xr-xml-map "ipv6_ospfv3_area_cfg:Enable";
              type empty;
              description "Enable sham link";
            }
            leaf hello-interval {
              xr:xr-xml-map "ipv6_ospfv3_area_cfg:HelloInterval";
              type uint32 {
                range "1..65535";
              }
              units "second";
              description "Time between HELLO packets";
            }
            leaf dead-interval {
              xr:xr-xml-map "ipv6_ospfv3_area_cfg:DeadInterval";
              type uint32 {
                range "1..65535";
              }
              units "second";
              description
                "Interval after which a neighbor is declared
                dead (in seconds)";
            }
            leaf retransmit-interval {
              xr:xr-xml-map "ipv6_ospfv3_area_cfg:RetransmitInterva"+
                "l";
              type uint32 {
                range "1..65535";
              }
              units "second";
              description
                "Specify the transmit interval in seconds";
            }
            leaf transmit-delay {
              xr:xr-xml-map "ipv6_ospfv3_area_cfg:TransmitDelay";
              type uint32 {
                range "1..65535";
              }
              units "second";
              description "Specify the transmit delay in seconds";
            }
            leaf source-address {
              xr:xr-xml-map "ipv6_ospfv3_area_cfg:SourceAddress";
              type inet:ipv6-address-no-zone;
              description "Local sham-link endpoint";
            }
            leaf destination-address {
              xr:xr-xml-map "ipv6_ospfv3_area_cfg:DestinationAddres"+
                "s";
              type inet:ipv6-address-no-zone;
              description "Remote sham-link endpoint";
            }
          }
        }

        container virtual-links {
          xr:xr-xml-map "ipv6_ospfv3_area_cfg:VirtualLinkTable";
          description "Virtual link sub-mode";

          list virtual-link {
            xr:xr-xml-map "ipv6_ospfv3_area_cfg:VirtualLink";
            key "virtual-link-address";
            description "Router ID of virtual link neighbor";

            container authentication {
              xr:xr-xml-map "ipv6_ospfv3_area_cfg:Authentication";
              description "Authenticate OSPFv3 packets";
              leaf enable {
                xr:xr-xml-map "ipv6_ospfv3_area_cfg:Enable";
                type boolean;
                description "Authenticate packets";
              }
              leaf spi {
                xr:xr-xml-map "ipv6_ospfv3_area_cfg:SPI";
                type uint32 {
                  range "256..4294967295";
                }
                description
                  "Use IPSec AH authentication. Specify the
                  Security Parameter Index (SPI) value";
              }
              leaf algorithm {
                xr:xr-xml-map "ipv6_ospfv3_area_cfg:Algorithm";
                type Ospfv3-authentication;
                description "Use the MD5 or SHA1 algorithm";
              }
              leaf password {
                xr:xr-xml-map "ipv6_ospfv3_area_cfg:Password";
                type xr:Proprietary-password;
                description "Specify MD5 or SHA1 password";
              }
            }

            container encryption {
              xr:xr-xml-map "ipv6_ospfv3_area_cfg:Encryption";
              description "Encrypt and authenticate OSPFv3 packets";
              leaf enable {
                xr:xr-xml-map "ipv6_ospfv3_area_cfg:Enable";
                type boolean;
                description "Authenticate packets";
              }
              leaf spi {
                xr:xr-xml-map "ipv6_ospfv3_area_cfg:SPI";
                type uint32 {
                  range "256..4294967295";
                }
                description
                  "Use IPSec ESP authentication. Specify the
                  Security Parameter Index (SPI) value";
              }
              leaf encryption-algorithm {
                xr:xr-xml-map "ipv6_ospfv3_area_cfg:EncryptionAlgor"+
                  "ithm";
                type Ospfv3-encryption-algorithm;
                description "Specify the encryption algorithm";
              }
              leaf encryption-password {
                xr:xr-xml-map "ipv6_ospfv3_area_cfg:EncryptionPassw"+
                  "ord";
                type xr:Proprietary-password;
                description "Encryption password";
              }
              leaf authentication-algorithm {
                xr:xr-xml-map "ipv6_ospfv3_area_cfg:AuthenticationA"+
                  "lgorithm";
                type Ospfv3-authentication-type2;
                description "Use the NULL, MD5 or SHA1 algorithm";
              }
              leaf authentication-password {
                xr:xr-xml-map "ipv6_ospfv3_area_cfg:AuthenticationP"+
                  "assword";
                type xr:Proprietary-password;
                description "Specify MD5 or SHA1 password";
              }
            }
            leaf enable {
              xr:xr-xml-map "ipv6_ospfv3_area_cfg:Enable";
              type empty;
              description "Enabled virtual link";
            }
            leaf hello-interval {
              xr:xr-xml-map "ipv6_ospfv3_area_cfg:HelloInterval";
              type uint32 {
                range "1..65535";
              }
              units "second";
              description "Time between HELLO packets";
            }
            leaf dead-interval {
              xr:xr-xml-map "ipv6_ospfv3_area_cfg:DeadInterval";
              type uint32 {
                range "1..65535";
              }
              units "second";
              description
                "Interval after which a neighbor is declared
                dead (in seconds)";
            }
            leaf retransmit-interval {
              xr:xr-xml-map "ipv6_ospfv3_area_cfg:RetransmitInterva"+
                "l";
              type uint32 {
                range "1..65535";
              }
              units "second";
              description
                "Specify the transmit interval in seconds";
            }
            leaf transmit-delay {
              xr:xr-xml-map "ipv6_ospfv3_area_cfg:TransmitDelay";
              type uint32 {
                range "1..65535";
              }
              units "second";
              description "Specify the transmit delay in seconds";
            }
            leaf virtual-link-address {
              xr:xr-xml-map "ipv6_ospfv3_area_cfg:VirtualLinkAddres"+
                "s";
              type inet:ipv4-address-no-zone;
              description "Router ID of virtual link neighbor";
            }
          }
        }
        leaf stub {
          xr:xr-xml-map "ipv6_ospfv3_area_cfg:Stub";
          type boolean;
          description
            "Specify area as a stub area.  Allowed only in
            non-backbone areas";
        }
        leaf packet-size {
          xr:xr-xml-map "ipv6_ospfv3_area_cfg:PacketSize";
          type uint32 {
            range "256..10000";
          }
          description "Limit size of OSPFv3 packets";
        }
        leaf instance {
          xr:xr-xml-map "ipv6_ospfv3_area_cfg:Instance";
          type uint32 {
            range "0..255";
          }
          description "Instance ID";
        }
        leaf demand-circuit {
          xr:xr-xml-map "ipv6_ospfv3_area_cfg:DemandCircuit";
          type boolean;
          description "Enable/disable demand circuit operation";
        }
        leaf priority {
          xr:xr-xml-map "ipv6_ospfv3_area_cfg:Priority";
          type uint32 {
            range "0..255";
          }
          description "Specify router priority";
        }
        leaf enable {
          xr:xr-xml-map "ipv6_ospfv3_area_cfg:Enable";
          type empty;
          description "Enable OSPFv3 area";
        }
        leaf mtu-ignore {
          xr:xr-xml-map "ipv6_ospfv3_area_cfg:MTUIgnore";
          type boolean;
          description
            "Enable/disable ignoring of MTU in DBD packets";
        }
        leaf passive {
          xr:xr-xml-map "ipv6_ospfv3_area_cfg:Passive";
          type boolean;
          description
            "Enable/disable routing updates on an interface";
        }
        leaf hello-interval {
          xr:xr-xml-map "ipv6_ospfv3_area_cfg:HelloInterval";
          type uint32 {
            range "1..65535";
          }
          units "second";
          description "Time between HELLO packets";
        }
        leaf dead-interval {
          xr:xr-xml-map "ipv6_ospfv3_area_cfg:DeadInterval";
          type uint32 {
            range "1..65535";
          }
          units "second";
          description
            "Interval after which a neighbor is declared
            dead (in seconds)";
        }
        leaf default-cost {
          xr:xr-xml-map "ipv6_ospfv3_area_cfg:DefaultCost";
          type uint32 {
            range "0..16777215";
          }
          description
            "Set the summary default-cost of a NSSA/stub
            area";
        }
        leaf flood-reduction {
          xr:xr-xml-map "ipv6_ospfv3_area_cfg:FloodReduction";
          type boolean;
          description "Enable/disable flood reduction";
        }
        leaf retransmit-interval {
          xr:xr-xml-map "ipv6_ospfv3_area_cfg:RetransmitInterval";
          type uint32 {
            range "1..65535";
          }
          units "second";
          description "Specify the transmit interval in seconds";
        }
        leaf ldp-sync {
          xr:xr-xml-map "ipv6_ospfv3_area_cfg:LDPSync";
          type boolean;
          description "Enable/Disable MPLS LDP sync";
        }
        leaf network {
          xr:xr-xml-map "ipv6_ospfv3_area_cfg:Network";
          type Ospfv3-network;
          description "Specify network type";
        }
        leaf transmit-delay {
          xr:xr-xml-map "ipv6_ospfv3_area_cfg:TransmitDelay";
          type uint32 {
            range "1..65535";
          }
          units "second";
          description "Specify the transmit delay in seconds";
        }
        leaf cost {
          xr:xr-xml-map "ipv6_ospfv3_area_cfg:Cost";
          type uint32 {
            range "1..65535";
          }
          description "Interface cost";
        }
      }

      list area-address {
        key "address";
        description "Configuration for a particular area";
        leaf address {
          xr:xr-xml-map "ipv6_ospfv3_area_cfg:Address";
          type inet:ipv4-address-no-zone;
          description "Area ID if in IP address format";
        }
        uses AREA-CONTENT;
      }

      list area-area-id {
        key "area-id";
        description "Configuration for a particular area";
        leaf area-id {
          xr:xr-xml-map "ipv6_ospfv3_area_cfg:AreaID";
          type int32;
          description "Area ID if in integer format";
        }
        uses AREA-CONTENT;
      }
    }
  }

  grouping AUTO-COST {
    description "Common node of default-vrf, vrf";

    container auto-cost {
      xr:xr-xml-map "ipv6_ospfv3_cfg:AutoCost";
      presence "enable auto-cost";
      description "Calculate interface cost according to bandwidth";
      leaf disable {
        xr:xr-xml-map "ipv6_ospfv3_cfg:Disable";
        type empty;
        description
          "Specify 'true' to assign cost based on
          interface type";
      }
      leaf reference-bandwidth {
        xr:xr-xml-map "ipv6_ospfv3_cfg:ReferenceBandwidth";
        type uint32 {
          range "1..4294967";
        }
        units "Mbit/s";
        description
          "Specify reference bandwidth for cost
          computations in terms of Mbits per second";
      }
    }
  }

  grouping TIMERS {
    description "Common node of default-vrf, vrf";

    container timers {
      xr:xr-xml-map "ipv6_ospfv3_cfg:Timers";
      description "Adjust routing timers";

      container pacing {
        xr:xr-xml-map "ipv6_ospfv3_cfg:Pacing";
        description "Pacing timers";
        leaf flood {
          xr:xr-xml-map "ipv6_ospfv3_cfg:Flood";
          xr:xr-cli-map "(ipv6 router ospf)|(router (ospfv3)|(ospf6"+
            ")) <string> vrf <string> timers pacing flood <number> ";
          type uint32 {
            range "5..100";
          }
          units "millisecond";
          description
            "The minimum interval in milliseconds to pace
            limit flooding on interface";
        }
        leaf retransmission {
          xr:xr-xml-map "ipv6_ospfv3_cfg:Retransmission";
          xr:xr-cli-map "(ipv6 router ospf)|(router (ospfv3)|(ospf6"+
            ")) <string> vrf <string> timers pacing retransmission "+
            "<number> ";
          type uint32 {
            range "5..100";
          }
          description
            "The minimum interval in msec between neighbor
            retransmissions";
        }
        leaf lsa-group {
          xr:xr-xml-map "ipv6_ospfv3_cfg:LSAGroup";
          xr:xr-cli-map "(ipv6 router ospf)|(router (ospfv3)|(ospf6"+
            ")) <string> vrf <string> timers pacing lsa-group <numb"+
            "er> ";
          type uint32 {
            range "10..1800";
          }
          units "second";
          description
            "Interval in seconds at which LSAs are grouped
            and refreshed, checksummed, or aged";
        }
      }

      container lsa-timers {
        xr:xr-xml-map "ipv6_ospfv3_cfg:LSATimers";
        description "LSA timers";
        leaf arrival {
          xr:xr-xml-map "ipv6_ospfv3_cfg:Arrival";
          xr:xr-cli-map "(ipv6 router ospf)|(router (ospfv3)|(ospf6"+
            ")) <string> vrf <string> timers lsa arrival <number> ";
          type uint32 {
            range "0..60000";
          }
          units "millisecond";
          description
            "The minimum interval in milliseconds between
            accepting the same LSA";
        }
      }

      container throttle {
        xr:xr-xml-map "ipv6_ospfv3_cfg:Throttle";
        description "Throttle timers";

        container lsa {
          xr:xr-xml-map "ipv6_ospfv3_cfg:LSA";
          description
            "LSA throttle timers for all types of OSPF LSAs";
          leaf first-delay {
            xr:xr-xml-map "ipv6_ospfv3_cfg:FirstDelay";
            type uint32 {
              range "0..600000";
            }
            units "millisecond";
            description
              "Delay to generate first occurrence of LSA in
              milliseconds";
          }
          leaf minimum-delay {
            xr:xr-xml-map "ipv6_ospfv3_cfg:MinimumDelay";
            type uint32 {
              range "1..600000";
            }
            units "millisecond";
            description
              "Minimum delay between originating the same
              LSA in milliseconds";
          }
          leaf maximum-delay {
            xr:xr-xml-map "ipv6_ospfv3_cfg:MaximumDelay";
            type uint32 {
              range "1..600000";
            }
            units "millisecond";
            description
              "Maximum delay between originating the same
              LSA in milliseconds";
          }
        }

        container spf {
          xr:xr-xml-map "ipv6_ospfv3_cfg:SPF";
          description "SPF throttle timers";
          leaf first-delay {
            xr:xr-xml-map "ipv6_ospfv3_cfg:FirstDelay";
            type uint32 {
              range "1..600000";
            }
            description
              "Initial delay between receiving a change and
              starting SPF in ms";
          }
          leaf minimum-delay {
            xr:xr-xml-map "ipv6_ospfv3_cfg:MinimumDelay";
            type uint32 {
              range "1..600000";
            }
            description
              "Minimum hold time between consecutive SPF
              calculations in ms";
          }
          leaf maximum-delay {
            xr:xr-xml-map "ipv6_ospfv3_cfg:MaximumDelay";
            type uint32 {
              range "1..600000";
            }
            description
              "Maximum wait time between consecutive SPF
              calculations in ms";
          }
        }
      }
    }
  }

  grouping LOG-ADJACENCY-CHANGES {
    description "Common node of default-vrf, vrf";
    leaf log-adjacency-changes {
      xr:xr-xml-map "ipv6_ospfv3_cfg:LogAdjacencyChanges";
      xr:xr-cli-map "(ipv6 router ospf)|(router (ospfv3)|(ospf6)) <"+
        "string> vrf <string> log adjacency changes (detail)|(disab"+
        "le) ";
      type Ospfv3-log-adj;
      description "Log changes in adjacency state";
    }
  }

  grouping ON-PROC-MIGRATION {
    description "Common node of rbit, v6bit, max-metric";
    leaf on-proc-migration {
      xr:xr-xml-map "ipv6_ospfv3_cfg:OnProcMigration";
      type uint32 {
        range "5..86400";
      }
      units "second";
      description
        "Time (in seconds) to stay in stub router
        operational state";
    }
  }

  grouping DEFAULT-INFORMATION {
    description "Common node of default-vrf, vrf";

    container default-information {
      xr:xr-xml-map "ipv6_ospfv3_cfg:DefaultInformation";
      description "Control distribution of default information";

      container originate {
        xr:xr-xml-map "ipv6_ospfv3_cfg:Originate";
        presence "Indicates a originate node is configured.";
        description "Distribute a default route";
        leaf always {
          xr:xr-xml-map "ipv6_ospfv3_cfg:Always";
          type boolean;
          mandatory true;
          description "Always advertise default route";
        }
        leaf metric {
          xr:xr-xml-map "ipv6_ospfv3_cfg:Metric";
          type uint32 {
            range "0..16777214";
          }
          description "OSPFv3 default metric";
        }
        leaf metric-type {
          xr:xr-xml-map "ipv6_ospfv3_cfg:MetricType";
          type uint32 {
            range "1..2";
          }
          description "OSPFv3 metric type for default routes";
        }
        leaf tag {
          xr:xr-xml-map "ipv6_ospfv3_cfg:Tag";
          type int32;
          description "Tag for default route";
        }
        leaf route-policy-name {
          xr:xr-xml-map "ipv6_ospfv3_cfg:RoutePolicyName";
          type string;
          description
            "Route policy to default-information
            origination";
        }
      }
    }
  }

  grouping STUB-ROUTER {
    description "Common node of default-vrf, vrf";

    container stub-router {
      xr:xr-xml-map "ipv6_ospfv3_cfg:StubRouter";
      description "Stub router configuration";

      container rbit {
        xr:xr-xml-map "ipv6_ospfv3_cfg:RBit";
        description "Stub router R-bit configuration";
        uses ON-SWITCHOVER;
        uses ALWAYS;
        uses EXTERNAL-LSA;
        uses ON-STARTUP;
        uses INCLUDE-STUB;
        uses ENABLE;
        uses ON-PROC-MIGRATION;
        uses ON-PROC-RESTART;
        uses SUMMARY-LSA;
      }

      container v6bit {
        xr:xr-xml-map "ipv6_ospfv3_cfg:V6Bit";
        description "Stub router V6-bit configuration";
        uses ON-SWITCHOVER;
        uses ALWAYS;
        uses EXTERNAL-LSA;
        uses ON-STARTUP;
        uses INCLUDE-STUB;
        uses ENABLE;
        uses ON-PROC-MIGRATION;
        uses ON-PROC-RESTART;
        uses SUMMARY-LSA;
      }

      container max-metric {
        xr:xr-xml-map "ipv6_ospfv3_cfg:MaxMetric";
        description "Stub router max-metric configuration";
        uses ON-SWITCHOVER;
        uses ALWAYS;
        uses EXTERNAL-LSA;
        uses ON-STARTUP;
        uses INCLUDE-STUB;
        uses ENABLE;
        uses ON-PROC-MIGRATION;
        uses ON-PROC-RESTART;
        uses SUMMARY-LSA;
      }
    }
  }

  grouping INCLUDE-STUB {
    description "Common node of rbit, v6bit, max-metric";
    leaf include-stub {
      xr:xr-xml-map "ipv6_ospfv3_cfg:IncludeStub";
      type empty;
      description
        "Advertise stub links with maximum metric in stub
        router mode";
    }
  }

  grouping IGNORE {
    description "Common node of default-vrf, vrf";

    container ignore {
      xr:xr-xml-map "ipv6_ospfv3_cfg:Ignore";
      description "Do not complain about a specified event";

      container lsa {
        xr:xr-xml-map "ipv6_ospfv3_cfg:LSA";
        description
          "Do not complain upon receiving LSA of the
          specified type";
        leaf mospf {
          xr:xr-xml-map "ipv6_ospfv3_cfg:MOSPF";
          xr:xr-cli-map "(ipv6 router ospf)|(router (ospfv3)|(ospf6"+
            ")) <string> vrf <string> ignore lsa mospf ";
          type empty;
          description "Enable ignore of MOSPF type 6 LSA";
        }
      }
    }
  }

  grouping DATABASE-FILTER {
    description "Common node of default-vrf, vrf";

    container database-filter {
      xr:xr-xml-map "ipv6_ospfv3_cfg:DatabaseFilter";
      description "Database filter";

      container all {
        xr:xr-xml-map "ipv6_ospfv3_cfg:All";
        description "All";
        leaf out {
          xr:xr-xml-map "ipv6_ospfv3_cfg:Out";
          xr:xr-cli-map "(ipv6 router ospf)|(router (ospfv3)|(ospf6"+
            ")) <string> vrf <string> database-filter all out ";
          type empty;
          description "Enable out";
        }
      }
    }
  }

  grouping CANDIDATE-INTERFACE-TABLE {
    description "Common node of per-link, per-prefix";

    container candidate-interfaces {
      xr:xr-xml-map "ipv6_ospfv3_intfobj_cfg:CandidateInterfaceTabl"+
        "e";
      description
        "Fast-reroute per-link/per-prefix candidate
        interface configuration";

      list candidate-interface {
        xr:xr-xml-map "ipv6_ospfv3_intfobj_cfg:CandidateInterface";
        xr:xr-cli-map "(ipv6 router ospf)|(router (ospfv3)|(ospf6))"+
          " <string> vrf <string> fast-reroute per-link lfa-candida"+
          "te interface <interface> ";
        xr:xr-cli-map "(ipv6 router ospf)|(router (ospfv3)|(ospf6))"+
          " <string> vrf <string> fast-reroute per-prefix lfa-candi"+
          "date interface <interface> ";
        key "interface-name";
        description "Candidate backup interface";
        leaf interface-name {
          xr:xr-xml-map "ipv6_ospfv3_intfobj_cfg:InterfaceName";
          type xr:Interface-name;
          description "Interface";
        }
      }
    }
  }

  grouping ENCRYPTION {
    description "Common node of default-vrf, vrf";

    container encryption {
      xr:xr-xml-map "ipv6_ospfv3_cfg:Encryption";
      description "Encrypt and authenticate OSPFv3 packets";
      leaf enable {
        xr:xr-xml-map "ipv6_ospfv3_cfg:Enable";
        type boolean;
        description "Authenticate packets";
      }
      leaf spi {
        xr:xr-xml-map "ipv6_ospfv3_cfg:SPI";
        type uint32 {
          range "256..4294967295";
        }
        description
          "Use IPSec ESP authentication. Specify the
          Security Parameter Index (SPI) value";
      }
      leaf encryption-algorithm {
        xr:xr-xml-map "ipv6_ospfv3_cfg:EncryptionAlgorithm";
        type Ospfv3-encryption-algorithm;
        description "Specify the encryption algorithm";
      }
      leaf encryption-password {
        xr:xr-xml-map "ipv6_ospfv3_cfg:EncryptionPassword";
        type xr:Proprietary-password;
        description "Encryption password";
      }
      leaf authentication-algorithm {
        xr:xr-xml-map "ipv6_ospfv3_cfg:AuthenticationAlgorithm";
        type Ospfv3-authentication-type2;
        description "Use the NULL, MD5 or SHA1 algorithm";
      }
      leaf authentication-password {
        xr:xr-xml-map "ipv6_ospfv3_cfg:AuthenticationPassword";
        type xr:Proprietary-password;
        description "Specify MD5 or SHA1 password";
      }
    }
  }

  grouping AUTHENTICATION {
    description "Common node of default-vrf, vrf";

    container authentication {
      xr:xr-xml-map "ipv6_ospfv3_cfg:Authentication";
      description "Authenticate OSPFv3 packets";
      leaf enable {
        xr:xr-xml-map "ipv6_ospfv3_cfg:Enable";
        type boolean;
        description "Authenticate packets";
      }
      leaf spi {
        xr:xr-xml-map "ipv6_ospfv3_cfg:SPI";
        type uint32 {
          range "256..4294967295";
        }
        description
          "Use IPSec AH authentication. Specify the
          Security Parameter Index (SPI) value";
      }
      leaf algorithm {
        xr:xr-xml-map "ipv6_ospfv3_cfg:Algorithm";
        type Ospfv3-authentication;
        description "Use the MD5 or SHA1 algorithm";
      }
      leaf password {
        xr:xr-xml-map "ipv6_ospfv3_cfg:Password";
        type xr:Proprietary-password;
        description "Specify MD5 or SHA1 password";
      }
    }
  }

  grouping SUMMARY-LSA {
    description "Common node of rbit, v6bit, max-metric";
    leaf summary-lsa {
      xr:xr-xml-map "ipv6_ospfv3_cfg:SummaryLSA";
      type uint32 {
        range "1..16777214";
      }
      default "16711680";
      description
        "Advertise summary LSAs with modified metric in
        stub router mode";
    }
  }

  grouping DISTRIBUTE-LIST-OUT {
    description "Common node of default-vrf, vrf";

    container distribute-list-out {
      xr:xr-xml-map "ipv6_ospfv3_cfg:DistributeListOut";
      description "Filter prefixes from RIB ";

      container distribute-outs {
        xr:xr-xml-map "ipv6_ospfv3_cfg:DistributeOutTable";
        description "Filter generated type-5 LSAs";

        list distribute-out {
          must "as-yy-and-as-xx-and-process-name" {
            description
              "as-yy-and-as-xx-and-process-name must be
              present.";
          }
          key "protocol-name";
          description "Filter generated type-5 LSAs";
          leaf protocol-name {
            xr:xr-xml-map "ipv6_ospfv3_cfg:ProtocolName";
            xr:xr-cli-map "(ipv6 router ospf)|(router (ospfv3)|(osp"+
              "f6)) <string> vrf <string> distribute-list prefix-li"+
              "st (<string>) out [connected|static|bgp (<number>)|("+
              "<number>)|(<number> <number>)|ospfv3 <string>|isis <"+
              "string>|eigrp <number>] ";
            type Ospfv3-protocol;
            description "none";
          }

          list as-yy-and-as-xx-and-process-name {
            xr:xr-xml-map "ipv6_ospfv3_cfg:DistributeOut";
            xr:xr-cli-map "(ipv6 router ospf)|(router (ospfv3)|(osp"+
              "f6)) <string> vrf <string> distribute-list prefix-li"+
              "st (<string>) out [connected|static|bgp (<number>)|("+
              "<number>)|(<number> <number>)|ospfv3 <string>|isis <"+
              "string>|eigrp <number>] ";
            when "../protocol-name = 'all'" {
              description "../protocol-name = all";
            }
            key "as-yy as-xx process-name";
            description "keys: as-yy, as-xx, process-name";
            leaf as-yy {
              xr:xr-xml-map "ipv6_ospfv3_cfg:AS_YY";
              type uint32 {
                range "0..4294967295";
              }
              description
                "4-byte AS number in asdot (X.Y) format -
                second half (Y), or 2-byte AS number, or
                4-byte AS number in asplain format";
            }
            leaf as-xx {
              xr:xr-xml-map "ipv6_ospfv3_cfg:AS_XX";
              type uint32 {
                range "1..65535";
              }
              description
                "4-byte AS number in asdot (X.Y) format -
                first half (X)";
            }
            leaf process-name {
              xr:xr-xml-map "ipv6_ospfv3_cfg:ProcessName";
              type xr:Cisco-ios-xr-string;
              description
                "If ISIS or OSPFv3, specify the instance name";
            }
            leaf prefix-list {
              xr:xr-xml-map "ipv6_ospfv3_cfg:PrefixList";
              type string;
              mandatory true;
              description "Prefix-list name";
            }
          }
        }
      }
    }
  }

  grouping DISTRIBUTE-LIST {
    description "Common node of default-vrf, vrf";

    container distribute-list {
      xr:xr-xml-map "ipv6_ospfv3_cfg:DistributeList";
      description "Filter prefixes to/from RIB";

      container in {
        xr:xr-xml-map "ipv6_ospfv3_cfg:In";
        description "Filter prefixes installed to RIB";
        leaf prefix-list {
          xr:xr-xml-map "ipv6_ospfv3_cfg:PrefixList";
          xr:xr-cli-map "(ipv6 router ospf)|(router (ospfv3)|(ospf6"+
            ")) <string> vrf <string> distribute-list prefix-list ("+
            "<string>) in ";
          type string;
          description
            "Filter prefixes based on an IPv6 prefix-list";
        }
      }
    }
  }

  grouping COST {
    description "Common node of default-vrf, vrf";
    leaf cost {
      xr:xr-xml-map "ipv6_ospfv3_cfg:Cost";
      xr:xr-cli-map "(ipv6 router ospf)|(router (ospfv3)|(ospf6)) <"+
        "string> vrf <string> cost <number> ";
      type uint32 {
        range "1..65535";
      }
      description "Interface cost";
    }
  }

  grouping PACKET-SIZE {
    description "Common node of default-vrf, vrf";
    leaf packet-size {
      xr:xr-xml-map "ipv6_ospfv3_cfg:PacketSize";
      xr:xr-cli-map "(ipv6 router ospf)|(router (ospfv3)|(ospf6)) <"+
        "string> vrf <string> packet-size <number> ";
      type uint32 {
        range "256..10000";
      }
      description "Limit size of OSPFv3 packets";
    }
  }

  grouping FAST-REROUTE {
    description "Common node of default-vrf, vrf";

    container fast-reroute {
      xr:xr-xml-map "ipv6_ospfv3_cfg:FastReroute";
      description "Fast-reroute instance scoped parameters";

      container per-link {
        xr:xr-xml-map "ipv6_ospfv3_cfg:PerLink";
        description "Fast-reroute per-link global configuration";
        uses PRIORITY;
      }

      container per-prefix {
        xr:xr-xml-map "ipv6_ospfv3_cfg:PerPrefix";
        description "Fast-reroute per-prefix global configuration";

        container tiebreakers {
          xr:xr-xml-map "ipv6_ospfv3_cfg:TiebreakerTable";
          description "Fast-reroute tiebreakers configurations";

          list tiebreaker {
            xr:xr-xml-map "ipv6_ospfv3_cfg:Tiebreaker";
            xr:xr-cli-map "(ipv6 router ospf)|(router (ospfv3)|(osp"+
              "f6)) <string> vrf <string> fast-reroute per-prefix t"+
              "iebreaker (downstream)|(lc-disjoint)|(lowest-backup-"+
              "metric)|(node-protecting)|(primary-path)|(secondary-"+
              "path)|(srlg-disjoint) index <number> ";
            key "tiebreaker-type";
            description "Fast-reroute tiebreakers configuration";
            leaf tiebreaker-type {
              xr:xr-xml-map "ipv6_ospfv3_cfg:TiebreakerType";
              type Ospfv3-fast-reroute-tiebreakers;
              description "Tiebreaker type";
            }
            leaf tiebreaker-index {
              xr:xr-xml-map "ipv6_ospfv3_cfg:TiebreakerIndex";
              type uint32 {
                range "1..255";
              }
              mandatory true;
              description "Index value for a tiebreaker";
            }
          }
        }
        leaf load-sharing-disable {
          xr:xr-xml-map "ipv6_ospfv3_cfg:LoadSharingDisable";
          xr:xr-cli-map "(ipv6 router ospf)|(router (ospfv3)|(ospf6"+
            ")) <string> vrf <string> fast-reroute per-prefix load-"+
            "sharing disable ";
          type empty;
          description
            "Disable load sharing between multiple backups";
        }
        uses PRIORITY;
      }
    }
  }

  grouping IPV6-OSPFV3-INTFOBJ-CFG-FAST-REROUTE {
    description
      "Common node of process-scope, area-scope,
      interface";

    container fast-reroute {
      xr:xr-xml-map "ipv6_ospfv3_intfobj_cfg:FastReroute";
      description "Fast-reroute configuration";

      container per-link {
        xr:xr-xml-map "ipv6_ospfv3_intfobj_cfg:PerLink";
        description "Fast-reroute per-link configuration";
        uses FAST-REROUTE-USE-CANDIDATE-ONLY;
        uses CANDIDATE-INTERFACE-TABLE;
        uses EXCLUDE-INTERFACE-TABLE;
      }

      container per-prefix {
        xr:xr-xml-map "ipv6_ospfv3_intfobj_cfg:PerPrefix";
        description "Fast-reroute per-link configuration";
        uses FAST-REROUTE-USE-CANDIDATE-ONLY;
        uses CANDIDATE-INTERFACE-TABLE;
        uses EXCLUDE-INTERFACE-TABLE;
      }
      leaf fast-reroute-enable {
        xr:xr-xml-map "ipv6_ospfv3_intfobj_cfg:FastRerouteEnable";
        xr:xr-cli-map "(ipv6 router ospf)|(router (ospfv3)|(ospf6))"+
          " <string> vrf <string> fast-reroute (per-link [enable|di"+
          "sable])|(per-prefix)|(disable) ";
        type Ospfv3-fast-reroute;
        description
          "Enable/Disable Fast-reroute per-link or
          per-prefix";
      }
    }
  }

  grouping SUMMARY-PREFIX-TABLE {
    description "Common node of default-vrf, vrf";

    container summary-prefixes {
      xr:xr-xml-map "ipv6_ospfv3_cfg:SummaryPrefixTable";
      description
        "Summarize redistributed routes matching
        prefix/length";

      list summary-prefix {
        xr:xr-xml-map "ipv6_ospfv3_cfg:SummaryPrefix";
        xr:xr-cli-map "(ipv6 router ospf)|(router (ospfv3)|(ospf6))"+
          " <string> vrf <string> summary-prefix <IPv6 address> [no"+
          "t-advertise|tag <number>] ";
        key "prefix prefix-length";
        description "IPv6 address";
        leaf prefix {
          xr:xr-xml-map "ipv6_ospfv3_cfg:Prefix";
          type xr:Cisco-ios-xr-string;
          description "IPv6 prefix string format";
        }
        leaf prefix-length {
          xr:xr-xml-map "ipv6_ospfv3_cfg:PrefixLength";
          type xr:Ipv6-prefix-length;
          description "IPV6 prefix length";
        }
        leaf not-advertise {
          xr:xr-xml-map "ipv6_ospfv3_cfg:NotAdvertise";
          type boolean;
          description "Suppress routes matching prefix/length";
        }
        leaf tag {
          xr:xr-xml-map "ipv6_ospfv3_cfg:Tag";
          type uint32 {
            range "1..4294967295";
          }
          description "Tag";
        }
      }
    }
  }

  grouping ENABLE {
    description "Common node of rbit, v6bit, max-metric";
    leaf enable {
      xr:xr-xml-map "ipv6_ospfv3_cfg:Enable";
      type empty;
      description "Enabled stub router configuration mode";
    }
  }

  grouping MAXIMUM {
    description "Common node of default-vrf, vrf";

    container maximum {
      xr:xr-xml-map "ipv6_ospfv3_cfg:Maximum";
      description "Set OSPFv3 limits";

      container redistributed-prefixes {
        xr:xr-xml-map "ipv6_ospfv3_cfg:RedistributedPrefixes";
        description "Limit number of redistributed prefixes";
        leaf prefixes {
          xr:xr-xml-map "ipv6_ospfv3_cfg:Prefixes";
          type uint32 {
            range "1..4294967295";
          }
          description
            "Maximum number of prefixes redistributed to
            protocol";
        }
        leaf threshold {
          xr:xr-xml-map "ipv6_ospfv3_cfg:Threshold";
          type uint32 {
            range "1..100";
          }
          description
            "Threshold value (%) at which to generate a
            warning message";
        }
        leaf warning-only {
          xr:xr-xml-map "ipv6_ospfv3_cfg:WarningOnly";
          type empty;
          description
            "Only give warning message when limit is
            exceeded";
        }
      }
      leaf interfaces {
        xr:xr-xml-map "ipv6_ospfv3_cfg:Interfaces";
        xr:xr-cli-map "(ipv6 router ospf)|(router (ospfv3)|(ospf6))"+
          " <string> vrf <string> maximum interfaces <number> ";
        type uint32 {
          range "1..4294967295";
        }
        description "Specify maximum number of interfaces";
      }
      leaf paths {
        xr:xr-xml-map "ipv6_ospfv3_cfg:Paths";
        xr:xr-cli-map "(ipv6 router ospf)|(router (ospfv3)|(ospf6))"+
          " <string> vrf <string> maximum paths <number> ";
        type uint32 {
          range "1..64";
        }
        description "Specify maximum number of paths per route";
      }
    }
  }

  grouping NETWORK {
    description "Common node of default-vrf, vrf";
    leaf network {
      xr:xr-xml-map "ipv6_ospfv3_cfg:Network";
      xr:xr-cli-map "(ipv6 router ospf)|(router (ospfv3)|(ospf6)) <"+
        "string> vrf <string> network (broadcast)|(non-broadcast)|("+
        "point-to-point)|(point-to-multipoint [non-broadcast]) ";
      type Ospfv3-network;
      description "Specify network type";
    }
  }

  grouping EXTERNAL-LSA {
    description "Common node of rbit, v6bit, max-metric";
    leaf external-lsa {
      xr:xr-xml-map "ipv6_ospfv3_cfg:ExternalLSA";
      type uint32 {
        range "1..16777214";
      }
      default "16711680";
      description
        "Advertise external LSAs with modified metric in
        stub router mode";
    }
  }

  grouping HELLO-INTERVAL {
    description "Common node of default-vrf, vrf";
    leaf hello-interval {
      xr:xr-xml-map "ipv6_ospfv3_cfg:HelloInterval";
      xr:xr-cli-map "(ipv6 router ospf)|(router (ospfv3)|(ospf6)) <"+
        "string> vrf <string> hello-interval <number> ";
      type uint32 {
        range "1..65535";
      }
      units "second";
      description "Time between HELLO packets";
    }
  }

  grouping PROCESS-SCOPE {
    description "Common node of default-vrf, vrf";

    container process-scope {
      xr:xr-xml-map "ipv6_ospfv3_cfg:ProcessScope";
      description "Process scope configuration";
      uses IPV6-OSPFV3-INTFOBJ-CFG-FAST-REROUTE;
    }
  }

  grouping SPF-PREFIX-PRIORITY-POLICY {
    description "Common node of default-vrf, vrf";
    leaf spf-prefix-priority-policy {
      xr:xr-xml-map "ipv6_ospfv3_cfg:SPFPrefixPriorityPolicy";
      xr:xr-cli-map "(ipv6 router ospf)|(router (ospfv3)|(ospf6)) <"+
        "string> vrf <string> spf prefix-priority route-policy (<st"+
        "ring>)|(<text>) ";
      type string;
      description "Route policy for SPF prefix prioritization";
    }
  }

  grouping MTU-IGNORE {
    description "Common node of default-vrf, vrf";
    leaf mtu-ignore {
      xr:xr-xml-map "ipv6_ospfv3_cfg:MTUIgnore";
      xr:xr-cli-map "(ipv6 router ospf)|(router (ospfv3)|(ospf6)) <"+
        "string> vrf <string> mtu-ignore enable ";
      type boolean;
      description "Enable/disable ignoring of MTU in DBD packets";
    }
  }

  grouping FAST-REROUTE-USE-CANDIDATE-ONLY {
    description "Common node of per-link, per-prefix";
    leaf fast-reroute-use-candidate-only {
      xr:xr-xml-map "ipv6_ospfv3_intfobj_cfg:FastRerouteUseCandidat"+
        "eOnly";
      xr:xr-cli-map "(ipv6 router ospf)|(router (ospfv3)|(ospf6)) <"+
        "string> vrf <string> fast-reroute per-link use-candidate-o"+
        "nly enable ";
      xr:xr-cli-map "(ipv6 router ospf)|(router (ospfv3)|(ospf6)) <"+
        "string> vrf <string> fast-reroute per-prefix use-candidate"+
        "-only enable ";
      type boolean;
      default "false";
      description
        "Use only interfaces on the candidate list as a
        backup path";
    }
  }

  grouping GRACEFUL-RESTART {
    description "Common node of default-vrf, vrf";

    container graceful-restart {
      xr:xr-xml-map "ipv6_ospfv3_cfg:GracefulRestart";
      description "Graceful restart configuration";
      leaf interval {
        xr:xr-xml-map "ipv6_ospfv3_cfg:Interval";
        xr:xr-cli-map "(ipv6 router ospf)|(router (ospfv3)|(ospf6))"+
          " <string> vrf <string> graceful-restart interval <number"+
          "> ";
        type uint32 {
          range "90..3600";
        }
        units "second";
        description
          "Minimum interval between graceful restarts
          (seconds)";
      }
      leaf strict-lsa-checking {
        xr:xr-xml-map "ipv6_ospfv3_cfg:StrictLSAChecking";
        xr:xr-cli-map "(ipv6 router ospf)|(router (ospfv3)|(ospf6))"+
          " <string> vrf <string> graceful-restart strict-lsa-check"+
          "ing ";
        type empty;
        description
          "Terminate graceful restart helper mode if LSA
          changed";
      }
      leaf helper {
        xr:xr-xml-map "ipv6_ospfv3_cfg:Helper";
        xr:xr-cli-map "(ipv6 router ospf)|(router (ospfv3)|(ospf6))"+
          " <string> vrf <string> graceful-restart helper (disable)"+
          "|(planned-only) ";
        type empty;
        description "Disable router's helper support";
      }
      leaf enable {
        xr:xr-xml-map "ipv6_ospfv3_cfg:Enable";
        xr:xr-cli-map "(ipv6 router ospf)|(router (ospfv3)|(ospf6))"+
          " <string> vrf <string> graceful-restart ";
        type empty;
        description "Enable graceful restart";
      }
      leaf lifetime {
        xr:xr-xml-map "ipv6_ospfv3_cfg:Lifetime";
        xr:xr-cli-map "(ipv6 router ospf)|(router (ospfv3)|(ospf6))"+
          " <string> vrf <string> graceful-restart lifetime <number"+
          "> ";
        type uint32 {
          range "90..1800";
        }
        units "second";
        description
          "Maximum route lifetime following restart
          (seconds)";
      }
    }
  }

  grouping BFD {
    description "Common node of default-vrf, vrf";

    container bfd {
      xr:xr-xml-map "ipv6_ospfv3_cfg:BFD";
      description "Configure BFD parameters";
      leaf interval {
        xr:xr-xml-map "ipv6_ospfv3_cfg:Interval";
        xr:xr-cli-map "(ipv6 router ospf)|(router (ospfv3)|(ospf6))"+
          " <string> vrf <string> bfd minimum-interval <number> ";
        type uint32 {
          range "3..30000";
        }
        units "millisecond";
        description "Hello interval in milli-seconds";
      }
      leaf detection-multiplier {
        xr:xr-xml-map "ipv6_ospfv3_cfg:DetectionMultiplier";
        xr:xr-cli-map "(ipv6 router ospf)|(router (ospfv3)|(ospf6))"+
          " <string> vrf <string> bfd multiplier <number> ";
        type uint32 {
          range "2..50";
        }
        description "Detect multiplier";
      }
      leaf fast-detect-mode {
        xr:xr-xml-map "ipv6_ospfv3_cfg:FastDetectMode";
        xr:xr-cli-map "(ipv6 router ospf)|(router (ospfv3)|(ospf6))"+
          " <string> vrf <string> bfd fast-detect strict-mode ";
        type Ospfv3bfd-enable-mode;
        description "Enable or disable BFD fast detection";
      }
    }
  }

  grouping SNMP {
    description "Common node of default-vrf, vrf";

    container snmp {
      xr:xr-xml-map "ipv6_ospfv3_cfg:SNMP";
      description "SNMP configuration";

      container trap-rate-limit {
        xr:xr-xml-map "ipv6_ospfv3_cfg:TrapRateLimit";
        description "SNMP trap rate configuration";
        leaf window-size {
          xr:xr-xml-map "ipv6_ospfv3_cfg:WindowSize";
          type uint32 {
            range "2..60";
          }
          description "Trap rate limit sliding window size";
        }
        leaf max-window-traps {
          xr:xr-xml-map "ipv6_ospfv3_cfg:MaxWindowTraps";
          type uint32 {
            range "0..300";
          }
          description "Max number of traps sent in window time";
        }
      }
      leaf context {
        xr:xr-xml-map "ipv6_ospfv3_cfg:Context";
        xr:xr-cli-map "(ipv6 router ospf)|(router (ospfv3)|(ospf6))"+
          " <string> vrf <string> snmp context <string> ";
        type string;
        description "SNMP context configuration";
      }
    }
  }

  grouping ON-STARTUP {
    description "Common node of rbit, v6bit, max-metric";

    container on-startup {
      xr:xr-xml-map "ipv6_ospfv3_cfg:OnStartup";
      description "Enter stub router operational state on startup";
      leaf wait-for-bgp {
        xr:xr-xml-map "ipv6_ospfv3_cfg:WaitForBGP";
        type boolean;
        default "false";
        description
          "Wait until BGP converges (only applicable to
          default VRF)";
      }
      leaf wait-time {
        xr:xr-xml-map "ipv6_ospfv3_cfg:WaitTime";
        when "../wait-for-bgp = 0" {
          description "../WaitForBGP = <expr>";
        }
        type uint32 {
          range "5..86400";
        }
        units "second";
        description
          "Time (in seconds) to stay in stub router
          operational state";
      }
    }
  }

  grouping FLOOD-REDUCTION {
    description "Common node of default-vrf, vrf";
    leaf flood-reduction {
      xr:xr-xml-map "ipv6_ospfv3_cfg:FloodReduction";
      xr:xr-cli-map "(ipv6 router ospf)|(router (ospfv3)|(ospf6)) <"+
        "string> vrf <string> flood-reduction enable ";
      type boolean;
      description "Enable/disable flood reduction";
    }
  }

  grouping ON-SWITCHOVER {
    description "Common node of rbit, v6bit, max-metric";
    leaf on-switchover {
      xr:xr-xml-map "ipv6_ospfv3_cfg:OnSwitchover";
      type uint32 {
        range "5..86400";
      }
      units "second";
      description
        "Time (in seconds) to stay in stub router
        operational state";
    }
  }

  grouping DEAD-INTERVAL {
    description "Common node of default-vrf, vrf";
    leaf dead-interval {
      xr:xr-xml-map "ipv6_ospfv3_cfg:DeadInterval";
      xr:xr-cli-map "(ipv6 router ospf)|(router (ospfv3)|(ospf6)) <"+
        "string> vrf <string> dead-interval <number> ";
      type uint32 {
        range "1..65535";
      }
      units "second";
      description
        "Interval after which a neighbor is declared dead
        (in seconds)";
    }
  }

  grouping INSTANCE {
    description "Common node of default-vrf, vrf";
    leaf instance {
      xr:xr-xml-map "ipv6_ospfv3_cfg:Instance";
      xr:xr-cli-map "(ipv6 router ospf)|(router (ospfv3)|(ospf6)) <"+
        "string> vrf <string> instance <number> ";
      type uint32 {
        range "0..255";
      }
      description "Instance ID";
    }
  }

  grouping ROUTER-ID {
    description "Common node of default-vrf, vrf";
    leaf router-id {
      xr:xr-xml-map "ipv6_ospfv3_cfg:RouterID";
      xr:xr-cli-map "(ipv6 router ospf)|(router (ospfv3)|(ospf6)) <"+
        "string> vrf <string> router-id <IPv4 address> ";
      type inet:ipv4-address-no-zone;
      description
        "Specify the router ID for this OSPFv3 process in
        IPv4 address format";
    }
  }

  grouping DEFAULT-METRIC {
    description "Common node of default-vrf, vrf";
    leaf default-metric {
      xr:xr-xml-map "ipv6_ospfv3_cfg:DefaultMetric";
      xr:xr-cli-map "(ipv6 router ospf)|(router (ospfv3)|(ospf6)) <"+
        "string> vrf <string> default-metric <number> ";
      type uint32 {
        range "1..16777214";
      }
      description "Set metric of redistributed routes";
    }
  }

  grouping RETRANSMIT-INTERVAL {
    description "Common node of default-vrf, vrf";
    leaf retransmit-interval {
      xr:xr-xml-map "ipv6_ospfv3_cfg:RetransmitInterval";
      xr:xr-cli-map "(ipv6 router ospf)|(router (ospfv3)|(ospf6)) <"+
        "string> vrf <string> retransmit-interval <number> ";
      type uint32 {
        range "1..65535";
      }
      units "second";
      description "Specify the transmit interval in seconds";
    }
  }

  grouping PRIORITY {
    description "Common node of per-link, per-prefix";
    leaf priority {
      xr:xr-xml-map "ipv6_ospfv3_cfg:Priority";
      xr:xr-cli-map "(ipv6 router ospf)|(router (ospfv3)|(ospf6)) <"+
        "string> vrf <string> fast-reroute per-link priority-limit "+
        "(critical)|(high)|(medium) ";
      xr:xr-cli-map "(ipv6 router ospf)|(router (ospfv3)|(ospf6)) <"+
        "string> vrf <string> fast-reroute per-prefix priority-limi"+
        "t (critical)|(high)|(medium) ";
      type Ospfv3-fast-reroute-priority;
      description
        "Fast-reroute per-link/per-prefix priority-limit
        command";
    }
  }

  grouping IPV6-OSPFV3-CFG-PRIORITY {
    description "Common node of default-vrf, vrf";
    leaf priority {
      xr:xr-xml-map "ipv6_ospfv3_cfg:Priority";
      xr:xr-cli-map "(ipv6 router ospf)|(router (ospfv3)|(ospf6)) <"+
        "string> vrf <string> priority <number> ";
      type uint32 {
        range "0..255";
      }
      description "Specify router priority";
    }
  }

  container ospfv3 {
    xr:xr-xml-map "ipv6_ospfv3_cfg:OSPFv3";
    description "OSPFv3 configuration";

    container processes {
      xr:xr-xml-map "ipv6_ospfv3_cfg:ProcessTable";
      description "OSPFv3 processes";

      list process {
        xr:xr-xml-map "ipv6_ospfv3_cfg:Process";
        key "process-name";
        description "An OSPFv3 process";

        container default-vrf {
          xr:xr-xml-map "ipv6_ospfv3_cfg:DefaultVRF";
          description "Default VRF related configuration";
          leaf ldp-sync {
            xr:xr-xml-map "ipv6_ospfv3_cfg:LDPSync";
            type boolean;
            description "Enable/Disable MPLS LDP sync";
          }
          leaf spf-prefix-priority-disable {
            xr:xr-xml-map "ipv6_ospfv3_cfg:SPFPrefixPriorityDisable";
            type empty;
            description "SPF prefix prioritization disabled";
          }
          uses AREA-TABLE;
          uses TIMERS;
          uses SUMMARY-PREFIX-TABLE;
          uses SNMP;
          uses FAST-REROUTE;
          uses RETRANSMIT-INTERVAL;
          uses DISTANCE;
          uses PASSIVE;
          uses DEFAULT-METRIC;
          uses FLOOD-REDUCTION;
          uses MAXIMUM;
          uses REDISTRIBUTE-TABLE;
          uses IGNORE;
          uses DISTRIBUTE-LIST-OUT;
          uses DISTRIBUTE-LIST;
          uses HELLO-INTERVAL;
          uses STUB-ROUTER;
          uses IPV6-OSPFV3-CFG-PRIORITY;
          uses BFD;
          uses COST;
          uses DEAD-INTERVAL;
          uses PACKET-SIZE;
          uses INSTANCE;
          uses SPF-PREFIX-PRIORITY-POLICY;
          uses DATABASE-FILTER;
          uses ROUTER-ID;
          uses NETWORK;
          uses MTU-IGNORE;
          uses LOG-ADJACENCY-CHANGES;
          uses AUTHENTICATION;
          uses DEMAND-CIRCUIT;
          uses GRACEFUL-RESTART;
          uses DEFAULT-INFORMATION;
          uses PROCESS-SCOPE;
          uses ENCRYPTION;
          uses AUTO-COST;
          uses TRANSMIT-DELAY;
        }

        container vrfs {
          xr:xr-xml-map "ipv6_ospfv3_cfg:VRFTable";
          description "VRF related configuration";

          list vrf {
            xr:xr-xml-map "ipv6_ospfv3_cfg:VRF";
            key "vrf-name";
            description "Configuration for a particular OSPF VRF";

            container capability {
              xr:xr-xml-map "ipv6_ospfv3_cfg:Capability";
              description "OSPFv3 Capability";
              leaf vrf-lite {
                xr:xr-xml-map "ipv6_ospfv3_cfg:VRFLite";
                xr:xr-cli-map "(ipv6 router ospf)|(router (ospfv3)|"+
                  "(ospf6)) <string> vrf <string> capability vrf-li"+
                  "te ";
                type boolean;
                description "Enable VRF Lite";
              }
            }

            container domain-id {
              xr:xr-xml-map "ipv6_ospfv3_cfg:DomainID";
              description "OSPFv3 Domain ID";

              container secondary-domain-ids {
                xr:xr-xml-map "ipv6_ospfv3_cfg:SecondaryDomainIDTab"+
                  "le";
                description "Secondary domain ID Table";

                list secondary-domain-id {
                  xr:xr-xml-map "ipv6_ospfv3_cfg:SecondaryDomainID";
                  xr:xr-cli-map "(ipv6 router ospf)|(router (ospfv3"+
                    ")|(ospf6)) <string> vrf <string> domain-id sec"+
                    "ondary type (<enum>)|(8005) value <string> ";
                  key "domain-id-type domain-id-name";
                  description "OSPF Secondary domain ID";
                  leaf domain-id-type {
                    xr:xr-xml-map "ipv6_ospfv3_cfg:DomainIDType";
                    type Ospfv3-domain-id;
                    description "Secondary domain ID type";
                  }
                  leaf domain-id-name {
                    xr:xr-xml-map "ipv6_ospfv3_cfg:DomainIDName";
                    type xr:Cisco-ios-xr-string;
                    description "Secondary domain ID value";
                  }
                }
              }

              container primary-domain-id {
                xr:xr-xml-map "ipv6_ospfv3_cfg:PrimaryDomainID";
                description "OSPF Primary domain ID";
                leaf domain-id-type {
                  xr:xr-xml-map "ipv6_ospfv3_cfg:DomainIDType";
                  type Ospfv3-domain-id;
                  description "Primary domain ID type";
                }
                leaf domain-id-name {
                  xr:xr-xml-map "ipv6_ospfv3_cfg:DomainIDName";
                  type string;
                  description "Primary domain ID value";
                }
              }
            }
            leaf enable {
              xr:xr-xml-map "ipv6_ospfv3_cfg:Enable";
              type empty;
              description "Enable OSPFv3 VRF configuration";
            }
            leaf snmpvrf-trap {
              xr:xr-xml-map "ipv6_ospfv3_cfg:SNMPVRFTrap";
              xr:xr-cli-map "(ipv6 router ospf)|(router (ospfv3)|(o"+
                "spf6)) <string> vrf <string> snmp trap ";
              type empty;
              description "Enable SNMP trap configuration in a VRF";
            }
            leaf vrf-name {
              xr:xr-xml-map "ipv6_ospfv3_cfg:VRFName";
              type xr:Cisco-ios-xr-string;
              description "Name for this VRF";
            }
            uses AREA-TABLE;
            uses TIMERS;
            uses SUMMARY-PREFIX-TABLE;
            uses SNMP;
            uses FAST-REROUTE;
            uses RETRANSMIT-INTERVAL;
            uses DISTANCE;
            uses PASSIVE;
            uses DEFAULT-METRIC;
            uses FLOOD-REDUCTION;
            uses MAXIMUM;
            uses REDISTRIBUTE-TABLE;
            uses IGNORE;
            uses DISTRIBUTE-LIST-OUT;
            uses DISTRIBUTE-LIST;
            uses HELLO-INTERVAL;
            uses STUB-ROUTER;
            uses IPV6-OSPFV3-CFG-PRIORITY;
            uses BFD;
            uses COST;
            uses DEAD-INTERVAL;
            uses PACKET-SIZE;
            uses INSTANCE;
            uses SPF-PREFIX-PRIORITY-POLICY;
            uses DATABASE-FILTER;
            uses ROUTER-ID;
            uses NETWORK;
            uses MTU-IGNORE;
            uses LOG-ADJACENCY-CHANGES;
            uses AUTHENTICATION;
            uses DEMAND-CIRCUIT;
            uses GRACEFUL-RESTART;
            uses DEFAULT-INFORMATION;
            uses PROCESS-SCOPE;
            uses ENCRYPTION;
            uses AUTO-COST;
            uses TRANSMIT-DELAY;
          }
        }

        container af {
          xr:xr-xml-map "ipv6_ospfv3_cfg:AF";
          presence "Indicates a af node is configured.";
          description "Address Family (AF)";
          leaf af-name {
            xr:xr-xml-map "ipv6_ospfv3_cfg:AFName";
            type Ospfv3-address-family;
            mandatory true;
            description "Address Family (AF) identifier";
          }
          leaf saf-name {
            xr:xr-xml-map "ipv6_ospfv3_cfg:SAFName";
            type Ospfv3-subsequent-address-family;
            description
              "Subsequent Address Family (SAF) identifier";
          }
        }

        container trace-bufs {
          xr:xr-xml-map "ipv6_ospfv3_cfg:Trace";
          description
            "Configuration to change size of trace buffer";

          list trace-buf {
            xr:xr-xml-map "ipv6_ospfv3_cfg:TraceBuf";
            xr:xr-cli-map "(ipv6 router ospf)|(router (ospfv3)|(osp"+
              "f6)) <string> trace size <string> (0)|(256)|(512)|(1"+
              "024)|(2048)|(4096)|(8192)|(16384)|(32768)|(65536) ";
            key "trace-buf-name";
            description
              "Changes the size of the specified trace
              buffer";
            leaf trace-buf-name {
              xr:xr-xml-map "ipv6_ospfv3_cfg:TraceBufName";
              type xr:Cisco-ios-xr-string;
              description "Name for this VRF";
            }
            leaf bufsize {
              xr:xr-xml-map "ipv6_ospfv3_cfg:Bufsize";
              type Trace-buf-size;
              mandatory true;
              description "Buffer size";
            }
          }
        }
        leaf nsr {
          xr:xr-xml-map "ipv6_ospfv3_cfg:NSR";
          xr:xr-cli-map "(ipv6 router ospf)|(router (ospfv3)|(ospf6"+
            ")) <string> nsr disable ";
          type Ospfv3nsr;
          default "true";
          description "Enable non-stop routing";
        }
        leaf protocol-shutdown {
          xr:xr-xml-map "ipv6_ospfv3_cfg:ProtocolShutdown";
          xr:xr-cli-map "(ipv6 router ospf)|(router (ospfv3)|(ospf6"+
            ")) <string> protocol shutdown ";
          type empty;
          description "Enable protocol shutdown";
        }
        leaf enable {
          xr:xr-xml-map "ipv6_ospfv3_cfg:Enable";
          type empty;
          description "Enable OSPFv3";
        }
        leaf process-name {
          xr:xr-xml-map "ipv6_ospfv3_cfg:ProcessName";
          type xr:Cisco-ios-xr-string {
            length "0..32";
          }
          description "OSPFv3 process name";
        }
      }
    }
    leaf dns-name-lookup {
      xr:xr-xml-map "ipv6_ospfv3_cfg:DNSNameLookup";
      xr:xr-cli-map "(ipv6 ospf)|(ospfv3) name-lookup ";
      type empty;
      description "Enable OSPFv3 router IDs as DNS names";
    }
  }

  augment "/a1:snmp/a1:notification" {

    container ospfv3 {
      xr:xr-xml-map "ospfv3mib_cfg:OSPFv3";
      description "OSPFv3-MIB notification configuration";

      container error {
        xr:xr-xml-map "ospfv3mib_cfg:Error";
        description "SNMP notifications for OSPF errors";
        leaf config-error {
          xr:xr-xml-map "ospfv3mib_cfg:ConfigError";
          type empty;
          description "Enable ospfv3IfConfigError notification";
        }
        leaf bad-packet {
          xr:xr-xml-map "ospfv3mib_cfg:BadPacket";
          type empty;
          description "Enable ospfv3IfRxBadPacket notification";
        }
        leaf virtual-bad-packet {
          xr:xr-xml-map "ospfv3mib_cfg:VirtualBadPacket";
          type empty;
          description "Enable ospfv3VirtIfRxBadPacket notification";
        }
        leaf virtual-config-error {
          xr:xr-xml-map "ospfv3mib_cfg:VirtualConfigError";
          type empty;
          description "Enable ospfv3VirtIfConfigError notification";
        }
      }

      container state-change {
        xr:xr-xml-map "ospfv3mib_cfg:StateChange";
        description "SNMP notifications for OSPF state change";
        leaf restart-virtual-helper {
          xr:xr-xml-map "ospfv3mib_cfg:RestartVirtualHelper";
          type empty;
          description
            "Enable ospfv3VirtNbrRestartHelperStatusChange
            notification";
        }
        leaf nssa-translator {
          xr:xr-xml-map "ospfv3mib_cfg:NSSATranslator";
          type empty;
          description
            "Enable ospfv3NssaTranslatorStatusChange
            notification";
        }
        leaf interface {
          xr:xr-xml-map "ospfv3mib_cfg:Interface";
          type empty;
          description "Enable ospfv3IfStateChange notification";
        }
        leaf restart {
          xr:xr-xml-map "ospfv3mib_cfg:Restart";
          type empty;
          description
            "Enable ospfv3RestartStatusChange notification";
        }
        leaf neighbor {
          xr:xr-xml-map "ospfv3mib_cfg:Neighbor";
          type empty;
          description "Enable ospfv3NbrStateChange notification";
        }
        leaf virtual-interface {
          xr:xr-xml-map "ospfv3mib_cfg:VirtualInterface";
          type empty;
          description "Enable ospfv3VirtIfStateChange notification";
        }
        leaf restart-helper {
          xr:xr-xml-map "ospfv3mib_cfg:RestartHelper";
          type empty;
          description
            "Enable ospfv3NbrRestartHelperStatusChange
            notification";
        }
        leaf virtual-neighbor {
          xr:xr-xml-map "ospfv3mib_cfg:VirtualNeighbor";
          type empty;
          description
            "Enable ospfv3VirtNbrStateChange notification";
        }
      }
    }
    description
      "This augment extends the configuration data of
      'Cisco-IOS-XR-snmp-agent-cfg'";
  }
}
