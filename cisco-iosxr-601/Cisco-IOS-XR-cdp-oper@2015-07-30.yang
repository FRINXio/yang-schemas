module Cisco-IOS-XR-cdp-oper {

  /*** NAMESPACE / PREFIX DEFINITION ***/

  namespace "http://cisco.com/ns/yang/Cisco-IOS-XR-cdp-oper";


  prefix "cdp-oper";

  /*** LINKAGE (IMPORTS / INCLUDES) ***/

  import Cisco-IOS-XR-types { prefix "xr"; }

  include Cisco-IOS-XR-cdp-oper-sub1 {
    revision-date 2015-07-30;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR cdp package operational data.

     This module contains definitions
     for the following management objects:
       cdp: CDP operational data

     Copyright (c) 2013-2015 by Cisco Systems, Inc.
     All rights reserved.";

  revision "2015-07-30" {
    description
      "Revison descritption string.";
  }

  revision "2015-01-07" {
    description
      "IOS XR 5.3.1 revision.";
  }


  container cdp {
    xr:xr-xml-map "cdp_oper:CDP";
    config false;
    description "CDP operational data";

    container nodes {
      xr:xr-xml-map "cdp_oper:NodeTable";
      description "Per node CDP operational data";

      list node {
        xr:xr-xml-map "cdp_oper:Node";
        key "node-name";
        description
          "The CDP operational data for a particular node";

        container neighbors {
          xr:xr-xml-map "cdp_oper:Neighbors";
          description "The CDP neighbor tables on this node";

          container details {
            xr:xr-xml-map "cdp_oper:DetailTable";
            description "The detailed CDP neighbor table";

            list detail {
              xr:xr-xml-map "cdp_oper:Detail";
              description
                "Detailed information about a CDP neighbor
                entry";
              leaf interface-name {
                xr:xr-xml-map "cdp_oper:InterfaceName";
                type xr:Interface-name;
                description "The interface name";
              }
              leaf device-id {
                xr:xr-xml-map "cdp_oper:DeviceID";
                type string;
                description "The neighboring device identifier";
              }
              uses CDP-NEIGHBOR;
            }
          }

          container devices {
            xr:xr-xml-map "cdp_oper:DeviceTable";
            description "The detailed CDP neighbor table";

            list device {
              xr:xr-xml-map "cdp_oper:Device";
              key "device-id";
              description
                "Detailed information about a CDP neighbor
                entry";
              leaf device-id {
                xr:xr-xml-map "cdp_oper:DeviceID";
                type string;
                description "The neighboring device identifier";
              }
              uses CDP-NEIGHBOR;
            }
          }

          container summaries {
            xr:xr-xml-map "cdp_oper:SummaryTable";
            description "The CDP neighbor summary table";

            list summary {
              xr:xr-xml-map "cdp_oper:Summary";
              description
                "Brief information about a CDP neighbor entry";
              leaf interface-name {
                xr:xr-xml-map "cdp_oper:InterfaceName";
                type xr:Interface-name;
                description "The interface name";
              }
              leaf device-id {
                xr:xr-xml-map "cdp_oper:DeviceID";
                type string;
                description "The neighboring device identifier";
              }
              uses CDP-NEIGHBOR;
            }
          }
        }

        container statistics {
          xr:xr-xml-map "cdp_oper:Statistics";
          description "The CDP traffic statistics for this node";
          uses CDP-STATS;
        }

        container interfaces {
          xr:xr-xml-map "cdp_oper:InterfaceTable";
          description
            "The table of interfaces on which CDP is
            running on this node";

          list interface {
            xr:xr-xml-map "cdp_oper:Interface";
            key "interface-name";
            description
              "Operational data for an interface on which
              CDP is running";
            leaf interface-name {
              xr:xr-xml-map "cdp_oper:InterfaceName";
              type xr:Interface-name;
              description "The interface name";
            }
            uses CDP-INTERFACE;
          }
        }
        leaf node-name {
          xr:xr-xml-map "cdp_oper:NodeName";
          type xr:Node-id;
          description "The identifier for the node";
        }
      }
    }
  }
}
