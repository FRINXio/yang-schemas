module Cisco-IOS-XR-ip-pfilter-oper {

  /*** NAMESPACE / PREFIX DEFINITION ***/

  namespace "http://cisco.com/ns/yang/Cisco-IOS-XR-ip-pfilter-oper";


  prefix "ip-pfilter-oper";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-pfilter package operational data.

     This module contains definitions
     for the following management objects:
       pfilter-ma: Root class of PfilterMa Oper schema

     Copyright (c) 2013-2015 by Cisco Systems, Inc.
     All rights reserved.";

  revision "2015-11-09" {
    description
      "IOS XR 6.0 revision.";
  }


  grouping INTERFACE-TABLE {
    description "Common node of ipv4, ipv6";

    container interfaces {
      xr:xr-xml-map "pfilter_oper:InterfaceTable";
      description "Operational data for pfilter";

      list interface {
        xr:xr-xml-map "pfilter_oper:Interface";
        key "interface-name";
        description "Operational data for pfilter";
        leaf interface-name {
          xr:xr-xml-map "pfilter_oper:InterfaceName";
          type xr:Interface-name;
          description "Name of the interface";
        }
        leaf acl-information {
          xr:xr-xml-map "pfilter_oper:ACLInformation";
          type string;
          mandatory true;
          description "Interface ACL Details";
        }
      }
    }
  }

  container pfilter-ma {
    xr:xr-xml-map "pfilter_oper:PfilterMa";
    config false;
    description "Root class of PfilterMa Oper schema";

    container nodes {
      xr:xr-xml-map "pfilter_oper:NodeTable";
      description "Node-specific operational data";

      list node {
        xr:xr-xml-map "pfilter_oper:Node";
        key "node-name";
        description
          "PfilterMa operational data for a particular
          node";

        container process {
          xr:xr-xml-map "pfilter_oper:Process";
          description "Operational data for pfilter";

          container ipv6 {
            xr:xr-xml-map "pfilter_oper:IPv6";
            description "Operational data for pfilter";
            uses INTERFACE-TABLE;
          }

          container ipv4 {
            xr:xr-xml-map "pfilter_oper:IPv4";
            description "Operational data for pfilter";
            uses INTERFACE-TABLE;
          }
        }
        leaf node-name {
          xr:xr-xml-map "pfilter_oper:NodeName";
          type xr:Node-id;
          description "The node";
        }
      }
    }
  }
}
