module Cisco-IOS-XR-ipv4-acl-oper {

  /*** NAMESPACE / PREFIX DEFINITION ***/

  namespace "http://cisco.com/ns/yang/Cisco-IOS-XR-ipv4-acl-oper";


  prefix "ipv4-acl-oper";

  /*** LINKAGE (IMPORTS / INCLUDES) ***/

  import Cisco-IOS-XR-types { prefix "xr"; }

  import Cisco-IOS-XR-common-acl-datatypes { prefix "dt1"; }

  include Cisco-IOS-XR-ipv4-acl-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-acl package operational data.

     This module contains definitions
     for the following management objects:
       ipv4-acl-and-prefix-list: Root class of IPv4 Oper schema tree

     Copyright (c) 2013-2015 by Cisco Systems, Inc.
     All rights reserved.";

  revision "2015-11-09" {
    description
      "IOS XR 6.0 revision.";
  }


  container ipv4-acl-and-prefix-list {
    xr:xr-xml-map "ipv4_acl_oper:IPV4_ACLAndPrefixList";
    config false;
    description "Root class of IPv4 Oper schema tree";

    container access-list-manager {
      xr:xr-xml-map "ipv4_acl_oper:AccessListManager";
      description
        "Access list manager containing access lists and
        prefix lists";

      container prefixes {
        xr:xr-xml-map "ipv4_acl_oper:PrefixListTable";
        description "Table of prefix lists";

        list prefix {
          xr:xr-xml-map "ipv4_acl_oper:PrefixList";
          key "prefix-list-name";
          description "Name of the prefix list";

          container prefix-list-sequences {
            xr:xr-xml-map "ipv4_acl_oper:PrefixListSequenceTable";
            description
              "Table of all the SequenceNumbers per prefix
              list";

            list prefix-list-sequence {
              xr:xr-xml-map "ipv4_acl_oper:PrefixListSequence";
              key "sequence-number";
              description "Sequence Number of a prefix list entry";
              leaf sequence-number {
                xr:xr-xml-map "ipv4_acl_oper:SequenceNumber";
                type dt1:Acl-sequence-number-range;
                description
                  "Sequence Number of the prefix list entry";
              }
              uses IPV4-PFX-EDM-ACE;
            }
          }
          leaf prefix-list-name {
            xr:xr-xml-map "ipv4_acl_oper:PrefixListName";
            type string;
            description "Name of the prefix list";
          }
        }
      }

      container accesses {
        xr:xr-xml-map "ipv4_acl_oper:AccessListTable";
        description
          "Access listL class displaying Usage and Entries";

        list access {
          xr:xr-xml-map "ipv4_acl_oper:AccessList";
          key "access-list-name";
          description "Name of the Access List";

          container access-list-sequences {
            xr:xr-xml-map "ipv4_acl_oper:AccessListSequenceTable";
            description
              "Table of all the SequenceNumbers per access
              list";

            list access-list-sequence {
              xr:xr-xml-map "ipv4_acl_oper:AccessListSequence";
              key "sequence-number";
              description "Sequence Number of an access list entry";
              leaf sequence-number {
                xr:xr-xml-map "ipv4_acl_oper:SequenceNumber";
                type dt1:Acl-sequence-number-range;
                description "ACLEntry Sequence Number";
              }
              uses IPV4-ACL-EDM-ACE;
            }
          }
          leaf access-list-name {
            xr:xr-xml-map "ipv4_acl_oper:AccessListName";
            type string;
            description "Name of the Access List";
          }
        }
      }

      container usages {
        xr:xr-xml-map "ipv4_acl_oper:UsageTable";
        description
          "Table of Usage statistics of access lists at
          different nodes";

        list usage {
          xr:xr-xml-map "ipv4_acl_oper:Usage";
          description
            "Usage statistics of an access list at a node";
          leaf node-name {
            xr:xr-xml-map "ipv4_acl_oper:NodeName";
            type xr:Node-id;
            description "Node where access list is applied";
          }
          leaf application-id {
            xr:xr-xml-map "ipv4_acl_oper:ApplicationID";
            type dt1:Acl-usage-app-id-enum;
            description "Application ID";
          }
          leaf access-list-name {
            xr:xr-xml-map "ipv4_acl_oper:AccessListName";
            type string;
            description "Name of the access list";
          }
          leaf usage-details {
            xr:xr-xml-map "ipv4_acl_oper:UsageDetails";
            type string;
            mandatory true;
            description "Usage Statistics Details";
          }
        }
      }
    }

    container oor {
      xr:xr-xml-map "ipv4_acl_oper:OOR";
      description
        "Out Of Resources, Limits to the resources
        allocatable";

      container details {
        xr:xr-xml-map "ipv4_acl_oper:Details";
        description
          "Details of the Overall Out Of Resources Limits";
        uses IPV4-ACL-EDM-OOR-DETAIL;
      }

      container oor-prefixes {
        xr:xr-xml-map "ipv4_acl_oper:OORPrefixListTable";
        description "Resource occupation details for prefix lists";

        list oor-prefix {
          xr:xr-xml-map "ipv4_acl_oper:OORPrefixList";
          key "prefix-list-name";
          description
            "Resource occupation details for a particular
            prefix list";
          leaf prefix-list-name {
            xr:xr-xml-map "ipv4_acl_oper:PrefixListName";
            type string;
            description "Name of a prefix list";
          }
          uses IPV4-ACL-EDM-OOR-DETAIL;
        }
      }

      container oor-accesses {
        xr:xr-xml-map "ipv4_acl_oper:OORAccessListTable";
        description "Resource occupation details for access lists";

        list oor-access {
          xr:xr-xml-map "ipv4_acl_oper:OORAccessList";
          key "access-list-name";
          description
            "Resource occupation details for a particular
            access list";
          leaf access-list-name {
            xr:xr-xml-map "ipv4_acl_oper:AccessListName";
            type string;
            description "Name of the Access List";
          }
          uses IPV4-ACL-EDM-OOR-DETAIL;
        }
      }

      container access-list-summary {
        xr:xr-xml-map "ipv4_acl_oper:AccessListSummary";
        description
          "Resource limits pertaining to access lists only";

        container details {
          xr:xr-xml-map "ipv4_acl_oper:Details";
          description
            "Details containing the resource limits of the
            access lists";
          uses IPV4-ACL-EDM-OOR-DETAIL;
        }
      }

      container prefix-list-summary {
        xr:xr-xml-map "ipv4_acl_oper:PrefixListSummary";
        description
          "Summary of the prefix Lists resource
          utilization";

        container details {
          xr:xr-xml-map "ipv4_acl_oper:Details";
          description
            "Summary Detail of the prefix list Resource
            Utilisation";
          uses IPV4-ACL-EDM-OOR-DETAIL;
        }
      }
    }
  }
}
