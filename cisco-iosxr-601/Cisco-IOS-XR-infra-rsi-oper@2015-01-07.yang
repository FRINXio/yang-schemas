module Cisco-IOS-XR-infra-rsi-oper {

  /*** NAMESPACE / PREFIX DEFINITION ***/

  namespace "http://cisco.com/ns/yang/Cisco-IOS-XR-infra-rsi-oper";


  prefix "infra-rsi-oper";

  /*** LINKAGE (IMPORTS / INCLUDES) ***/

  import Cisco-IOS-XR-types { prefix "xr"; }

  include Cisco-IOS-XR-infra-rsi-oper-sub2 {
    revision-date 2015-01-07;
  }

  include Cisco-IOS-XR-infra-rsi-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rsi package operational data.

     This module contains definitions
     for the following management objects:
       vrf-group: VRF group operational data
       srlg: srlg
       selective-vrf-download: selective vrf download

     Copyright (c) 2013-2015 by Cisco Systems, Inc.
     All rights reserved.";

  revision "2015-01-07" {
    description
      "IOS XR 5.3.1 revision.";
  }


  container vrf-group {
    xr:xr-xml-map "rsi_vrfgroup_oper:VRFGroup";
    config false;
    description "VRF group operational data";

    container nodes {
      xr:xr-xml-map "rsi_vrfgroup_oper:NodeTable";
      description "Node operational data";

      list node {
        xr:xr-xml-map "rsi_vrfgroup_oper:Node";
        key "node-name";
        description "Node details";

        container groups {
          xr:xr-xml-map "rsi_vrfgroup_oper:GroupTable";
          description "Group operational data";

          list group {
            xr:xr-xml-map "rsi_vrfgroup_oper:Group";
            key "group-name";
            description "Group details";
            leaf group-name {
              xr:xr-xml-map "rsi_vrfgroup_oper:GroupName";
              type xr:Cisco-ios-xr-string {
                length "0..32";
              }
              description "Group name";
            }
            uses RSI-VRFGROUP-GROUP-SHOW;
          }
        }
        leaf node-name {
          xr:xr-xml-map "rsi_vrfgroup_oper:NodeName";
          type xr:Node-id;
          description "Node";
        }
      }
    }
  }

  container srlg {
    xr:xr-xml-map "rsi_srlg_oper_gl:SRLG";
    config false;
    description "srlg";

    container srlg-maps {
      xr:xr-xml-map "rsi_srlg_oper_gl:SRLGMapTable";
      description "Set of SRLG name, value maps configured";

      list srlg-map {
        xr:xr-xml-map "rsi_srlg_oper_gl:SRLGMap";
        key "srlg-name";
        description "Configured SRLG name details ";
        leaf srlg-name {
          xr:xr-xml-map "rsi_srlg_oper_gl:SRLGName";
          type xr:Cisco-ios-xr-string {
            length "0..64";
          }
          description "SRLG name";
        }
        uses RSI-SRLG-NAME-VALUE-SHOW;
      }
    }

    container nodes {
      xr:xr-xml-map "rsi_srlg_oper:NodeTable";
      description "RSI SRLG operational data";

      list node {
        xr:xr-xml-map "rsi_srlg_oper:Node";
        key "node-name";
        description "RSI SRLG operational data";

        container srlg-maps {
          xr:xr-xml-map "rsi_srlg_oper:SRLGMapTable";
          description "Set of SRLG name, value maps configured";

          list srlg-map {
            xr:xr-xml-map "rsi_srlg_oper:SRLGMap";
            key "srlg-name";
            description "Configured SRLG name details ";
            leaf srlg-name {
              xr:xr-xml-map "rsi_srlg_oper:SRLGName";
              type xr:Cisco-ios-xr-string {
                length "0..64";
              }
              description "SRLG name";
            }
            uses RSI-SRLG-NAME-VALUE-SHOW;
          }
        }

        container groups {
          xr:xr-xml-map "rsi_srlg_oper:GroupTable";
          description "Set of Groups configured for SRLG";

          list group {
            xr:xr-xml-map "rsi_srlg_oper:Group";
            key "group-name";
            description "SRLG group details";
            leaf group-name {
              xr:xr-xml-map "rsi_srlg_oper:GroupName";
              type xr:Cisco-ios-xr-string;
              description "Group name";
            }
            uses RSI-SRLG-GROUP-SHOW;
          }
        }

        container inherit-nodes {
          xr:xr-xml-map "rsi_srlg_oper:InheritNodeTable";
          description
            "Set of inherit locations configured for SRLG";

          list inherit-node {
            xr:xr-xml-map "rsi_srlg_oper:InheritNode";
            key "inherit-node-name";
            description "SRLG inherit location details";
            leaf inherit-node-name {
              xr:xr-xml-map "rsi_srlg_oper:InheritNodeName";
              type xr:Pq-node-id;
              description "Inherit node";
            }
            uses RSI-SRLG-INHLOC-SHOW;
          }
        }

        container interfaces {
          xr:xr-xml-map "rsi_srlg_oper:InterfaceTable";
          description "Set of interfaces configured for SRLG";

          list interface {
            xr:xr-xml-map "rsi_srlg_oper:Interface";
            key "interface-name";
            description "SRLG interface summary";
            leaf interface-name {
              xr:xr-xml-map "rsi_srlg_oper:InterfaceName";
              type xr:Interface-name;
              description "Interface name";
            }
            uses RSI-SRLG-INTF-BRIEF-SHOW;
          }
        }

        container interface-details {
          xr:xr-xml-map "rsi_srlg_oper:InterfaceDetailTable";
          description "Set of interfaces configured for SRLG";

          list interface-detail {
            xr:xr-xml-map "rsi_srlg_oper:InterfaceDetail";
            key "interface-name";
            description "SRLG interface details";
            leaf interface-name {
              xr:xr-xml-map "rsi_srlg_oper:InterfaceName";
              type xr:Interface-name;
              description "Interface name";
            }
            uses RSI-SRLG-INTF-DETAIL-SHOW;
          }
        }

        container srlg-values {
          xr:xr-xml-map "rsi_srlg_oper:SRLGValueTable";
          description "Set of SRLG values configured";

          list srlg-value {
            xr:xr-xml-map "rsi_srlg_oper:SRLGValue";
            key "value";
            description "Configured SRLG value details ";
            leaf value {
              xr:xr-xml-map "rsi_srlg_oper:Value";
              type int32;
              description "SRLG value";
            }
            uses RSI-SRLG-INTF-SHOW;
          }
        }

        container interface-srlg-names {
          xr:xr-xml-map "rsi_srlg_oper:InterfaceSRLGNameTable";
          description "Set of SRLG names configured";

          list interface-srlg-name {
            xr:xr-xml-map "rsi_srlg_oper:InterfaceSRLGName";
            key "srlg-name";
            description "Configured SRLG name details ";
            leaf srlg-name {
              xr:xr-xml-map "rsi_srlg_oper:SRLGName";
              type xr:Cisco-ios-xr-string {
                length "0..64";
              }
              description "SRLG name";
            }
            uses RSI-SRLG-NAME-INTF-SHOW;
          }
        }
        leaf node-name {
          xr:xr-xml-map "rsi_srlg_oper:NodeName";
          type xr:Node-id;
          description "Node";
        }
      }
    }

    container interface-srlg-names {
      xr:xr-xml-map "rsi_srlg_oper_gl:InterfaceSRLGNameTable";
      description "Set of SRLG names configured";

      list interface-srlg-name {
        xr:xr-xml-map "rsi_srlg_oper_gl:InterfaceSRLGName";
        key "srlg-name";
        description "Configured SRLG name details ";
        leaf srlg-name {
          xr:xr-xml-map "rsi_srlg_oper_gl:SRLGName";
          type xr:Cisco-ios-xr-string {
            length "0..64";
          }
          description "SRLG name";
        }
        uses RSI-SRLG-NAME-INTF-SHOW;
      }
    }
  }

  container selective-vrf-download {
    xr:xr-xml-map "rsi_svd_oper:SelectiveVRFDownload";
    config false;
    description "selective vrf download";

    container state {
      xr:xr-xml-map "rsi_svd_oper:State";
      description "Selective VRF Download feature state details";
      uses RSI-MASTER-STATE;
    }
  }
}
