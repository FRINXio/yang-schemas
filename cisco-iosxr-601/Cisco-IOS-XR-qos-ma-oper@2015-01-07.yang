module Cisco-IOS-XR-qos-ma-oper {

  /*** NAMESPACE / PREFIX DEFINITION ***/

  namespace "http://cisco.com/ns/yang/Cisco-IOS-XR-qos-ma-oper";


  prefix "qos-ma-oper";

  /*** LINKAGE (IMPORTS / INCLUDES) ***/

  import Cisco-IOS-XR-types { prefix "xr"; }

  include Cisco-IOS-XR-qos-ma-oper-sub2 {
    revision-date 2015-01-07;
  }

  include Cisco-IOS-XR-qos-ma-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR qos-ma package operational data.

     This module contains definitions
     for the following management objects:
       qos: QoS operational data

     Copyright (c) 2013-2015 by Cisco Systems, Inc.
     All rights reserved.";

  revision "2015-01-07" {
    description
      "IOS XR 5.3.1 revision.";
  }


  grouping STATISTICS {
    description "Common node of input, output";
  }

  grouping QOS-PI-ASR9K-OPER-STATISTICS {
    description "Common node of input, output";

    container statistics {
      xr:xr-xml-map "qos_pi_asr9k_oper:Statistics";
      description
        "Policy-map statistics operational data for an
        interface";
      uses QOS-STATS;
    }
  }

  grouping QOS-PI-SKYWARP-OPER-STATISTICS {
    description "Common node of input, output";

    container statistics {
      xr:xr-xml-map "qos_pi_skywarp_oper:Statistics";
      description
        "Policy-map statistics operational data for an
        interface";
      uses QOS-STATS;
    }
  }

  grouping INTERFACE {
    description
      "Common node of interface-table,
      nv-interface-table";

    list interface {
      xr:xr-xml-map "qos_pi_asr9k_oper:Interface";
      key "interface-name";
      description
        "QoS policy-map operational data for a particular
        interface";
      leaf interface-name {
        xr:xr-xml-map "qos_pi_asr9k_oper:InterfaceName";
        type xr:Interface-name;
        description "Name of the interface";
      }
      uses MEMBER-INTERFACE-TABLE;
      uses SATELLITE-ID-TABLE;
      uses QOS-PI-ASR9K-OPER-INPUT;
      uses QOS-PI-ASR9K-OPER-OUTPUT;
    }
  }

  grouping QOS-PI-SKYWARP-OPER-INTERFACE {
    description
      "Common node of interface-table,
      nv-interface-table";
  }

  grouping QOS-EA-FRETTA-PI-OPER-INTERFACE {
    description
      "Common node of interface-table,
      nv-interface-table";
  }

  grouping INPUT {
    description
      "Common node of interface, node,
      nv-satellite-interface, satellite-id";
  }

  grouping QOS-MA-NV-STATUS-OPER-INPUT {
    description
      "Common node of member-interface,
      nv-satellite-interface";

    container input {
      xr:xr-xml-map "qos_ma_nv_status_oper:Input";
      description
        "A piece of QoS policy-map operational data for
        an interface";
      uses STATUS;
    }
  }

  grouping QOS-PI-ASR9K-OPER-INPUT {
    description
      "Common node of shared-policy-instance,
      member-interface, interface,
      nv-satellite-interface, satellite-id";

    container input {
      xr:xr-xml-map "qos_pi_asr9k_oper:Input";
      description
        "A piece of QoS policy-map operational data for
        an interface";
      uses QOS-PI-ASR9K-OPER-STATISTICS;
    }
  }

  grouping QOS-PI-SKYWARP-OPER-INPUT {
    description
      "Common node of shared-policy-instance,
      member-interface, interface,
      nv-satellite-interface, satellite-id";

    container input {
      xr:xr-xml-map "qos_pi_skywarp_oper:Input";
      description
        "A piece of QoS policy-map operational data for
        an interface";
      uses QOS-PI-SKYWARP-OPER-STATISTICS;
    }
  }

  grouping VO-Q-STATS {
    description
      "Common node of locationvo-q, output-vo-q,
      vo-qoutput";
  }

  grouping QOS-EA-FRETTA-PI-OPER-VO-Q-STATS {
    description
      "Common node of locationvo-q, output-vo-q,
      vo-qoutput";

    container vo-q-stats {
      xr:xr-xml-map "qos_ea_fretta_pi_oper:VoQStats";
      description
        "VoQ statistics operational data for an interface";
      uses QOS-STATS;
    }
  }

  grouping QOS-PI-ASR9K-OPER-VO-Q-STATS {
    description
      "Common node of locationvo-q, output-vo-q,
      vo-qoutput";
  }

  grouping MEMBER-INTERFACE-TABLE {
    description
      "Common node of interface, nv-satellite-interface,
      shared-policy-instance";

    container member-interfaces {
      xr:xr-xml-map "qos_pi_asr9k_oper:MemberInterfaceTable";
      description "QoS policy-map member interface table";

      list member-interface {
        xr:xr-xml-map "qos_pi_asr9k_oper:MemberInterface";
        key "interface-name";
        description "QoS policy-map member interface statistics";
        leaf interface-name {
          xr:xr-xml-map "qos_pi_asr9k_oper:InterfaceName";
          type xr:Interface-name;
          description "Name of member interface";
        }
        uses SATELLITE-ID-TABLE;
        uses QOS-PI-ASR9K-OPER-INPUT;
        uses QOS-PI-ASR9K-OPER-OUTPUT;
      }
    }
  }

  grouping QOS-EA-FRETTA-PI-OPER-MEMBER-INTERFACE-TABLE {
    description "Common node of interface, nv-satellite-interface";
  }

  grouping QOS-PI-SKYWARP-OPER-MEMBER-INTERFACE-TABLE {
    description
      "Common node of interface, nv-satellite-interface,
      shared-policy-instance";

    container member-interfaces {
      xr:xr-xml-map "qos_pi_skywarp_oper:MemberInterfaceTable";
      description "QoS policy-map member interface table";

      list member-interface {
        xr:xr-xml-map "qos_pi_skywarp_oper:MemberInterface";
        key "interface-name";
        description "QoS policy-map member interface statistics";
        leaf interface-name {
          xr:xr-xml-map "qos_pi_skywarp_oper:InterfaceName";
          type xr:Interface-name;
          description "Name of member interface";
        }
        uses OUTPUT;
        uses QOS-PI-SKYWARP-OPER-INPUT;
        uses QOS-PI-SKYWARP-OPER-SATELLITE-ID-TABLE;
      }
    }
  }

  grouping STATUS {
    description
      "Common node of input, output,
      nv-satellite-interface";

    container status {
      xr:xr-xml-map "qos_ma_nv_status_oper:Status";
      description
        "Policy-map status operational data for an
        interface";
      uses QOS-MA-SAT-IF-EDM-INFO-XML;
    }
  }

  grouping INTERFACE-TABLE {
    description "Common node of qos, policy-map";

    container interface-table {
      xr:xr-xml-map "qos_ma_oper:InterfaceTable";
      description "Operational data for all interfaces";
      uses INTERFACE;
    }
  }

  grouping OUTPUT {
    description
      "Common node of shared-policy-instance,
      member-interface, interface,
      nv-satellite-interface, satellite-id";

    container output {
      xr:xr-xml-map "qos_pi_skywarp_oper:Output";
      description
        "A piece of QoS policy-map operational data for
        an interface";
      uses QOS-PI-SKYWARP-OPER-STATISTICS;
    }
  }

  grouping QOS-MA-NV-STATUS-OPER-OUTPUT {
    description
      "Common node of member-interface,
      nv-satellite-interface";

    container output {
      xr:xr-xml-map "qos_ma_nv_status_oper:Output";
      description
        "A piece of QoS policy-map operational data for
        an interface";
      uses STATUS;
    }
  }

  grouping QOS-EA-FRETTA-PI-OPER-OUTPUT {
    description
      "Common node of member-interface, interface, node,
      nv-satellite-interface, satellite-id";
  }

  grouping QOS-PI-ASR9K-OPER-OUTPUT {
    description
      "Common node of shared-policy-instance,
      member-interface, interface,
      nv-satellite-interface, satellite-id";

    container output {
      xr:xr-xml-map "qos_pi_asr9k_oper:Output";
      description
        "A piece of QoS policy-map operational data for
        an interface";
      uses QOS-PI-ASR9K-OPER-STATISTICS;
    }
  }

  grouping SATELLITE-ID-TABLE {
    description "Common node of interface, member-interface";

    container satellite-ids {
      xr:xr-xml-map "qos_pi_asr9k_oper:SatelliteIDTable";
      description "Satellite ID information";

      list satellite-id {
        xr:xr-xml-map "qos_pi_asr9k_oper:SatelliteID";
        key "nv-satellite-id";
        description "Satellite ID information";
        leaf nv-satellite-id {
          xr:xr-xml-map "qos_pi_asr9k_oper:nVSatelliteID";
          type int32;
          description "Satellite ID";
        }
        uses QOS-PI-ASR9K-OPER-INPUT;
        uses QOS-PI-ASR9K-OPER-OUTPUT;
      }
    }
  }

  grouping QOS-EA-FRETTA-PI-OPER-SATELLITE-ID-TABLE {
    description "Common node of interface, member-interface";
  }

  grouping QOS-PI-SKYWARP-OPER-SATELLITE-ID-TABLE {
    description "Common node of interface, member-interface";

    container satellite-ids {
      xr:xr-xml-map "qos_pi_skywarp_oper:SatelliteIDTable";
      description "Satellite ID information";

      list satellite-id {
        xr:xr-xml-map "qos_pi_skywarp_oper:SatelliteID";
        key "nv-satellite-id";
        description "Satellite ID information";
        leaf nv-satellite-id {
          xr:xr-xml-map "qos_pi_skywarp_oper:nVSatelliteID";
          type int32;
          description "Satellite ID";
        }
        uses OUTPUT;
        uses QOS-PI-SKYWARP-OPER-INPUT;
      }
    }
  }

  container qos {
    xr:xr-xml-map "qos_ma_oper:QOS";
    config false;
    description "QoS operational data";

    container nv-interface-table {
      xr:xr-xml-map "qos_ma_oper:nVInterfaceTable";
      description "Operational data for satellite interfaces";
      uses INTERFACE;
    }

    container nv-satellite {
      xr:xr-xml-map "qos_ma_oper:nVSatellite";
      description "Satellite table";

      container nv-satellite-statistics {
        xr:xr-xml-map "qos_ma_oper:nVSatelliteStatistics";
        description "Satellite statistics based on Satellite ID";

        container nv-satellite-ids {
          xr:xr-xml-map "qos_ma_oper:nVSatelliteIDTable";
          description "Satellite ID table";

          list nv-satellite-id {
            xr:xr-xml-map "qos_ma_oper:nVSatelliteID";
            key "satellite-id";
            description "Satellite ID information";

            container nv-satellite-interfaces {
              xr:xr-xml-map "qos_pi_skywarp_oper:nVSatelliteInterfa"+
                "ceTable";
              description
                "Operational data of satellite interface of a
                particular satellite";

              list nv-satellite-interface {
                xr:xr-xml-map "qos_pi_skywarp_oper:nVSatelliteInter"+
                  "face";
                key "interface-name";
                description
                  "Operational data for a particular satellite
                  interface";
                leaf interface-name {
                  xr:xr-xml-map "qos_pi_skywarp_oper:InterfaceName";
                  type xr:Interface-name;
                  description "Name of the interface";
                }
                uses OUTPUT;
                uses QOS-PI-SKYWARP-OPER-INPUT;
                uses QOS-PI-SKYWARP-OPER-MEMBER-INTERFACE-TABLE;
              }
            }
            leaf satellite-id {
              xr:xr-xml-map "qos_ma_oper:SatelliteID";
              type int32;
              description "Satellite ID";
            }
          }
        }
      }

      container nv-satellite-status {
        xr:xr-xml-map "qos_ma_nv_status_oper:nVSatelliteStatus";
        description
          "Satellite QOS offload status based on Satellite
          ID";

        container nv-satellite-ids {
          xr:xr-xml-map "qos_ma_nv_status_oper:nVSatelliteIDTable";
          description "Satellite ID table";

          list nv-satellite-id {
            xr:xr-xml-map "qos_ma_nv_status_oper:nVSatelliteID";
            key "satellite-id";
            description "Satellite ID information";

            container nv-satellite-interfaces {
              xr:xr-xml-map "qos_ma_nv_status_oper:nVSatelliteInter"+
                "faceTable";
              description
                "QOS offload status of satellite interface of
                a particular satellite";

              list nv-satellite-interface {
                xr:xr-xml-map "qos_ma_nv_status_oper:nVSatelliteInt"+
                  "erface";
                key "interface-name";
                description
                  "QOS offload status for a particular
                  satellite interface";

                container member-interfaces {
                  xr:xr-xml-map "qos_ma_nv_status_oper:MemberInterf"+
                    "aceTable";
                  description "Satellite member interface table";

                  list member-interface {
                    xr:xr-xml-map "qos_ma_nv_status_oper:MemberInte"+
                      "rface";
                    key "interface-name";
                    description
                      "Satellite member interface statistics";
                    leaf interface-name {
                      xr:xr-xml-map "qos_ma_nv_status_oper:Interfac"+
                        "eName";
                      type xr:Interface-name;
                      description "Name of member interface";
                    }
                    uses QOS-MA-NV-STATUS-OPER-INPUT;
                    uses QOS-MA-NV-STATUS-OPER-OUTPUT;
                  }
                }
                leaf interface-name {
                  xr:xr-xml-map "qos_ma_nv_status_oper:InterfaceNam"+
                    "e";
                  type xr:Interface-name;
                  description "Name of the interface";
                }
                uses QOS-MA-NV-STATUS-OPER-INPUT;
                uses STATUS;
                uses QOS-MA-NV-STATUS-OPER-OUTPUT;
              }
            }
            leaf satellite-id {
              xr:xr-xml-map "qos_ma_nv_status_oper:SatelliteID";
              type int32;
              description "Satellite ID";
            }
          }
        }
      }
    }

    container nodes {
      xr:xr-xml-map "qos_ma_oper:NodeTable";
      description "Node-specific QoS operational data";

      list node {
        xr:xr-xml-map "qos_ma_oper:Node";
        key "node-name";
        description "QoS operational data for a particular node";

        container policy-map {
          xr:xr-xml-map "qos_ma_oper:PolicyMap";
          description "Operational data for policymaps";

          container shared-policy-instances {
            xr:xr-xml-map "qos_pi_asr9k_oper:SharedPolicyInstanceTa"+
              "ble";
            description "Operational data for all SPI";

            list shared-policy-instance {
              xr:xr-xml-map "qos_pi_asr9k_oper:SharedPolicyInstance";
              key "spi-name";
              description
                "QoS policy-map operational data for a
                particular SPI ";
              leaf spi-name {
                xr:xr-xml-map "qos_pi_asr9k_oper:SPIName";
                type xr:Cisco-ios-xr-string;
                description "Name of the shared policy instance";
              }
              uses MEMBER-INTERFACE-TABLE;
              uses QOS-PI-ASR9K-OPER-INPUT;
              uses QOS-PI-ASR9K-OPER-OUTPUT;
            }
          }
          uses INTERFACE-TABLE;
        }
        leaf node-name {
          xr:xr-xml-map "qos_ma_oper:NodeName";
          type xr:Node-id;
          description "The node";
        }
      }
    }

    container qos-global {
      xr:xr-xml-map "qos_ma_oper:QOSGlobal";
      description "For global registrations";

      container vo-q {
        xr:xr-xml-map "qos_ma_oper:VoQ";
        description "For VoQ operational data";

        container vo-q-statistics {
          xr:xr-xml-map "qos_ma_oper:VoQStatistics";
          description "For VoQ statistics";

          container vo-qinterfaces {
            xr:xr-xml-map "qos_ma_oper:VoQTable";
            description "VoQ interface";

            list vo-qinterface {
              xr:xr-xml-map "qos_ea_fretta_pi_oper:VoQinterface";
              key "interface-name";
              description
                "QoS policy-map operational data for a
                particular interface";

              container vo-q-member-interfaces {
                xr:xr-xml-map "qos_ea_fretta_pi_oper:VoQMemberInter"+
                  "faceTable";
                description
                  "VoQ QoS policy-map member interface table";

                list vo-q-member-interface {
                  xr:xr-xml-map "qos_ea_fretta_pi_oper:VoQMemberInt"+
                    "erface";
                  key "interface-name";
                  description
                    "QoS policy-map member interface statistics";

                  container vo-qoutput {
                    xr:xr-xml-map "qos_ea_fretta_pi_oper:VoQoutput";
                    description "output VoQ interface";
                    uses QOS-EA-FRETTA-PI-OPER-VO-Q-STATS;
                  }
                  leaf interface-name {
                    xr:xr-xml-map "qos_ea_fretta_pi_oper:InterfaceN"+
                      "ame";
                    type xr:Interface-name;
                    description "Name of member interface";
                  }
                }
              }

              container output-vo-q {
                xr:xr-xml-map "qos_ea_fretta_pi_oper:OutputVoQ";
                description "output VoQ interface";

                container locationvo-qs {
                  xr:xr-xml-map "qos_ea_fretta_pi_oper:LocationTabl"+
                    "eVoQ";
                  description "QoS policy-map location table";

                  list locationvo-q {
                    xr:xr-xml-map "qos_ea_fretta_pi_oper:LocationVo"+
                      "Q";
                    key "node-name";
                    description
                      "QoS operational data for a particular
                      location";
                    leaf node-name {
                      xr:xr-xml-map "qos_ea_fretta_pi_oper:NodeName";
                      type xr:Node-id;
                      description "The node";
                    }
                    uses QOS-EA-FRETTA-PI-OPER-VO-Q-STATS;
                  }
                }
                uses QOS-EA-FRETTA-PI-OPER-VO-Q-STATS;
              }
              leaf interface-name {
                xr:xr-xml-map "qos_ea_fretta_pi_oper:InterfaceName";
                type xr:Interface-name;
                description "Name of the interface";
              }
            }
          }
        }
      }
    }
    uses INTERFACE-TABLE;
  }
}
