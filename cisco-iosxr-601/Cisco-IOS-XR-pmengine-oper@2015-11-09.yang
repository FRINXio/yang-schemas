module Cisco-IOS-XR-pmengine-oper {

  /*** NAMESPACE / PREFIX DEFINITION ***/

  namespace "http://cisco.com/ns/yang/Cisco-IOS-XR-pmengine-oper";


  prefix "pmengine-oper";

  /*** LINKAGE (IMPORTS / INCLUDES) ***/

  import Cisco-IOS-XR-types { prefix "xr"; }

  include Cisco-IOS-XR-pmengine-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pmengine package operational data.

     This module contains definitions
     for the following management objects:
       performance-management: performace data
       performance-management-history: performance management history

     Copyright (c) 2013-2015 by Cisco Systems, Inc.
     All rights reserved.";

  revision "2015-11-09" {
    description
      "IOS XR 6.0 revision.";
  }


  container performance-management {
    xr:xr-xml-map "pm_ma_oper:PerformanceManagement";
    config false;
    description "performace data";

    container ho-vc {
      xr:xr-xml-map "pm_ma_oper:ho_vc";
      description "HO_VC controller performance data";

      container ho-vc-ports {
        xr:xr-xml-map "pm_ma_oper:Ho_vcPortTable";
        description "Port performance data";

        list ho-vc-port {
          xr:xr-xml-map "pm_ma_oper:Ho_vcPort";
          key "name";
          description "Port performance data";

          container ho-vc-current {
            xr:xr-xml-map "pm_ma_oper:Ho_vcCurrent";
            description "port current performance data";

            container ho-vc-hour24 {
              xr:xr-xml-map "pm_ma_oper:Ho_vcHour24";
              description "port current performance data";

              container ho-vc-hour24-paths {
                xr:xr-xml-map "pm_ma_oper:Ho_vcHour24PathTable";
                description "port current performance data";

                list ho-vc-hour24-path {
                  xr:xr-xml-map "pm_ma_oper:Ho_vcHour24Path";
                  key "number";
                  description "port 24 hour Path performance data";
                  leaf number {
                    xr:xr-xml-map "pm_ma_oper:Number";
                    type int32;
                    description "channel number";
                  }
                  uses PM-HO-VC-PARAS;
                }
              }
            }

            container ho-vc-minute15 {
              xr:xr-xml-map "pm_ma_oper:Ho_vcMinute15";
              description "port current performance data";

              container ho-vc-minute15-paths {
                xr:xr-xml-map "pm_ma_oper:Ho_vcMinute15PathTable";
                description "port current performance data";

                list ho-vc-minute15-path {
                  xr:xr-xml-map "pm_ma_oper:Ho_vcMinute15Path";
                  key "number";
                  description
                    "port 15-minute Path performance data";
                  leaf number {
                    xr:xr-xml-map "pm_ma_oper:Number";
                    type int32;
                    description "channel number";
                  }
                  uses PM-HO-VC-PARAS;
                }
              }
            }
          }
          leaf name {
            xr:xr-xml-map "pm_ma_oper:Name";
            type xr:Interface-name;
            description "Port name";
          }
        }
      }
    }

    container odu {
      xr:xr-xml-map "pm_ma_oper:odu";
      description "ODU controller performance data";

      container odu-ports {
        xr:xr-xml-map "pm_ma_oper:OduPortTable";
        description "Port performance data";

        list odu-port {
          xr:xr-xml-map "pm_ma_oper:OduPort";
          key "name";
          description "Port performance data";

          container odu-current {
            xr:xr-xml-map "pm_ma_oper:OduCurrent";
            description "port current performance data";

            container odu-minute15 {
              xr:xr-xml-map "pm_ma_oper:OduMinute15";
              description "port current performance data";

              container odu-minute15gfps {
                xr:xr-xml-map "pm_ma_oper:OduMinute15GFPTable";
                description "port current performance data";

                list odu-minute15gfp {
                  xr:xr-xml-map "pm_ma_oper:OduMinute15GFP";
                  key "number";
                  description "port 15-minute otn performance data";
                  leaf number {
                    xr:xr-xml-map "pm_ma_oper:Number";
                    type int32;
                    description "channel number";
                  }
                  uses PM-GFP-PARAS;
                }
              }

              container odu-minute15prbses {
                xr:xr-xml-map "pm_ma_oper:OduMinute15PRBSTable";
                description "port current performance data";

                list odu-minute15prbs {
                  xr:xr-xml-map "pm_ma_oper:OduMinute15PRBS";
                  key "number";
                  description
                    "port 15-minute prbs performance data";
                  leaf number {
                    xr:xr-xml-map "pm_ma_oper:Number";
                    type int32;
                    description "channel number";
                  }
                  uses PM-PRBS-PARAS;
                }
              }

              container odu-minute15otns {
                xr:xr-xml-map "pm_ma_oper:OduMinute15OTNTable";
                description "port current performance data";

                list odu-minute15otn {
                  xr:xr-xml-map "pm_ma_oper:OduMinute15OTN";
                  key "number";
                  description "port 15-minute otn performance data";
                  leaf number {
                    xr:xr-xml-map "pm_ma_oper:Number";
                    type int32;
                    description "channel number";
                  }
                  uses PM-OTN-PARAS;
                }
              }
            }

            container odu-hour24 {
              xr:xr-xml-map "pm_ma_oper:OduHour24";
              description "port current performance data";

              container odu-hour24prbses {
                xr:xr-xml-map "pm_ma_oper:OduHour24PRBSTable";
                description "port 24 hour performance data";

                list odu-hour24prbs {
                  xr:xr-xml-map "pm_ma_oper:OduHour24PRBS";
                  key "number";
                  description "port 24 hour otn performance data";
                  leaf number {
                    xr:xr-xml-map "pm_ma_oper:Number";
                    type int32;
                    description "channel number";
                  }
                  uses PM-PRBS-PARAS;
                }
              }

              container odu-hour24gfps {
                xr:xr-xml-map "pm_ma_oper:OduHour24GFPTable";
                description "port 24 hour performance data";

                list odu-hour24gfp {
                  xr:xr-xml-map "pm_ma_oper:OduHour24GFP";
                  key "number";
                  description "port 24 hour otn performance data";
                  leaf number {
                    xr:xr-xml-map "pm_ma_oper:Number";
                    type int32;
                    description "channel number";
                  }
                  uses PM-GFP-PARAS;
                }
              }

              container odu-hour24otns {
                xr:xr-xml-map "pm_ma_oper:OduHour24OTNTable";
                description "port 24 hour performance data";

                list odu-hour24otn {
                  xr:xr-xml-map "pm_ma_oper:OduHour24OTN";
                  key "number";
                  description "port 24 hour otn performance data";
                  leaf number {
                    xr:xr-xml-map "pm_ma_oper:Number";
                    type int32;
                    description "channel number";
                  }
                  uses PM-OTN-PARAS;
                }
              }
            }
          }
          leaf name {
            xr:xr-xml-map "pm_ma_oper:Name";
            type xr:Interface-name;
            description "Port name";
          }
        }
      }
    }

    container otu {
      xr:xr-xml-map "pm_ma_oper:otu";
      description "OTU controller performance data";

      container otu-ports {
        xr:xr-xml-map "pm_ma_oper:OtuPortTable";
        description "Port performance data";

        list otu-port {
          xr:xr-xml-map "pm_ma_oper:OtuPort";
          key "name";
          description "Port performance data";

          container otu-current {
            xr:xr-xml-map "pm_ma_oper:OtuCurrent";
            description "port current performance data";

            container otu-minute15 {
              xr:xr-xml-map "pm_ma_oper:OtuMinute15";
              description "port current performance data";

              container otu-minute15fecs {
                xr:xr-xml-map "pm_ma_oper:OtuMinute15FECTable";
                description "port current performance data";

                list otu-minute15fec {
                  xr:xr-xml-map "pm_ma_oper:OtuMinute15FEC";
                  key "number";
                  description "port 15-minute fec performance data";
                  leaf number {
                    xr:xr-xml-map "pm_ma_oper:Number";
                    type int32;
                    description "channel number";
                  }
                  uses PM-FEC-PARAS;
                }
              }

              container otu-minute15otns {
                xr:xr-xml-map "pm_ma_oper:OtuMinute15OTNTable";
                description "port current performance data";

                list otu-minute15otn {
                  xr:xr-xml-map "pm_ma_oper:OtuMinute15OTN";
                  key "number";
                  description "port 15-minute otn performance data";
                  leaf number {
                    xr:xr-xml-map "pm_ma_oper:Number";
                    type int32;
                    description "channel number";
                  }
                  uses PM-OTN-PARAS;
                }
              }
            }

            container otu-hour24 {
              xr:xr-xml-map "pm_ma_oper:OtuHour24";
              description "port current performance data";

              container otu-hour24fecs {
                xr:xr-xml-map "pm_ma_oper:OtuHour24FECTable";
                description "port current performance data";

                list otu-hour24fec {
                  xr:xr-xml-map "pm_ma_oper:OtuHour24FEC";
                  key "number";
                  description "port 24 hour fec performance data";
                  leaf number {
                    xr:xr-xml-map "pm_ma_oper:Number";
                    type int32;
                    description "channel number";
                  }
                  uses PM-FEC-PARAS;
                }
              }

              container otu-hour24otns {
                xr:xr-xml-map "pm_ma_oper:OtuHour24OTNTable";
                description "port 24 hour performance data";

                list otu-hour24otn {
                  xr:xr-xml-map "pm_ma_oper:OtuHour24OTN";
                  key "number";
                  description "port 24 hour otn performance data";
                  leaf number {
                    xr:xr-xml-map "pm_ma_oper:Number";
                    type int32;
                    description "channel number";
                  }
                  uses PM-OTN-PARAS;
                }
              }
            }
          }
          leaf name {
            xr:xr-xml-map "pm_ma_oper:Name";
            type xr:Interface-name;
            description "Port name";
          }
        }
      }
    }

    container stm {
      xr:xr-xml-map "pm_ma_oper:stm";
      description "STM controller performance data";

      container stm-ports {
        xr:xr-xml-map "pm_ma_oper:StmPortTable";
        description "Port performance data";

        list stm-port {
          xr:xr-xml-map "pm_ma_oper:StmPort";
          key "name";
          description "Port performance data";

          container stm-current {
            xr:xr-xml-map "pm_ma_oper:StmCurrent";
            description "port current performance data";

            container stm-hour24 {
              xr:xr-xml-map "pm_ma_oper:StmHour24";
              description "port current performance data";

              container stm-hour24stms {
                xr:xr-xml-map "pm_ma_oper:StmHour24STMTable";
                description "port current performance data";

                list stm-hour24stm {
                  xr:xr-xml-map "pm_ma_oper:StmHour24STM";
                  key "number";
                  description "port 24 hour stm performance data";
                  leaf number {
                    xr:xr-xml-map "pm_ma_oper:Number";
                    type int32;
                    description "channel number";
                  }
                  uses PM-STM-PARAS;
                }
              }
            }

            container stm-minute15 {
              xr:xr-xml-map "pm_ma_oper:StmMinute15";
              description "port current performance data";

              container stm-minute15stms {
                xr:xr-xml-map "pm_ma_oper:StmMinute15STMTable";
                description "port current performance data";

                list stm-minute15stm {
                  xr:xr-xml-map "pm_ma_oper:StmMinute15STM";
                  key "number";
                  description "port 15-minute stm performance data";
                  leaf number {
                    xr:xr-xml-map "pm_ma_oper:Number";
                    type int32;
                    description "channel number";
                  }
                  uses PM-STM-PARAS;
                }
              }
            }
          }
          leaf name {
            xr:xr-xml-map "pm_ma_oper:Name";
            type xr:Interface-name;
            description "Port name";
          }
        }
      }
    }

    container sonet {
      xr:xr-xml-map "pm_ma_oper:sonet";
      description "SONET controller performance data";

      container sonet-ports {
        xr:xr-xml-map "pm_ma_oper:SonetPortTable";
        description "Port performance data";

        list sonet-port {
          xr:xr-xml-map "pm_ma_oper:SonetPort";
          key "name";
          description "Port performance data";

          container sonet-current {
            xr:xr-xml-map "pm_ma_oper:SonetCurrent";
            description "port current performance data";

            container sonet-minute15 {
              xr:xr-xml-map "pm_ma_oper:SonetMinute15";
              description "port current performance data";

              container sonet-minute15-paths {
                xr:xr-xml-map "pm_ma_oper:SonetMinute15PathTable";
                description "port current performance data";

                list sonet-minute15-path {
                  xr:xr-xml-map "pm_ma_oper:SonetMinute15Path";
                  key "number";
                  description
                    "port 15-minute Path performance data";
                  leaf number {
                    xr:xr-xml-map "pm_ma_oper:Number";
                    type int32;
                    description "channel number";
                  }
                  uses PM-SONET-PATH-PARAS;
                }
              }

              container sonet-minute15ocns {
                xr:xr-xml-map "pm_ma_oper:SonetMinute15OCNTable";
                description "port current performance data";

                list sonet-minute15ocn {
                  xr:xr-xml-map "pm_ma_oper:SonetMinute15OCN";
                  key "number";
                  description "port 15-minute ocn performance data";
                  leaf number {
                    xr:xr-xml-map "pm_ma_oper:Number";
                    type int32;
                    description "channel number";
                  }
                  uses PM-SONET-PARAS;
                }
              }
            }

            container sonet-hour24 {
              xr:xr-xml-map "pm_ma_oper:SonetHour24";
              description "port current performance data";

              container sonet-hour24ocns {
                xr:xr-xml-map "pm_ma_oper:SonetHour24OCNTable";
                description "port current performance data";

                list sonet-hour24ocn {
                  xr:xr-xml-map "pm_ma_oper:SonetHour24OCN";
                  key "number";
                  description "port 24 hour ocn performance data";
                  leaf number {
                    xr:xr-xml-map "pm_ma_oper:Number";
                    type int32;
                    description "channel number";
                  }
                  uses PM-SONET-PARAS;
                }
              }

              container sonet-hour24-paths {
                xr:xr-xml-map "pm_ma_oper:SonetHour24PathTable";
                description "port current performance data";

                list sonet-hour24-path {
                  xr:xr-xml-map "pm_ma_oper:SonetHour24Path";
                  key "number";
                  description "port 24 hour Path performance data";
                  leaf number {
                    xr:xr-xml-map "pm_ma_oper:Number";
                    type int32;
                    description "channel number";
                  }
                  uses PM-SONET-PATH-PARAS;
                }
              }
            }
          }
          leaf name {
            xr:xr-xml-map "pm_ma_oper:Name";
            type xr:Interface-name;
            description "Port name";
          }
        }
      }
    }

    container optics {
      xr:xr-xml-map "pm_ma_oper:optics";
      description "OPTICS controller performance data";

      container optics-ports {
        xr:xr-xml-map "pm_ma_oper:OpticsPortTable";
        description "Port performance data";

        list optics-port {
          xr:xr-xml-map "pm_ma_oper:OpticsPort";
          key "name";
          description "Port performance data";

          container optics-current {
            xr:xr-xml-map "pm_ma_oper:OpticsCurrent";
            description "port current performance data";

            container optics-hour24 {
              xr:xr-xml-map "pm_ma_oper:OpticsHour24";
              description "port current performance data";

              container optics-hour24-optics {
                xr:xr-xml-map "pm_ma_oper:OpticsHour24OpticsTable";
                description "port 24 hour performance data";

                list optics-hour24-optic {
                  xr:xr-xml-map "pm_ma_oper:OpticsHour24Optics";
                  key "number";
                  description
                    "port 24 hour optics performance data";
                  leaf number {
                    xr:xr-xml-map "pm_ma_oper:Number";
                    type int32;
                    description "channel number";
                  }
                  uses PM-OPTICS-PARAS;
                }
              }

              container optics-hour24fecs {
                xr:xr-xml-map "pm_ma_oper:OpticsHour24FECTable";
                description "port current performance data";

                list optics-hour24fec {
                  xr:xr-xml-map "pm_ma_oper:OpticsHour24FEC";
                  key "number";
                  description "port 24 hour fec performance data";
                  leaf number {
                    xr:xr-xml-map "pm_ma_oper:Number";
                    type int32;
                    description "channel number";
                  }
                  uses PM-FEC-PARAS;
                }
              }
            }

            container optics-minute15 {
              xr:xr-xml-map "pm_ma_oper:OpticsMinute15";
              description "port current performance data";

              container optics-minute15-optics {
                xr:xr-xml-map "pm_ma_oper:OpticsMinute15OpticsTable";
                description "port current performance data";

                list optics-minute15-optic {
                  xr:xr-xml-map "pm_ma_oper:OpticsMinute15Optics";
                  key "number";
                  description
                    "port 15-minute optics performance data";
                  leaf number {
                    xr:xr-xml-map "pm_ma_oper:Number";
                    type int32;
                    description "channel number";
                  }
                  uses PM-OPTICS-PARAS;
                }
              }

              container optics-minute15fecs {
                xr:xr-xml-map "pm_ma_oper:OpticsMinute15FECTable";
                description "port current performance data";

                list optics-minute15fec {
                  xr:xr-xml-map "pm_ma_oper:OpticsMinute15FEC";
                  key "number";
                  description "port 15-minute fec performance data";
                  leaf number {
                    xr:xr-xml-map "pm_ma_oper:Number";
                    type int32;
                    description "channel number";
                  }
                  uses PM-FEC-PARAS;
                }
              }
            }
          }
          leaf name {
            xr:xr-xml-map "pm_ma_oper:Name";
            type xr:Interface-name;
            description "Port name";
          }
        }
      }
    }

    container sts {
      xr:xr-xml-map "pm_ma_oper:sts";
      description "STS controller performance data";

      container sts-ports {
        xr:xr-xml-map "pm_ma_oper:StsPortTable";
        description "Port performance data";

        list sts-port {
          xr:xr-xml-map "pm_ma_oper:StsPort";
          key "name";
          description "Port performance data";

          container sts-current {
            xr:xr-xml-map "pm_ma_oper:StsCurrent";
            description "port current performance data";

            container sts-minute15 {
              xr:xr-xml-map "pm_ma_oper:StsMinute15";
              description "port current performance data";

              container sts-minute15-paths {
                xr:xr-xml-map "pm_ma_oper:StsMinute15PathTable";
                description "port current performance data";

                list sts-minute15-path {
                  xr:xr-xml-map "pm_ma_oper:StsMinute15Path";
                  key "number";
                  description
                    "port 15-minute Path performance data";
                  leaf number {
                    xr:xr-xml-map "pm_ma_oper:Number";
                    type int32;
                    description "channel number";
                  }
                  uses PM-SONET-PATH-PARAS;
                }
              }
            }

            container sts-hour24 {
              xr:xr-xml-map "pm_ma_oper:StsHour24";
              description "port current performance data";

              container sts-hour24-paths {
                xr:xr-xml-map "pm_ma_oper:StsHour24PathTable";
                description "port current performance data";

                list sts-hour24-path {
                  xr:xr-xml-map "pm_ma_oper:StsHour24Path";
                  key "number";
                  description "port 24 hour Path performance data";
                  leaf number {
                    xr:xr-xml-map "pm_ma_oper:Number";
                    type int32;
                    description "channel number";
                  }
                  uses PM-SONET-PATH-PARAS;
                }
              }
            }
          }
          leaf name {
            xr:xr-xml-map "pm_ma_oper:Name";
            type xr:Interface-name;
            description "Port name";
          }
        }
      }
    }

    container dwdm {
      xr:xr-xml-map "pm_ma_oper:dwdm";
      description "DWDM controller performance data";

      container dwdm-ports {
        xr:xr-xml-map "pm_ma_oper:DwdmPortTable";
        description "Port performance data";

        list dwdm-port {
          xr:xr-xml-map "pm_ma_oper:DwdmPort";
          key "name";
          description "Port performance data";

          container dwdm-current {
            xr:xr-xml-map "pm_ma_oper:DwdmCurrent";
            description "port current performance data";

            container dwdm-minute15 {
              xr:xr-xml-map "pm_ma_oper:DwdmMinute15";
              description "port current performance data";

              container dwdm-minute15fecs {
                xr:xr-xml-map "pm_ma_oper:DwdmMinute15FECTable";
                description "port current performance data";

                list dwdm-minute15fec {
                  xr:xr-xml-map "pm_ma_oper:DwdmMinute15FEC";
                  key "number";
                  description "port 15-minute fec performance data";
                  leaf number {
                    xr:xr-xml-map "pm_ma_oper:Number";
                    type int32;
                    description "channel number";
                  }
                  uses PM-FEC-PARAS;
                }
              }

              container dwdm-minute15-optics {
                xr:xr-xml-map "pm_ma_oper:DwdmMinute15OpticsTable";
                description "port current performance data";

                list dwdm-minute15-optic {
                  xr:xr-xml-map "pm_ma_oper:DwdmMinute15Optics";
                  key "number";
                  description
                    "port 15-minute optics performance data";
                  leaf number {
                    xr:xr-xml-map "pm_ma_oper:Number";
                    type int32;
                    description "channel number";
                  }
                  uses PM-OPTICS-PARAS;
                }
              }

              container dwdm-minute15otns {
                xr:xr-xml-map "pm_ma_oper:DwdmMinute15OTNTable";
                description "port current performance data";

                list dwdm-minute15otn {
                  xr:xr-xml-map "pm_ma_oper:DwdmMinute15OTN";
                  key "number";
                  description "port 15-minute otn performance data";
                  leaf number {
                    xr:xr-xml-map "pm_ma_oper:Number";
                    type int32;
                    description "channel number";
                  }
                  uses PM-OTN-PARAS;
                }
              }
            }

            container dwdm-hour24 {
              xr:xr-xml-map "pm_ma_oper:DwdmHour24";
              description "port current performance data";

              container dwdm-hour24-optics {
                xr:xr-xml-map "pm_ma_oper:DwdmHour24OpticsTable";
                description "port 24 hour performance data";

                list dwdm-hour24-optic {
                  xr:xr-xml-map "pm_ma_oper:DwdmHour24Optics";
                  key "number";
                  description
                    "port 24 hour optics performance data";
                  leaf number {
                    xr:xr-xml-map "pm_ma_oper:Number";
                    type int32;
                    description "channel number";
                  }
                  uses PM-OPTICS-PARAS;
                }
              }

              container dwdm-hour24fecs {
                xr:xr-xml-map "pm_ma_oper:DwdmHour24FECTable";
                description "port current performance data";

                list dwdm-hour24fec {
                  xr:xr-xml-map "pm_ma_oper:DwdmHour24FEC";
                  key "number";
                  description "port 24 hour fec performance data";
                  leaf number {
                    xr:xr-xml-map "pm_ma_oper:Number";
                    type int32;
                    description "channel number";
                  }
                  uses PM-FEC-PARAS;
                }
              }

              container dwdm-hour24otns {
                xr:xr-xml-map "pm_ma_oper:DwdmHour24OTNTable";
                description "port 24 hour performance data";

                list dwdm-hour24otn {
                  xr:xr-xml-map "pm_ma_oper:DwdmHour24OTN";
                  key "number";
                  description "port 24 hour otn performance data";
                  leaf number {
                    xr:xr-xml-map "pm_ma_oper:Number";
                    type int32;
                    description "channel number";
                  }
                  uses PM-OTN-PARAS;
                }
              }
            }
          }
          leaf name {
            xr:xr-xml-map "pm_ma_oper:Name";
            type xr:Interface-name;
            description "Port name";
          }
        }
      }
    }

    container oc {
      xr:xr-xml-map "pm_ma_oper:oc";
      description "OC controller performance data";

      container oc-ports {
        xr:xr-xml-map "pm_ma_oper:OcPortTable";
        description "Port performance data";

        list oc-port {
          xr:xr-xml-map "pm_ma_oper:OcPort";
          key "name";
          description "Port performance data";

          container oc-current {
            xr:xr-xml-map "pm_ma_oper:OcCurrent";
            description "port current performance data";

            container oc-hour24 {
              xr:xr-xml-map "pm_ma_oper:OcHour24";
              description "port current performance data";

              container oc-hour24ocns {
                xr:xr-xml-map "pm_ma_oper:OcHour24OCNTable";
                description "port current performance data";

                list oc-hour24ocn {
                  xr:xr-xml-map "pm_ma_oper:OcHour24OCN";
                  key "number";
                  description "port 24 hour ocn performance data";
                  leaf number {
                    xr:xr-xml-map "pm_ma_oper:Number";
                    type int32;
                    description "channel number";
                  }
                  uses PM-SONET-PARAS;
                }
              }
            }

            container oc-minute15 {
              xr:xr-xml-map "pm_ma_oper:OcMinute15";
              description "port current performance data";

              container oc-minute15ocns {
                xr:xr-xml-map "pm_ma_oper:OcMinute15OCNTable";
                description "port current performance data";

                list oc-minute15ocn {
                  xr:xr-xml-map "pm_ma_oper:OcMinute15OCN";
                  key "number";
                  description "port 15-minute ocn performance data";
                  leaf number {
                    xr:xr-xml-map "pm_ma_oper:Number";
                    type int32;
                    description "channel number";
                  }
                  uses PM-SONET-PARAS;
                }
              }
            }
          }
          leaf name {
            xr:xr-xml-map "pm_ma_oper:Name";
            type xr:Interface-name;
            description "Port name";
          }
        }
      }
    }

    container ethernet {
      xr:xr-xml-map "pm_ma_oper:ethernet";
      description "EHERNET controller performance data";

      container ethernet-ports {
        xr:xr-xml-map "pm_ma_oper:EthernetPortTable";
        description "Port performance data";

        list ethernet-port {
          xr:xr-xml-map "pm_ma_oper:EthernetPort";
          key "name";
          description "Port performance data";

          container ethernet-current {
            xr:xr-xml-map "pm_ma_oper:EthernetCurrent";
            description "port current performance data";

            container ethernet-hour24 {
              xr:xr-xml-map "pm_ma_oper:EthernetHour24";
              description "port current performance data";

              container ethernet-hour24-ether-s {
                xr:xr-xml-map "pm_ma_oper:EthernetHour24ETHERTable";
                description "port current performance data";

                list ethernet-hour24-ether {
                  xr:xr-xml-map "pm_ma_oper:EthernetHour24ETHER";
                  key "number";
                  description
                    "port 24 hour ethernet performance data";
                  leaf number {
                    xr:xr-xml-map "pm_ma_oper:Number";
                    type int32;
                    description "channel number";
                  }
                  uses PM-ETHERNET-PARAS;
                }
              }
            }

            container minute15 {
              xr:xr-xml-map "pm_ma_oper:Minute15";
              description "port current performance data";

              container minute15-ethers {
                xr:xr-xml-map "pm_ma_oper:Minute15EtherTable";
                description
                  "ETHERNET port interval performance data";

                list minute15-ether {
                  xr:xr-xml-map "pm_ma_oper:Minute15Ether";
                  key "slot-number";
                  description
                    "ETHERNET port 15-minute ether performance
                    data";
                  leaf slot-number {
                    xr:xr-xml-map "pm_ma_oper:SlotNumber";
                    type int32;
                    description "interval slot number";
                  }
                  uses PM-ETHERNET-PARAS;
                }
              }
            }
          }
          leaf name {
            xr:xr-xml-map "pm_ma_oper:Name";
            type xr:Interface-name;
            description "Port name";
          }
        }
      }
    }
  }

  container performance-management-history {
    xr:xr-xml-map "pm_ma_oper:PerformanceManagementHistory";
    config false;
    description "performance management history";

    container global {
      xr:xr-xml-map "pm_ma_oper:Global";
      description "global History performace data";

      container periodic {
        xr:xr-xml-map "pm_ma_oper:periodic";
        description "History performace data";

        container sonet-history {
          xr:xr-xml-map "pm_ma_oper:sonetHistory";
          description "SONET controller History performance data";

          container sonet-port-histories {
            xr:xr-xml-map "pm_ma_oper:SonetHistoryPortTable";
            description "Port performance data";

            list sonet-port-history {
              xr:xr-xml-map "pm_ma_oper:SonetPortHistory";
              key "name";
              description "Port performance data";

              container sonet-minute15-history {
                xr:xr-xml-map "pm_ma_oper:SonetMinute15History";
                description "port current performance data";

                container sonet-minute15ocn-histories {
                  xr:xr-xml-map "pm_ma_oper:SonetMinute15OCNTableHi"+
                    "story";
                  description "port current performance data";

                  list sonet-minute15ocn-history {
                    xr:xr-xml-map "pm_ma_oper:SonetMinute15OCNHisto"+
                      "ry";
                    key "number";
                    description
                      "port 15-minute ocn performance data";

                    container "sonet-minute15ocn-time-line"+
                      "-instances" {
                      xr:xr-xml-map "pm_ma_oper:SonetMinute15OCNTab"+
                        "leTimeLine";
                      description "port current performance data";

                      list sonet-minute15ocn-time-line-instance {
                        xr:xr-xml-map "pm_ma_oper:SonetMinute15OCNT"+
                          "imeLineInstance";
                        key "number";
                        description
                          "port 15-minute otn performance data";
                        leaf number {
                          xr:xr-xml-map "pm_ma_oper:Number";
                          type int32;
                          description "History Index number";
                        }
                        uses PM-SONET-PARAS;
                      }
                    }
                    leaf number {
                      xr:xr-xml-map "pm_ma_oper:Number";
                      type int32;
                      description "channel number";
                    }
                  }
                }

                container sonet-minute15-path-histories {
                  xr:xr-xml-map "pm_ma_oper:SonetMinute15PathTableH"+
                    "istory";
                  description "port current performance data";

                  list sonet-minute15-path-history {
                    xr:xr-xml-map "pm_ma_oper:SonetMinute15PathHist"+
                      "ory";
                    key "number";
                    description
                      "port 15-minute Path performance data";

                    container "sonet-minute15-path-time-line"+
                      "-instances" {
                      xr:xr-xml-map "pm_ma_oper:SonetMinute15PathTa"+
                        "bleTimeLine";
                      description "port current performance data";

                      list sonet-minute15-path-time-line-instance {
                        xr:xr-xml-map "pm_ma_oper:SonetMinute15Path"+
                          "TimeLineInstance";
                        key "number";
                        description
                          "port 15-minute otn performance data";
                        leaf number {
                          xr:xr-xml-map "pm_ma_oper:Number";
                          type int32;
                          description "History Index number";
                        }
                        uses PM-SONET-PATH-PARAS;
                      }
                    }
                    leaf number {
                      xr:xr-xml-map "pm_ma_oper:Number";
                      type int32;
                      description "channel number";
                    }
                  }
                }
              }

              container sonet-hour24-history {
                xr:xr-xml-map "pm_ma_oper:SonetHour24History";
                description "port current performance data";

                container sonet-hour24-path-histories {
                  xr:xr-xml-map "pm_ma_oper:SonetHour24PathTableHis"+
                    "tory";
                  description "port current performance data";

                  list sonet-hour24-path-history {
                    xr:xr-xml-map "pm_ma_oper:SonetHour24PathHistor"+
                      "y";
                    key "number";
                    description
                      "port 24 hour Path performance data";

                    container "sonet-hour24-path-time-line"+
                      "-instances" {
                      xr:xr-xml-map "pm_ma_oper:SonetHour24PathTabl"+
                        "eTimeLine";
                      description "port current performance data";

                      list sonet-hour24-path-time-line-instance {
                        xr:xr-xml-map "pm_ma_oper:SonetHour24PathTi"+
                          "meLineInstance";
                        key "number";
                        description
                          "port 15-minute otn performance data";
                        leaf number {
                          xr:xr-xml-map "pm_ma_oper:Number";
                          type int32;
                          description "History Index number";
                        }
                        uses PM-SONET-PATH-PARAS;
                      }
                    }
                    leaf number {
                      xr:xr-xml-map "pm_ma_oper:Number";
                      type int32;
                      description "channel number";
                    }
                  }
                }

                container sonet-hour24ocn-histories {
                  xr:xr-xml-map "pm_ma_oper:SonetHour24OCNTableHist"+
                    "ory";
                  description "port current performance data";

                  list sonet-hour24ocn-history {
                    xr:xr-xml-map "pm_ma_oper:SonetHour24OCNHistory";
                    key "number";
                    description "port 24 hour ocn performance data";

                    container sonet-hour24ocn-time-line-instances {
                      xr:xr-xml-map "pm_ma_oper:SonetHour24OCNTable"+
                        "TimeLine";
                      description "port current performance data";

                      list sonet-hour24ocn-time-line-instance {
                        xr:xr-xml-map "pm_ma_oper:SonetHour24OCNTim"+
                          "eLineInstance";
                        key "number";
                        description
                          "port 15-minute otn performance data";
                        leaf number {
                          xr:xr-xml-map "pm_ma_oper:Number";
                          type int32;
                          description "History Index number";
                        }
                        uses PM-SONET-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container sts-history {
          xr:xr-xml-map "pm_ma_oper:stsHistory";
          description "STS controller History performance data";

          container sts-port-histories {
            xr:xr-xml-map "pm_ma_oper:StsHistoryPortTable";
            description "Port performance data";

            list sts-port-history {
              xr:xr-xml-map "pm_ma_oper:StsPortHistory";
              key "name";
              description "Port performance data";

              container sts-minute15-history {
                xr:xr-xml-map "pm_ma_oper:StsMinute15History";
                description "port current performance data";

                container sts-minute15-path-histories {
                  xr:xr-xml-map "pm_ma_oper:StsMinute15PathTableHis"+
                    "tory";
                  description "port current performance data";

                  list sts-minute15-path-history {
                    xr:xr-xml-map "pm_ma_oper:StsMinute15PathHistor"+
                      "y";
                    key "number";
                    description
                      "port 15-minute Path performance data";

                    container "sts-minute15-path-time-line"+
                      "-instances" {
                      xr:xr-xml-map "pm_ma_oper:StsMinute15PathTabl"+
                        "eTimeLine";
                      description "port current performance data";

                      list sts-minute15-path-time-line-instance {
                        xr:xr-xml-map "pm_ma_oper:StsMinute15PathTi"+
                          "meLineInstance";
                        key "number";
                        description
                          "port 15-minute otn performance data";
                        leaf number {
                          xr:xr-xml-map "pm_ma_oper:Number";
                          type int32;
                          description "History Index number";
                        }
                        uses PM-SONET-PATH-PARAS;
                      }
                    }
                    leaf number {
                      xr:xr-xml-map "pm_ma_oper:Number";
                      type int32;
                      description "channel number";
                    }
                  }
                }
              }

              container sts-hour24-history {
                xr:xr-xml-map "pm_ma_oper:StsHour24History";
                description "port current performance data";

                container sts-hour24-path-histories {
                  xr:xr-xml-map "pm_ma_oper:StsHour24PathTableHisto"+
                    "ry";
                  description "port current performance data";

                  list sts-hour24-path-history {
                    xr:xr-xml-map "pm_ma_oper:StsHour24PathHistory";
                    key "number";
                    description
                      "port 24 hour Path performance data";

                    container sts-hour24-path-time-line-instances {
                      xr:xr-xml-map "pm_ma_oper:StsHour24PathTableT"+
                        "imeLine";
                      description "port current performance data";

                      list sts-hour24-path-time-line-instance {
                        xr:xr-xml-map "pm_ma_oper:StsHour24PathTime"+
                          "LineInstance";
                        key "number";
                        description
                          "port 15-minute sts performance data";
                        leaf number {
                          xr:xr-xml-map "pm_ma_oper:Number";
                          type int32;
                          description "History Index number";
                        }
                        uses PM-SONET-PATH-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container ethernet-history {
          xr:xr-xml-map "pm_ma_oper:ethernetHistory";
          description "EHERNET controller History performance data";

          container ethernet-port-histories {
            xr:xr-xml-map "pm_ma_oper:EthernetHistoryPortTable";
            description "Port performance data";

            list ethernet-port-history {
              xr:xr-xml-map "pm_ma_oper:EthernetPortHistory";
              key "name";
              description "Port performance data";

              container ethernet-hour24-history {
                xr:xr-xml-map "pm_ma_oper:EthernetHour24History";
                description "port current performance data";

                container ethernet-hour24-ether-histories {
                  xr:xr-xml-map "pm_ma_oper:EthernetHour24ETHERTabl"+
                    "eHistory";
                  description "port current performance data";

                  list ethernet-hour24-ether-history {
                    xr:xr-xml-map "pm_ma_oper:EthernetHour24ETHERHi"+
                      "story";
                    key "number";
                    description
                      "port 24 hour ethernet performance data";

                    container "ethernet-hour24-ether-time-line"+
                      "-instances" {
                      xr:xr-xml-map "pm_ma_oper:EthernetHour24ETHER"+
                        "TableTimeLine";
                      description "port current performance data";

                      list "ethernet-hour24-ether-time-line"+
                        "-instance" {
                        xr:xr-xml-map "pm_ma_oper:EthernetHour24ETH"+
                          "ERTimeLineInstance";
                        key "number";
                        description
                          "port 15-minute otn performance data";
                        leaf number {
                          xr:xr-xml-map "pm_ma_oper:Number";
                          type int32;
                          description "History Index number";
                        }
                        uses PM-ETHERNET-PARAS;
                      }
                    }
                    leaf number {
                      xr:xr-xml-map "pm_ma_oper:Number";
                      type int32;
                      description "channel number";
                    }
                  }
                }
              }

              container ethernet-minute15-history {
                xr:xr-xml-map "pm_ma_oper:EthernetMinute15History";
                description "port current performance data";

                container minute15-ether-histories {
                  xr:xr-xml-map "pm_ma_oper:Minute15EtherTableHisto"+
                    "ry";
                  description
                    "ETHERNET port interval performance data";

                  list minute15-ether-history {
                    xr:xr-xml-map "pm_ma_oper:Minute15EtherHistory";
                    key "slot-number";
                    description
                      "ETHERNET port 15-minute ether performance
                      data";

                    container minute15-ether-time-line-instances {
                      xr:xr-xml-map "pm_ma_oper:Minute15EtherTableT"+
                        "imeLine";
                      description "port current performance data";

                      list minute15-ether-time-line-instance {
                        xr:xr-xml-map "pm_ma_oper:Minute15EtherTime"+
                          "LineInstance";
                        key "number";
                        description
                          "port 15-minute otn performance data";
                        leaf number {
                          xr:xr-xml-map "pm_ma_oper:Number";
                          type int32;
                          description "History Index number";
                        }
                        uses PM-ETHERNET-PARAS;
                      }
                    }
                    leaf slot-number {
                      xr:xr-xml-map "pm_ma_oper:SlotNumber";
                      type int32;
                      description "interval slot number";
                    }
                  }
                }
              }
              leaf name {
                xr:xr-xml-map "pm_ma_oper:Name";
                type xr:Interface-name;
                description "Port name";
              }
            }
          }
        }

        container dwdm-history {
          xr:xr-xml-map "pm_ma_oper:dwdmHistory";
          description "DWDM controller History performance data";

          container dwdm-port-histories {
            xr:xr-xml-map "pm_ma_oper:DwdmHistoryPortTable";
            description "Port performance data";

            list dwdm-port-history {
              xr:xr-xml-map "pm_ma_oper:DwdmPortHistory";
              key "name";
              description "Port performance data";

              container dwdm-minute15-history {
                xr:xr-xml-map "pm_ma_oper:DwdmMinute15History";
                description "port current performance data";

                container dwdm-minute15otn-histories {
                  xr:xr-xml-map "pm_ma_oper:DwdmMinute15OTNTableHis"+
                    "tory";
                  description "port current performance data";

                  list dwdm-minute15otn-history {
                    xr:xr-xml-map "pm_ma_oper:DwdmMinute15OTNHistor"+
                      "y";
                    key "number";
                    description
                      "port 15-minute otn performance data";

                    container dwdm-minute15otn-time-line-instances {
                      xr:xr-xml-map "pm_ma_oper:DwdmMinute15OTNTabl"+
                        "eTimeLine";
                      description "port current performance data";

                      list dwdm-minute15otn-time-line-instance {
                        xr:xr-xml-map "pm_ma_oper:DwdmMinute15OTNTi"+
                          "meLineInstance";
                        key "number";
                        description
                          "port 15-minute otn performance data";
                        leaf number {
                          xr:xr-xml-map "pm_ma_oper:Number";
                          type int32;
                          description "History Index number";
                        }
                        uses PM-OTN-PARAS;
                      }
                    }
                    leaf number {
                      xr:xr-xml-map "pm_ma_oper:Number";
                      type int32;
                      description "channel number";
                    }
                  }
                }

                container dwdm-minute15fec-histories {
                  xr:xr-xml-map "pm_ma_oper:DwdmMinute15FECTableHis"+
                    "tory";
                  description "port current performance data";

                  list dwdm-minute15fec-history {
                    xr:xr-xml-map "pm_ma_oper:DwdmMinute15FECHistor"+
                      "y";
                    key "number";
                    description
                      "port 15-minute fec performance data";

                    container dwdm-minute15fec-time-line-instances {
                      xr:xr-xml-map "pm_ma_oper:DwdmMinute15FECTabl"+
                        "eTimeLine";
                      description "port current performance data";

                      list dwdm-minute15fec-time-line-instance {
                        xr:xr-xml-map "pm_ma_oper:DwdmMinute15FECTi"+
                          "meLineInstance";
                        key "number";
                        description
                          "port 15-minute fec performance data by
                          index";
                        leaf number {
                          xr:xr-xml-map "pm_ma_oper:Number";
                          type int32;
                          description "History Index number";
                        }
                        uses PM-FEC-PARAS;
                      }
                    }
                    leaf number {
                      xr:xr-xml-map "pm_ma_oper:Number";
                      type int32;
                      description "channel number";
                    }
                  }
                }

                container dwdm-minute15-optics-histories {
                  xr:xr-xml-map "pm_ma_oper:DwdmMinute15OpticsTable"+
                    "History";
                  description "port current performance data";

                  list dwdm-minute15-optics-history {
                    xr:xr-xml-map "pm_ma_oper:DwdmMinute15OpticsHis"+
                      "tory";
                    key "number";
                    description
                      "port 15-minute optics performance data";

                    container "dwdm-minute15-optics-time-line"+
                      "-instances" {
                      xr:xr-xml-map "pm_ma_oper:DwdmMinute15OpticsT"+
                        "ableTimeLine";
                      description "port current performance data";

                      list dwdm-minute15-optics-time-line-instance {
                        xr:xr-xml-map "pm_ma_oper:DwdmMinute15Optic"+
                          "sTimeLineInstance";
                        key "number";
                        description
                          "port 15-minute otn performance data";
                        leaf number {
                          xr:xr-xml-map "pm_ma_oper:Number";
                          type int32;
                          description "History Index number";
                        }
                        uses PM-OPTICS-PARAS;
                      }
                    }
                    leaf number {
                      xr:xr-xml-map "pm_ma_oper:Number";
                      type int32;
                      description "channel number";
                    }
                  }
                }
              }

              container dwdm-hour24-history {
                xr:xr-xml-map "pm_ma_oper:DwdmHour24History";
                description "port current performance data";

                container dwdm-hour24otn-histories {
                  xr:xr-xml-map "pm_ma_oper:DwdmHour24OTNTableHisto"+
                    "ry";
                  description "port 24 hour performance data";

                  list dwdm-hour24otn-history {
                    xr:xr-xml-map "pm_ma_oper:DwdmHour24OTNHistory";
                    key "number";
                    description "port 24 hour otn performance data";

                    container dwdm-hour24otn-time-line-instances {
                      xr:xr-xml-map "pm_ma_oper:DwdmHour24OTNTableT"+
                        "imeLine";
                      description "port current performance data";

                      list dwdm-hour24otn-time-line-instance {
                        xr:xr-xml-map "pm_ma_oper:DwdmHour24OTNTime"+
                          "LineInstance";
                        key "number";
                        description
                          "port 15-minute otn performance data";
                        leaf number {
                          xr:xr-xml-map "pm_ma_oper:Number";
                          type int32;
                          description "History Index number";
                        }
                        uses PM-OTN-PARAS;
                      }
                    }
                    leaf number {
                      xr:xr-xml-map "pm_ma_oper:Number";
                      type int32;
                      description "channel number";
                    }
                  }
                }

                container dwdm-hour24fec-histories {
                  xr:xr-xml-map "pm_ma_oper:DwdmHour24FECTableHisto"+
                    "ry";
                  description "port current performance data";

                  list dwdm-hour24fec-history {
                    xr:xr-xml-map "pm_ma_oper:DwdmHour24FECHistory";
                    key "number";
                    description "port 24 hour fec performance data";

                    container dwdm-hour24fec-time-line-instances {
                      xr:xr-xml-map "pm_ma_oper:DwdmHour24FECTableT"+
                        "imeLine";
                      description "port current performance data";

                      list dwdm-hour24fec-time-line-instance {
                        xr:xr-xml-map "pm_ma_oper:DwdmHour24FECTime"+
                          "LineInstance";
                        key "number";
                        description
                          "port 15-minute fec performance data by
                          index";
                        leaf number {
                          xr:xr-xml-map "pm_ma_oper:Number";
                          type int32;
                          description "History Index number";
                        }
                        uses PM-FEC-PARAS;
                      }
                    }
                    leaf number {
                      xr:xr-xml-map "pm_ma_oper:Number";
                      type int32;
                      description "channel number";
                    }
                  }
                }

                container dwdm-hour24-optics-histories {
                  xr:xr-xml-map "pm_ma_oper:DwdmHour24OpticsTableHi"+
                    "story";
                  description "port 24 hour performance data";

                  list dwdm-hour24-optics-history {
                    xr:xr-xml-map "pm_ma_oper:DwdmHour24OpticsHisto"+
                      "ry";
                    key "number";
                    description
                      "port 24 hour optics performance data";

                    container "dwdm-hour24-optics-time-line"+
                      "-instances" {
                      xr:xr-xml-map "pm_ma_oper:DwdmHour24OpticsTab"+
                        "leTimeLine";
                      description "port current performance data";

                      list dwdm-hour24-optics-time-line-instance {
                        xr:xr-xml-map "pm_ma_oper:DwdmHour24OpticsT"+
                          "imeLineInstance";
                        key "number";
                        description
                          "port 15-minute otn performance data";
                        leaf number {
                          xr:xr-xml-map "pm_ma_oper:Number";
                          type int32;
                          description "History Index number";
                        }
                        uses PM-OPTICS-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container stm-history {
          xr:xr-xml-map "pm_ma_oper:stmHistory";
          description "STM controller History performance data";

          container stm-port-histories {
            xr:xr-xml-map "pm_ma_oper:StmHistoryPortTable";
            description "Port performance data";

            list stm-port-history {
              xr:xr-xml-map "pm_ma_oper:StmPortHistory";
              key "name";
              description "Port performance data";

              container stm-hour24-history {
                xr:xr-xml-map "pm_ma_oper:StmHour24History";
                description "port current performance data";

                container stm-hour24stm-histories {
                  xr:xr-xml-map "pm_ma_oper:StmHour24STMTableHistor"+
                    "y";
                  description "port current performance data";

                  list stm-hour24stm-history {
                    xr:xr-xml-map "pm_ma_oper:StmHour24STMHistory";
                    key "number";
                    description "port 24 hour stm performance data";

                    container stm-hour24stm-time-line-instances {
                      xr:xr-xml-map "pm_ma_oper:StmHour24STMTableTi"+
                        "meLine";
                      description "port current performance data";

                      list stm-hour24stm-time-line-instance {
                        xr:xr-xml-map "pm_ma_oper:StmHour24STMTimeL"+
                          "ineInstance";
                        key "number";
                        description
                          "port 15-minute stm performance data";
                        leaf number {
                          xr:xr-xml-map "pm_ma_oper:Number";
                          type int32;
                          description "History Index number";
                        }
                        uses PM-STM-PARAS;
                      }
                    }
                    leaf number {
                      xr:xr-xml-map "pm_ma_oper:Number";
                      type int32;
                      description "channel number";
                    }
                  }
                }
              }

              container stm-minute15-history {
                xr:xr-xml-map "pm_ma_oper:StmMinute15History";
                description "port current performance data";

                container stm-minute15stm-histories {
                  xr:xr-xml-map "pm_ma_oper:StmMinute15STMTableHist"+
                    "ory";
                  description "port current performance data";

                  list stm-minute15stm-history {
                    xr:xr-xml-map "pm_ma_oper:StmMinute15STMHistory";
                    key "number";
                    description
                      "port 15-minute stm performance data";

                    container stm-minute15stm-time-line-instances {
                      xr:xr-xml-map "pm_ma_oper:StmMinute15STMTable"+
                        "TimeLine";
                      description "port current performance data";

                      list stm-minute15stm-time-line-instance {
                        xr:xr-xml-map "pm_ma_oper:StmMinute15STMTim"+
                          "eLineInstance";
                        key "number";
                        description
                          "port 15-minute stm performance data";
                        leaf number {
                          xr:xr-xml-map "pm_ma_oper:Number";
                          type int32;
                          description "History Index number";
                        }
                        uses PM-STM-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container odu-history {
          xr:xr-xml-map "pm_ma_oper:oduHistory";
          description "ODU controller History performance data";

          container odu-port-histories {
            xr:xr-xml-map "pm_ma_oper:OduHistoryPortTable";
            description "Port performance data";

            list odu-port-history {
              xr:xr-xml-map "pm_ma_oper:OduPortHistory";
              key "name";
              description "Port performance data";

              container odu-hour24-history {
                xr:xr-xml-map "pm_ma_oper:OduHour24History";
                description "port current performance data";

                container odu-hour24gfp-histories {
                  xr:xr-xml-map "pm_ma_oper:OduHour24GFPTableHistor"+
                    "y";
                  description "port 24 hour performance data";

                  list odu-hour24gfp-history {
                    xr:xr-xml-map "pm_ma_oper:OduHour24GFPHistory";
                    key "number";
                    description "port 24 hour otn performance data";

                    container odu-hour24gfp-time-line-instances {
                      xr:xr-xml-map "pm_ma_oper:OduHour24GFPTableTi"+
                        "meLine";
                      description "port current performance data";

                      list odu-hour24gfp-time-line-instance {
                        xr:xr-xml-map "pm_ma_oper:OduHour24GFPTimeL"+
                          "ineInstance";
                        key "number";
                        description
                          "port 15-minute otn performance data";
                        leaf number {
                          xr:xr-xml-map "pm_ma_oper:Number";
                          type int32;
                          description "History Index number";
                        }
                        uses PM-GFP-PARAS;
                      }
                    }
                    leaf number {
                      xr:xr-xml-map "pm_ma_oper:Number";
                      type int32;
                      description "channel number";
                    }
                  }
                }

                container odu-hour24prbs-histories {
                  xr:xr-xml-map "pm_ma_oper:OduHour24PRBSTableHisto"+
                    "ry";
                  description "port 24 hour performance data";

                  list odu-hour24prbs-history {
                    xr:xr-xml-map "pm_ma_oper:OduHour24PRBSHistory";
                    key "number";
                    description
                      "port 24 hour prbs performance data";

                    container odu-hour24prbs-time-line-instances {
                      xr:xr-xml-map "pm_ma_oper:OduHour24PRBSTableT"+
                        "imeLine";
                      description "port current performance data";

                      list odu-hour24prbs-time-line-instance {
                        xr:xr-xml-map "pm_ma_oper:OduHour24PRBSTime"+
                          "LineInstance";
                        key "number";
                        description
                          "port 15-minute prbs performance data";
                        leaf number {
                          xr:xr-xml-map "pm_ma_oper:Number";
                          type int32;
                          description "History Index number";
                        }
                        uses PM-PRBS-PARAS;
                      }
                    }
                    leaf number {
                      xr:xr-xml-map "pm_ma_oper:Number";
                      type int32;
                      description "channel number";
                    }
                  }
                }

                container odu-hour24otn-histories {
                  xr:xr-xml-map "pm_ma_oper:OduHour24OTNTableHistor"+
                    "y";
                  description "port 24 hour performance data";

                  list odu-hour24otn-history {
                    xr:xr-xml-map "pm_ma_oper:OduHour24OTNHistory";
                    key "number";
                    description "port 24 hour otn performance data";

                    container odu-hour24otn-time-line-instances {
                      xr:xr-xml-map "pm_ma_oper:OduHour24OTNTableTi"+
                        "meLine";
                      description "port current performance data";

                      list odu-hour24otn-time-line-instance {
                        xr:xr-xml-map "pm_ma_oper:OduHour24OTNTimeL"+
                          "ineInstance";
                        key "number";
                        description
                          "port 15-minute otn performance data";
                        leaf number {
                          xr:xr-xml-map "pm_ma_oper:Number";
                          type int32;
                          description "History Index number";
                        }
                        uses PM-OTN-PARAS;
                      }
                    }
                    leaf number {
                      xr:xr-xml-map "pm_ma_oper:Number";
                      type int32;
                      description "channel number";
                    }
                  }
                }
              }

              container odu-minute15-history {
                xr:xr-xml-map "pm_ma_oper:OduMinute15History";
                description "port current performance data";

                container odu-minute15prbs-histories {
                  xr:xr-xml-map "pm_ma_oper:OduMinute15PRBSTableHis"+
                    "tory";
                  description "port current performance data";

                  list odu-minute15prbs-history {
                    xr:xr-xml-map "pm_ma_oper:OduMinute15PRBSHistor"+
                      "y";
                    key "number";
                    description
                      "port 15-minute prbs performance data";

                    container odu-minute15prbs-time-line-instances {
                      xr:xr-xml-map "pm_ma_oper:OduMinute15PRBSTabl"+
                        "eTimeLine";
                      description "port current performance data";

                      list odu-minute15prbs-time-line-instance {
                        xr:xr-xml-map "pm_ma_oper:OduMinute15PRBSTi"+
                          "meLineInstance";
                        key "number";
                        description
                          "port 15-minute prbs performance data";
                        leaf number {
                          xr:xr-xml-map "pm_ma_oper:Number";
                          type int32;
                          description "History Index number";
                        }
                        uses PM-PRBS-PARAS;
                      }
                    }
                    leaf number {
                      xr:xr-xml-map "pm_ma_oper:Number";
                      type int32;
                      description "channel number";
                    }
                  }
                }

                container odu-minute15gfp-histories {
                  xr:xr-xml-map "pm_ma_oper:OduMinute15GFPTableHist"+
                    "ory";
                  description "port current performance data";

                  list odu-minute15gfp-history {
                    xr:xr-xml-map "pm_ma_oper:OduMinute15GFPHistory";
                    key "number";
                    description
                      "port 15-minute otn performance data";

                    container odu-minute15gfp-time-line-instances {
                      xr:xr-xml-map "pm_ma_oper:OduMinute15GFPTable"+
                        "TimeLine";
                      description "port current performance data";

                      list odu-minute15gfp-time-line-instance {
                        xr:xr-xml-map "pm_ma_oper:OduMinute15GFPTim"+
                          "eLineInstance";
                        key "number";
                        description
                          "port 15-minute otn performance data";
                        leaf number {
                          xr:xr-xml-map "pm_ma_oper:Number";
                          type int32;
                          description "History Index number";
                        }
                        uses PM-GFP-PARAS;
                      }
                    }
                    leaf number {
                      xr:xr-xml-map "pm_ma_oper:Number";
                      type int32;
                      description "channel number";
                    }
                  }
                }

                container odu-minute15otn-histories {
                  xr:xr-xml-map "pm_ma_oper:OduMinute15OTNTableHist"+
                    "ory";
                  description "port current performance data";

                  list odu-minute15otn-history {
                    xr:xr-xml-map "pm_ma_oper:OduMinute15OTNHistory";
                    key "number";
                    description
                      "port 15-minute otn performance data";

                    container odu-minute15otn-time-line-instances {
                      xr:xr-xml-map "pm_ma_oper:OduMinute15OTNTable"+
                        "TimeLine";
                      description "port current performance data";

                      list odu-minute15otn-time-line-instance {
                        xr:xr-xml-map "pm_ma_oper:OduMinute15OTNTim"+
                          "eLineInstance";
                        key "number";
                        description
                          "port 15-minute otn performance data";
                        leaf number {
                          xr:xr-xml-map "pm_ma_oper:Number";
                          type int32;
                          description "History Index number";
                        }
                        uses PM-OTN-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container otu-history {
          xr:xr-xml-map "pm_ma_oper:otuHistory";
          description "OTU controller History performance data";

          container otu-port-histories {
            xr:xr-xml-map "pm_ma_oper:OtuHistoryPortTable";
            description "Port performance data";

            list otu-port-history {
              xr:xr-xml-map "pm_ma_oper:OtuPortHistory";
              key "name";
              description "Port performance data";

              container otu-minute15-history {
                xr:xr-xml-map "pm_ma_oper:OtuMinute15History";
                description "port current performance data";

                container otu-minute15fec-histories {
                  xr:xr-xml-map "pm_ma_oper:OtuMinute15FECTableHist"+
                    "ory";
                  description "port current performance data";

                  list otu-minute15fec-history {
                    xr:xr-xml-map "pm_ma_oper:OtuMinute15FECHistory";
                    key "number";
                    description
                      "port 15-minute fec performance data";

                    container otu-minute15fec-time-line-instances {
                      xr:xr-xml-map "pm_ma_oper:OtuMinute15FECTable"+
                        "TimeLine";
                      description "port current performance data";

                      list otu-minute15fec-time-line-instance {
                        xr:xr-xml-map "pm_ma_oper:OtuMinute15FECTim"+
                          "eLineInstance";
                        key "number";
                        description
                          "port 15-minute fec performance data";
                        leaf number {
                          xr:xr-xml-map "pm_ma_oper:Number";
                          type int32;
                          description "History Index number";
                        }
                        uses PM-FEC-PARAS;
                      }
                    }
                    leaf number {
                      xr:xr-xml-map "pm_ma_oper:Number";
                      type int32;
                      description "channel number";
                    }
                  }
                }

                container otu-minute15otn-histories {
                  xr:xr-xml-map "pm_ma_oper:OtuMinute15OTNTableHist"+
                    "ory";
                  description "port current performance data";

                  list otu-minute15otn-history {
                    xr:xr-xml-map "pm_ma_oper:OtuMinute15OTNHistory";
                    key "number";
                    description
                      "port 15-minute otn performance data";

                    container otu-minute15otn-time-line-instances {
                      xr:xr-xml-map "pm_ma_oper:OtuMinute15OTNTable"+
                        "TimeLine";
                      description "port current performance data";

                      list otu-minute15otn-time-line-instance {
                        xr:xr-xml-map "pm_ma_oper:OtuMinute15OTNTim"+
                          "eLineInstance";
                        key "number";
                        description
                          "port 15-minute otn performance data";
                        leaf number {
                          xr:xr-xml-map "pm_ma_oper:Number";
                          type int32;
                          description "History Index number";
                        }
                        uses PM-OTN-PARAS;
                      }
                    }
                    leaf number {
                      xr:xr-xml-map "pm_ma_oper:Number";
                      type int32;
                      description "channel number";
                    }
                  }
                }
              }

              container otu-hour24-history {
                xr:xr-xml-map "pm_ma_oper:OtuHour24History";
                description "port current performance data";

                container otu-hour24otn-histories {
                  xr:xr-xml-map "pm_ma_oper:OtuHour24OTNTableHistor"+
                    "y";
                  description "port 24 hour performance data";

                  list otu-hour24otn-history {
                    xr:xr-xml-map "pm_ma_oper:OtuHour24OTNHistory";
                    key "number";
                    description "port 24 hour otn performance data";

                    container otu-hour24otn-time-line-instances {
                      xr:xr-xml-map "pm_ma_oper:OtuHour24OTNTableTi"+
                        "meLine";
                      description "port current performance data";

                      list otu-hour24otn-time-line-instance {
                        xr:xr-xml-map "pm_ma_oper:OtuHour24OTNTimeL"+
                          "ineInstance";
                        key "number";
                        description
                          "port 15-minute otn performance data";
                        leaf number {
                          xr:xr-xml-map "pm_ma_oper:Number";
                          type int32;
                          description "History Index number";
                        }
                        uses PM-OTN-PARAS;
                      }
                    }
                    leaf number {
                      xr:xr-xml-map "pm_ma_oper:Number";
                      type int32;
                      description "channel number";
                    }
                  }
                }

                container otu-hour24fec-histories {
                  xr:xr-xml-map "pm_ma_oper:OtuHour24FECTableHistor"+
                    "y";
                  description "port current performance data";

                  list otu-hour24fec-history {
                    xr:xr-xml-map "pm_ma_oper:OtuHour24FECHistory";
                    key "number";
                    description "port 24 hour fec performance data";

                    container otu-hour24fec-time-line-instances {
                      xr:xr-xml-map "pm_ma_oper:OtuHour24FECTableTi"+
                        "meLine";
                      description "port current performance data";

                      list otu-hour24fec-time-line-instance {
                        xr:xr-xml-map "pm_ma_oper:OtuHour24FECTimeL"+
                          "ineInstance";
                        key "number";
                        description
                          "port 15-minute fec performance data";
                        leaf number {
                          xr:xr-xml-map "pm_ma_oper:Number";
                          type int32;
                          description "History Index number";
                        }
                        uses PM-FEC-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container ho-vc-history {
          xr:xr-xml-map "pm_ma_oper:Ho_vcHistory";
          description "HO_VC controller History performance data";

          container ho-vc-port-histories {
            xr:xr-xml-map "pm_ma_oper:Ho_vcHistoryPortTable";
            description "Port performance data";

            list ho-vc-port-history {
              xr:xr-xml-map "pm_ma_oper:Ho_vcPortHistory";
              key "name";
              description "Port performance data";

              container ho-vc-minute15-history {
                xr:xr-xml-map "pm_ma_oper:Ho_vcMinute15History";
                description "port current performance data";

                container ho-vc-minute15-path-histories {
                  xr:xr-xml-map "pm_ma_oper:Ho_vcMinute15PathTableH"+
                    "istory";
                  description "port current performance data";

                  list ho-vc-minute15-path-history {
                    xr:xr-xml-map "pm_ma_oper:Ho_vcMinute15PathHist"+
                      "ory";
                    key "number";
                    description
                      "port 15-minute Path performance data";

                    container "ho-vc-minute15-path-time-line"+
                      "-instances" {
                      xr:xr-xml-map "pm_ma_oper:Ho_vcMinute15PathTa"+
                        "bleTimeLine";
                      description "port current performance data";

                      list ho-vc-minute15-path-time-line-instance {
                        xr:xr-xml-map "pm_ma_oper:Ho_vcMinute15Path"+
                          "TimeLineInstance";
                        key "number";
                        description
                          "port 15-minute ho_vc performance data";
                        leaf number {
                          xr:xr-xml-map "pm_ma_oper:Number";
                          type int32;
                          description "History Index number";
                        }
                        uses PM-HO-VC-PARAS;
                      }
                    }
                    leaf number {
                      xr:xr-xml-map "pm_ma_oper:Number";
                      type int32;
                      description "channel number";
                    }
                  }
                }
              }

              container ho-vc-hour24-history {
                xr:xr-xml-map "pm_ma_oper:Ho_vcHour24History";
                description "port current performance data";

                container ho-vc-hour24-path-histories {
                  xr:xr-xml-map "pm_ma_oper:Ho_vcHour24PathTableHis"+
                    "tory";
                  description "port current performance data";

                  list ho-vc-hour24-path-history {
                    xr:xr-xml-map "pm_ma_oper:Ho_vcHour24PathHistor"+
                      "y";
                    key "number";
                    description
                      "port 24 hour Path performance data";

                    container "ho-vc-hour24-path-time-line"+
                      "-instances" {
                      xr:xr-xml-map "pm_ma_oper:Ho_vcHour24PathTabl"+
                        "eTimeLine";
                      description "port current performance data";

                      list ho-vc-hour24-path-time-line-instance {
                        xr:xr-xml-map "pm_ma_oper:Ho_vcHour24PathTi"+
                          "meLineInstance";
                        key "number";
                        description
                          "port 15-minute otn performance data";
                        leaf number {
                          xr:xr-xml-map "pm_ma_oper:Number";
                          type int32;
                          description "History Index number";
                        }
                        uses PM-HO-VC-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container optics-history {
          xr:xr-xml-map "pm_ma_oper:opticsHistory";
          description "OPTICS controller History performance data";

          container optics-port-histories {
            xr:xr-xml-map "pm_ma_oper:OpticsHistoryPortTable";
            description "Port performance data";

            list optics-port-history {
              xr:xr-xml-map "pm_ma_oper:OpticsPortHistory";
              key "name";
              description "Port performance data";

              container optics-hour24-history {
                xr:xr-xml-map "pm_ma_oper:OpticsHour24History";
                description "port current performance data";

                container optics-hour24-optics-histories {
                  xr:xr-xml-map "pm_ma_oper:OpticsHour24OpticsTable"+
                    "History";
                  description "port 24 hour performance data";

                  list optics-hour24-optics-history {
                    xr:xr-xml-map "pm_ma_oper:OpticsHour24OpticsHis"+
                      "tory";
                    key "number";
                    description
                      "port 24 hour optics performance data";

                    container "optics-hour24-optics-time-line"+
                      "-instances" {
                      xr:xr-xml-map "pm_ma_oper:OpticsHour24OpticsT"+
                        "ableTimeLine";
                      description "port current performance data";

                      list optics-hour24-optics-time-line-instance {
                        xr:xr-xml-map "pm_ma_oper:OpticsHour24Optic"+
                          "sTimeLineInstance";
                        key "number";
                        description
                          "port 15-minute otn performance data";
                        leaf number {
                          xr:xr-xml-map "pm_ma_oper:Number";
                          type int32;
                          description "History Index number";
                        }
                        uses PM-OPTICS-PARAS;
                      }
                    }
                    leaf number {
                      xr:xr-xml-map "pm_ma_oper:Number";
                      type int32;
                      description "channel number";
                    }
                  }
                }

                container optics-hour24fec-histories {
                  xr:xr-xml-map "pm_ma_oper:OpticsHour24FECTableHis"+
                    "tory";
                  description "port current performance data";

                  list optics-hour24fec-history {
                    xr:xr-xml-map "pm_ma_oper:OpticsHour24FECHistor"+
                      "y";
                    key "number";
                    description "port 24 hour fec performance data";

                    container optics-hour24fec-time-line-instances {
                      xr:xr-xml-map "pm_ma_oper:OpticsHour24FECTabl"+
                        "eTimeLine";
                      description "port current performance data";

                      list optics-hour24fec-time-line-instance {
                        xr:xr-xml-map "pm_ma_oper:OpticsHour24FECTi"+
                          "meLineInstance";
                        key "number";
                        description
                          "port 15-minute fec performance data";
                        leaf number {
                          xr:xr-xml-map "pm_ma_oper:Number";
                          type int32;
                          description "History Index number";
                        }
                        uses PM-FEC-PARAS;
                      }
                    }
                    leaf number {
                      xr:xr-xml-map "pm_ma_oper:Number";
                      type int32;
                      description "channel number";
                    }
                  }
                }
              }

              container optics-minute15-history {
                xr:xr-xml-map "pm_ma_oper:OpticsMinute15History";
                description "port current performance data";

                container optics-minute15-optics-histories {
                  xr:xr-xml-map "pm_ma_oper:OpticsMinute15OpticsTab"+
                    "leHistory";
                  description "port current performance data";

                  list optics-minute15-optics-history {
                    xr:xr-xml-map "pm_ma_oper:OpticsMinute15OpticsH"+
                      "istory";
                    key "number";
                    description
                      "port 15-minute optics performance data";

                    container "optics-minute15-optics-time-line"+
                      "-instances" {
                      xr:xr-xml-map "pm_ma_oper:OpticsMinute15Optic"+
                        "sTableTimeLine";
                      description "port current performance data";

                      list "optics-minute15-optics-time-line"+
                        "-instance" {
                        xr:xr-xml-map "pm_ma_oper:OpticsMinute15Opt"+
                          "icsTimeLineInstance";
                        key "number";
                        description
                          "port 15-minute otn performance data";
                        leaf number {
                          xr:xr-xml-map "pm_ma_oper:Number";
                          type int32;
                          description "History Index number";
                        }
                        uses PM-OPTICS-PARAS;
                      }
                    }
                    leaf number {
                      xr:xr-xml-map "pm_ma_oper:Number";
                      type int32;
                      description "channel number";
                    }
                  }
                }

                container optics-minute15fec-histories {
                  xr:xr-xml-map "pm_ma_oper:OpticsMinute15FECTableH"+
                    "istory";
                  description "port current performance data";

                  list optics-minute15fec-history {
                    xr:xr-xml-map "pm_ma_oper:OpticsMinute15FECHist"+
                      "ory";
                    key "number";
                    description
                      "port 15-minute fec performance data";

                    container "optics-minute15fec-time-line"+
                      "-instances" {
                      xr:xr-xml-map "pm_ma_oper:OpticsMinute15FECTa"+
                        "bleTimeLine";
                      description "port current performance data";

                      list optics-minute15fec-time-line-instance {
                        xr:xr-xml-map "pm_ma_oper:OpticsMinute15FEC"+
                          "TimeLineInstance";
                        key "number";
                        description
                          "port 15-minute fec performance data";
                        leaf number {
                          xr:xr-xml-map "pm_ma_oper:Number";
                          type int32;
                          description "History Index number";
                        }
                        uses PM-FEC-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }

        container oc-history {
          xr:xr-xml-map "pm_ma_oper:ocHistory";
          description "OC controller History performance data";

          container oc-port-histories {
            xr:xr-xml-map "pm_ma_oper:OcHistoryPortTable";
            description "Port performance data";

            list oc-port-history {
              xr:xr-xml-map "pm_ma_oper:OcPortHistory";
              key "name";
              description "Port performance data";

              container oc-hour24-history {
                xr:xr-xml-map "pm_ma_oper:OcHour24History";
                description "port current performance data";

                container oc-hour24ocn-histories {
                  xr:xr-xml-map "pm_ma_oper:OcHour24OCNTableHistory";
                  description "port current performance data";

                  list oc-hour24ocn-history {
                    xr:xr-xml-map "pm_ma_oper:OcHour24OCNHistory";
                    key "number";
                    description "port 24 hour ocn performance data";

                    container oc-hour24ocn-time-line-instances {
                      xr:xr-xml-map "pm_ma_oper:OcHour24OCNTableTim"+
                        "eLine";
                      description "port current performance data";

                      list oc-hour24ocn-time-line-instance {
                        xr:xr-xml-map "pm_ma_oper:OcHour24OCNTimeLi"+
                          "neInstance";
                        key "number";
                        description
                          "port 15-minute otn performance data";
                        leaf number {
                          xr:xr-xml-map "pm_ma_oper:Number";
                          type int32;
                          description "History Index number";
                        }
                        uses PM-SONET-PARAS;
                      }
                    }
                    leaf number {
                      xr:xr-xml-map "pm_ma_oper:Number";
                      type int32;
                      description "channel number";
                    }
                  }
                }
              }

              container oc-minute15-history {
                xr:xr-xml-map "pm_ma_oper:OcMinute15History";
                description "port current performance data";

                container oc-minute15ocn-histories {
                  xr:xr-xml-map "pm_ma_oper:OcMinute15OCNTableHisto"+
                    "ry";
                  description "port current performance data";

                  list oc-minute15ocn-history {
                    xr:xr-xml-map "pm_ma_oper:OcMinute15OCNHistory";
                    key "number";
                    description
                      "port 15-minute ocn performance data";

                    container oc-minute15ocn-time-line-instances {
                      xr:xr-xml-map "pm_ma_oper:OcMinute15OCNTableT"+
                        "imeLine";
                      description "port current performance data";

                      list oc-minute15ocn-time-line-instance {
                        xr:xr-xml-map "pm_ma_oper:OcMinute15OCNTime"+
                          "LineInstance";
                        key "number";
                        description
                          "port 15-minute ocn performance data";
                        leaf number {
                          xr:xr-xml-map "pm_ma_oper:Number";
                          type int32;
                          description "History Index number";
                        }
                        uses PM-SONET-PARAS;
                      }
                    }
                    leaf number {
                      xr:xr-xml-map "pm_ma_oper:Number";
                      type int32;
                      description "channel number";
                    }
                  }
                }
              }
              leaf name {
                xr:xr-xml-map "pm_ma_oper:Name";
                type xr:Interface-name;
                description "Port name";
              }
            }
          }
        }
      }
    }
  }
}
