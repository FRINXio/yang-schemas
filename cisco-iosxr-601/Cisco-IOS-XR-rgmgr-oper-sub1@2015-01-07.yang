submodule Cisco-IOS-XR-rgmgr-oper-sub1 {

  belongs-to Cisco-IOS-XR-rgmgr-oper {
    prefix Cisco-IOS-XR-rgmgr-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR rgmgr package operational data.

     Copyright (c) 2013-2015 by Cisco Systems, Inc.
     All rights reserved.";

  revision "2015-01-07" {
    description
      "IOS XR 5.3.1 revision.";
  }


  grouping RGMGR-RED-GRP {
    description "RGMGR RED GRP";
    leaf multi-router-aps-group-number {
      xr:xr-xml-map "rgmgr_show:MultiRouterAPSGroupNumber";
      type string {
        length "0..64";
      }
      description "Configured interchassis redundancy group number";
    }
    leaf controller-name-xr {
      xr:xr-xml-map "rgmgr_show:controller-name-xr";
      type string {
        length "0..64";
      }
      description "Name of controller being backed up";
    }
    leaf controller-handle {
      xr:xr-xml-map "rgmgr_show:ControllerHandle";
      type xr:Interface-name;
      description "Handle of controller being backed up";
    }
    leaf backup-interface-name {
      xr:xr-xml-map "rgmgr_show:BackupInterfaceName";
      type string {
        length "0..64";
      }
      description "Backup interface name";
    }
    leaf backup-interface-handle {
      xr:xr-xml-map "rgmgr_show:BackupInterfaceHandle";
      type xr:Interface-name;
      description "Backup interface handle";
    }
    leaf backup-interface-next-hop-ip-address {
      xr:xr-xml-map "rgmgr_show:BackupInterfaceNextHopIPAddress";
      type inet:ipv4-address;
      description "Backup interface next hop IP address";
    }
    leaf inter-chassis-group-state {
      xr:xr-xml-map "rgmgr_show:InterChassisGroupState";
      type string {
        length "0..64";
      }
      description "Configured interchassis redundancy group state";
    }
  }
}
