submodule Cisco-IOS-XR-infra-syslog-oper-sub1 {

  belongs-to Cisco-IOS-XR-infra-syslog-oper {
    prefix Cisco-IOS-XR-infra-syslog-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-syslog package operational data.

     Copyright (c) 2013-2015 by Cisco Systems, Inc.
     All rights reserved.";

  revision "2015-12-01" {
    description
      "Schema added for Logging history oper data";
  }

  revision "2015-01-07" {
    description
      "IOS XR 5.3.1 revision.";
  }

  typedef System-message-severity {
    type enumeration {
      enum message-severity-unknown {
        value -1;
        description "Unknown";
      }
      enum message-severity-emergency {
        value 0;
        description "Emergency";
      }
      enum message-severity-alert {
        value 1;
        description "Alert";
      }
      enum message-severity-critical {
        value 2;
        description "Critical";
      }
      enum message-severity-error {
        value 3;
        description "Error";
      }
      enum message-severity-warning {
        value 4;
        description "Warning";
      }
      enum message-severity-notice {
        value 5;
        description "Notice";
      }
      enum message-severity-informational {
        value 6;
        description "Informational";
      }
      enum message-severity-debug {
        value 7;
        description "Debug";
      }
    }
    description "System message severity";
  }

  grouping FILE-LOG-STATS {
    description "System log file destination statistics";
    leaf file-name {
      xr:xr-xml-map "infra_syslog:FileName";
      type string;
      description "File name for logging messages";
    }
    leaf message-count {
      xr:xr-xml-map "infra_syslog:MessageCount";
      type uint32;
      description "Message count";
    }
  }

  grouping REMOTE-LOG-STATS {
    description "System log remote statistics";
    leaf remote-host-name {
      xr:xr-xml-map "infra_syslog:RemoteHostname";
      type string;
      description "Remote hostname";
    }
    leaf message-count {
      xr:xr-xml-map "infra_syslog:MessageCount";
      type uint32;
      description "Message count";
    }
  }

  grouping LOG-DEST-STATS {
    description "System log statistics";
    leaf is-log-enabled {
      xr:xr-xml-map "infra_syslog:IsLogEnabled";
      type boolean;
      description "Is log enabled";
    }
    leaf severity {
      xr:xr-xml-map "infra_syslog:Severity";
      type System-message-severity;
      description "Configured severity";
    }
    leaf message-count {
      xr:xr-xml-map "infra_syslog:MessageCount";
      type uint32;
      description "Message count";
    }
    leaf buffer-size {
      xr:xr-xml-map "infra_syslog:BufferSize";
      type uint32;
      units "byte";
      description
        "Buffer size in bytes if logging buffer isenabled";
    }
  }

  grouping LOG-ENABLE-STATS {
    description "System log discard statistics";
    leaf is-log-enabled {
      xr:xr-xml-map "infra_syslog:IsLogEnabled";
      type boolean;
      description "Is log enabled";
    }
    leaf drop-count {
      xr:xr-xml-map "infra_syslog:DropCount";
      type uint32;
      description "Number of messages dropped";
    }
    leaf flush-count {
      xr:xr-xml-map "infra_syslog:FlushCount";
      type uint32;
      description "Number of messages flushed";
    }
    leaf overrun-count {
      xr:xr-xml-map "infra_syslog:OverrunCount";
      type uint32;
      description "Number of messages overrun";
    }
  }

  grouping SYSTEM-MESSAGE-STATISTICS {
    description "System message statistics";

    container logging-stats {
      description "Logging statistics";
      uses LOG-ENABLE-STATS;
    }

    container console-logging-stats {
      description "Console logging statistics";
      uses LOG-DEST-STATS;
    }

    container monitor-logging-stats {
      description "Monitor loggingstatistics";
      uses LOG-DEST-STATS;
    }

    container trap-logging-stats {
      description "Trap logging statistics";
      uses LOG-DEST-STATS;
    }

    container buffer-logging-stats {
      description "Buffer logging statistics";
      uses LOG-DEST-STATS;
    }

    list remote-logging-stat {
      description "Remote logging statistics";
      uses REMOTE-LOG-STATS;
    }

    list file-logging-stat {
      description "File logging statistics";
      uses FILE-LOG-STATS;
    }
  }

  grouping SYSTEM-MESSAGE {
    description "System message";
    leaf card-type {
      xr:xr-xml-map "infra_syslog:CardType";
      type string;
      description
        "Message card location: 'RP', 'DRP', 'LC', 'SC',
        'SP' or 'UNK' ";
    }
    leaf node-name {
      xr:xr-xml-map "infra_syslog:NodeName";
      type xr:Node-id;
      description "Message source location";
    }
    leaf time-stamp {
      xr:xr-xml-map "infra_syslog:TimeStamp";
      type uint64;
      units "millisecond";
      description
        "Time in milliseconds since 00:00:00 UTC, January
        11970 of when message was generated";
    }
    leaf time-of-day {
      xr:xr-xml-map "infra_syslog:TimeOfDay";
      type string;
      description
        "Time of day of event in DDD MMM DD  YYYY HH:MM
        :SS format, e.g Wed Apr 01 2009  15:50:26";
    }
    leaf time-zone {
      xr:xr-xml-map "infra_syslog:TimeZone";
      type string;
      description
        "Time Zone in UTC+/-HH:MM format,  e.g UTC+5:30,
        UTC-6";
    }
    leaf process-name {
      xr:xr-xml-map "infra_syslog:ProcessName";
      type string;
      description "Process name";
    }
    leaf category {
      xr:xr-xml-map "infra_syslog:Category";
      type string;
      description "Message category";
    }
    leaf group {
      xr:xr-xml-map "infra_syslog:Group";
      type string;
      description "Message group";
    }
    leaf message-name {
      xr:xr-xml-map "infra_syslog:MessageName";
      type string;
      description "Message name";
    }
    leaf severity {
      xr:xr-xml-map "infra_syslog:Severity";
      type System-message-severity;
      description "Message severity";
    }
    leaf text {
      xr:xr-xml-map "infra_syslog:Text";
      type string;
      description "Additional message text";
    }
  }

  grouping AN-REMOTE-LOG-SERVER {
    description "A System log AN remote log server structure";
    leaf ip-address {
      xr:xr-xml-map "infra_syslog:IPAddress";
      type string;
      description "IP Address";
    }
    leaf vrf-name {
      xr:xr-xml-map "infra_syslog:VRFName";
      type string;
      description "VRF Name";
    }
    leaf vrf-severity {
      xr:xr-xml-map "infra_syslog:VRFSeverity";
      type string;
      description "VRF Severity";
    }
    leaf rh-discriminator {
      xr:xr-xml-map "infra_syslog:RH_Discriminator";
      type string;
      description "Remote-Host Discriminator";
    }
  }

  grouping AN-REMOTE-LOG-SERVERS {
    description "System log All AN remote servers";

    list an-remote-log-server {
      description "AN Remote Log Servers";
      uses AN-REMOTE-LOG-SERVER;
    }
  }
}
