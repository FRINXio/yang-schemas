module Cisco-IOS-XR-ip-tcp-oper {

  /*** NAMESPACE / PREFIX DEFINITION ***/

  namespace "http://cisco.com/ns/yang/Cisco-IOS-XR-ip-tcp-oper";


  prefix "ip-tcp-oper";

  /*** LINKAGE (IMPORTS / INCLUDES) ***/

  import Cisco-IOS-XR-types { prefix "xr"; }

  include Cisco-IOS-XR-ip-tcp-oper-sub5 {
    revision-date 2015-11-09;
  }

  include Cisco-IOS-XR-ip-tcp-oper-sub4 {
    revision-date 2015-11-09;
  }

  include Cisco-IOS-XR-ip-tcp-oper-sub3 {
    revision-date 2015-11-09;
  }

  include Cisco-IOS-XR-ip-tcp-oper-sub2 {
    revision-date 2015-11-09;
  }

  include Cisco-IOS-XR-ip-tcp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-tcp package operational data.

     This module contains definitions
     for the following management objects:
       tcp-connection: TCP connection operational data
       tcp: tcp
       tcp-nsr: tcp nsr

     Copyright (c) 2013-2015 by Cisco Systems, Inc.
     All rights reserved.";

  revision "2015-11-09" {
    description
      "IOS XR 6.0 revision.";
  }

  typedef Show {
    type enumeration {
      enum all {
        value 0;
        description "To dispay all";
      }
      enum static-policy {
        value 1;
        description "To display static policy";
      }
      enum interface-filter {
        value 2;
        description "To display interface filter";
      }
      enum packet-filter {
        value 3;
        description "To display packet type filter";
      }
    }
    description "Show";
  }

  container tcp-connection {
    xr:xr-xml-map "ip_tcp_oper:TCPConnection";
    config false;
    description "TCP connection operational data";

    container nodes {
      xr:xr-xml-map "ip_tcp_oper:NodeTable";
      description
        "Table of information about all nodes present on
        the system";

      list node {
        xr:xr-xml-map "ip_tcp_oper:Node";
        key "id";
        description "Information about a single node";

        container statistics {
          xr:xr-xml-map "ip_tcp_oper:Statistics";
          description "Statistics of all TCP connections";

          container clients {
            xr:xr-xml-map "ip_tcp_oper:ClientTable";
            description "Table listing clients";

            list client {
              xr:xr-xml-map "ip_tcp_oper:Client";
              key "client-id";
              description "Describing Client ID";
              leaf client-id {
                xr:xr-xml-map "ip_tcp_oper:ClientID";
                type uint32 {
                  range "0..4294967295";
                }
                description
                  "Displaying client's aggregated statistics";
              }
              uses TRANSP-CLIENT-STATS-BAG;
            }
          }

          container pcbs {
            xr:xr-xml-map "ip_tcp_oper:PCBTable";
            description
              "Table listing the TCP connections for which
              statistics are provided";

            list pcb {
              xr:xr-xml-map "ip_tcp_oper:PCB";
              key "id";
              description "Protocol Control Block ID";
              leaf id {
                xr:xr-xml-map "ip_tcp_oper:ID";
                type uint32 {
                  range "0..4294967295";
                }
                description
                  "Displaying statistics associated with a
                  particular PCB";
              }
              uses TCP-SH-PCB-STATS-BAG;
            }
          }

          container summary {
            xr:xr-xml-map "ip_tcp_oper:Summary";
            description
              "Summary statistics across all TCP connections";
            uses TCP-SH-STATS-BAG;
          }
        }

        container extended-information {
          xr:xr-xml-map "ip_tcp_oper:ExtendedInformation";
          description "Extended Filter related Information";

          container display-types {
            xr:xr-xml-map "ip_tcp_oper:DisplayTypeTable";
            description "Table listing display types";

            list display-type {
              xr:xr-xml-map "ip_tcp_oper:DisplayType";
              key "disp-type";
              description "Describing particular display type";
              leaf disp-type {
                xr:xr-xml-map "ip_tcp_oper:DispType";
                type Show;
                description "Specifying display type";
              }

              list connection-id {
                xr:xr-xml-map "ip_tcp_oper:ConnectionID";
                key "pcb-id";
                description "Describing connection ID";
                leaf pcb-id {
                  xr:xr-xml-map "ip_tcp_oper:PCB_ID";
                  type uint32 {
                    range "0..4294967295";
                  }
                  description
                    "Displaying inforamtion based on selected
                    display type associatedwith a particular
                    PCB";
                }
                uses SHOW-PCB-INFO;
              }
            }
          }
        }

        container detail-informations {
          xr:xr-xml-map "ip_tcp_oper:DetailInformationTable";
          description
            "Table listing TCP connections for which
            detailed information is provided";

          list detail-information {
            xr:xr-xml-map "ip_tcp_oper:DetailInformation";
            key "pcb-id";
            description "Protocol Control Block ID";
            leaf pcb-id {
              xr:xr-xml-map "ip_tcp_oper:PCB_ID";
              type uint32 {
                range "0..4294967295";
              }
              description
                "Detail information about TCP connection, put
                null for all";
            }
            uses TCP-SH-TABLE-BAG;
          }
        }

        container brief-informations {
          xr:xr-xml-map "ip_tcp_oper:BriefInformationTable";
          description
            "Table listing connections for which brief
            information is provided.Note that not all
            connections are listed in the brief table.";

          list brief-information {
            xr:xr-xml-map "ip_tcp_oper:BriefInformation";
            key "pcb-id";
            description "Brief information about a TCP connection";
            leaf pcb-id {
              xr:xr-xml-map "ip_tcp_oper:PCB_ID";
              type uint32 {
                range "0..4294967295";
              }
              description "Protocol Control Block ID";
            }
            uses TCP-SH-BRIEF-BAG;
          }
        }
        leaf id {
          xr:xr-xml-map "ip_tcp_oper:ID";
          type xr:Node-id;
          description "Describing a location";
        }
      }
    }
  }

  container tcp {
    xr:xr-xml-map "ip_tcp_traffic_oper:TCP";
    config false;
    description "tcp";

    container nodes {
      xr:xr-xml-map "ip_tcp_traffic_oper:NodeTable";
      description "Node-specific TCP operational data";

      list node {
        xr:xr-xml-map "ip_tcp_traffic_oper:Node";
        key "node-name";
        description "TCP operational data for a particular node";

        container statistics {
          xr:xr-xml-map "ip_tcp_traffic_oper:Statistics";
          description "Statistical TCP operational data for a node";

          container ipv4-traffic {
            xr:xr-xml-map "ip_tcp_traffic_oper:IPv4Traffic";
            description "TCP Traffic statistics for IPv4";
            uses IP-TCP;
          }

          container ipv6-traffic {
            xr:xr-xml-map "ip_tcp_traffic_oper:IPv6Traffic";
            description "TCP Traffic statistics for IPv6";
            uses IP-TCP;
          }
        }
        leaf node-name {
          xr:xr-xml-map "ip_tcp_traffic_oper:NodeName";
          type xr:Node-id;
          description "Node name";
        }
      }
    }
  }

  container tcp-nsr {
    xr:xr-xml-map "ip_tcp_sso_oper:TCP_NSR";
    config false;
    description "tcp nsr";

    container nodes {
      xr:xr-xml-map "ip_tcp_sso_oper:NodeTable";
      description
        "Table of information about all nodes present on
        the system";

      list node {
        xr:xr-xml-map "ip_tcp_sso_oper:Node";
        key "id";
        description "Information about a single node";

        container session {
          xr:xr-xml-map "ip_tcp_sso_oper:Session";
          description "Information about TCP NSR Sessions";

          container brief-sessions {
            xr:xr-xml-map "ip_tcp_sso_oper:BriefSessionTable";
            description "Information about TCP NSR Sessions";

            list brief-session {
              xr:xr-xml-map "ip_tcp_sso_oper:BriefSession";
              key "id";
              description "Brief information about NSR Sessions";
              leaf id {
                xr:xr-xml-map "ip_tcp_sso_oper:ID";
                type xr:Hex-integer;
                description "ID of NSR Sesison";
              }
              uses TCP-NSR-PCB-BRIEF-BAG;
            }
          }

          container detail-sessions {
            xr:xr-xml-map "ip_tcp_sso_oper:DetailSessionTable";
            description "Table about TCP NSR Sessions details";

            list detail-session {
              xr:xr-xml-map "ip_tcp_sso_oper:DetailSession";
              key "id";
              description
                "showing detailed information of NSR Sessions";
              leaf id {
                xr:xr-xml-map "ip_tcp_sso_oper:ID";
                type xr:Hex-integer;
                description "ID of NSR Sesison";
              }
              uses TCP-NSR-PCB-DETAILED-BAG;
            }
          }
        }

        container client {
          xr:xr-xml-map "ip_tcp_sso_oper:Client";
          description "Information about TCP NSR Client";

          container detail-clients {
            xr:xr-xml-map "ip_tcp_sso_oper:DetailClientTable";
            description "Table about TCP NSR Client details";

            list detail-client {
              xr:xr-xml-map "ip_tcp_sso_oper:DetailClient";
              key "id";
              description
                "showing detailed information of NSR Clients";
              leaf id {
                xr:xr-xml-map "ip_tcp_sso_oper:ID";
                type xr:Hex-integer;
                description "ID of NSR client";
              }
              uses TCP-NSR-CCB-DETAILED-BAG;
            }
          }

          container brief-clients {
            xr:xr-xml-map "ip_tcp_sso_oper:BriefClientTable";
            description "Information about TCP NSR Client";

            list brief-client {
              xr:xr-xml-map "ip_tcp_sso_oper:BriefClient";
              key "id";
              description "Brief information about NSR Client";
              leaf id {
                xr:xr-xml-map "ip_tcp_sso_oper:ID";
                type xr:Hex-integer;
                description "ID of NSR client";
              }
              uses TCP-NSR-CCB-BRIEF-BAG;
            }
          }
        }

        container session-set {
          xr:xr-xml-map "ip_tcp_sso_oper:SessionSet";
          description "Information about TCP NSR Session Sets";

          container detail-sets {
            xr:xr-xml-map "ip_tcp_sso_oper:DetailSetTable";
            description "Table about TCP NSR Session Sets details";

            list detail-set {
              xr:xr-xml-map "ip_tcp_sso_oper:DetailSet";
              key "id";
              description
                "showing detailed information of NSR Session
                Sets";
              leaf id {
                xr:xr-xml-map "ip_tcp_sso_oper:ID";
                type xr:Hex-integer;
                description "ID of NSR Sesison Set";
              }
              uses TCP-NSR-SSCB-DETAILED-BAG;
            }
          }

          container brief-sets {
            xr:xr-xml-map "ip_tcp_sso_oper:BriefSetTable";
            description "Information about TCP NSR Session Sets";

            list brief-set {
              xr:xr-xml-map "ip_tcp_sso_oper:BriefSet";
              key "id";
              description
                "Brief information about NSR Session Sets";
              leaf id {
                xr:xr-xml-map "ip_tcp_sso_oper:ID";
                type xr:Hex-integer;
                description "ID of NSR Session Set";
              }
              uses TCP-NSR-SSCB-BRIEF-BAG;
            }
          }
        }

        container statistics {
          xr:xr-xml-map "ip_tcp_sso_oper:Statistics";
          description
            "Statis Information about TCP NSR connections";

          container summary {
            xr:xr-xml-map "ip_tcp_sso_oper:Summary";
            description
              "Summary statistics across all NSR connections";
            uses TCP-NSR-SUMMARY-STATS-BAG;
          }

          container statistic-clients {
            xr:xr-xml-map "ip_tcp_sso_oper:StatisticClientTable";
            description
              "Table listing NSR connections for which
              statistic information is provided";

            list statistic-client {
              xr:xr-xml-map "ip_tcp_sso_oper:StatisticClient";
              key "id";
              description
                "showing statistic information of NSR Clients";
              leaf id {
                xr:xr-xml-map "ip_tcp_sso_oper:ID";
                type xr:Hex-integer;
                description "ID of NSR Client";
              }
              uses TCP-NSR-CCB-STATS-BAG;
            }
          }

          container statistic-sets {
            xr:xr-xml-map "ip_tcp_sso_oper:StatisticSetTable";
            description
              "Table listing NSR connections for which
              statistic information is provided";

            list statistic-set {
              xr:xr-xml-map "ip_tcp_sso_oper:StatisticSet";
              key "id";
              description
                "showing statistic information of NSR Session
                Set";
              leaf id {
                xr:xr-xml-map "ip_tcp_sso_oper:ID";
                type xr:Hex-integer;
                description "ID of NSR Session Set";
              }
              uses TCP-NSR-SSCB-STATS-BAG;
            }
          }

          container statistic-sessions {
            xr:xr-xml-map "ip_tcp_sso_oper:StatisticSessionTable";
            description
              "Table listing NSR connections for which
              statistic information is provided";

            list statistic-session {
              xr:xr-xml-map "ip_tcp_sso_oper:StatisticSession";
              key "id";
              description
                "showing statistic information of TCP
                connections";
              leaf id {
                xr:xr-xml-map "ip_tcp_sso_oper:ID";
                type xr:Hex-integer;
                description "ID of TCP connection";
              }
              uses TCP-NSR-PCB-STATS-BAG;
            }
          }
        }
        leaf id {
          xr:xr-xml-map "ip_tcp_sso_oper:ID";
          type xr:Node-id;
          description "Describing a location";
        }
      }
    }
  }
}
