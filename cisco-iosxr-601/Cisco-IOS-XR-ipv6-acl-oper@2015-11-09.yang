module Cisco-IOS-XR-ipv6-acl-oper {

  /*** NAMESPACE / PREFIX DEFINITION ***/

  namespace "http://cisco.com/ns/yang/Cisco-IOS-XR-ipv6-acl-oper";


  prefix "ipv6-acl-oper";

  /*** LINKAGE (IMPORTS / INCLUDES) ***/

  import Cisco-IOS-XR-types { prefix "xr"; }

  import Cisco-IOS-XR-ipv6-acl-datatypes { prefix "dt1"; }

  import Cisco-IOS-XR-common-acl-datatypes { prefix "dt2"; }

  include Cisco-IOS-XR-ipv6-acl-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-acl package operational data.

     This module contains definitions
     for the following management objects:
       ipv6-acl-and-prefix-list: Root class of IPv6 Oper schema tree

     Copyright (c) 2013-2015 by Cisco Systems, Inc.
     All rights reserved.";

  revision "2015-11-09" {
    description
      "IOS XR 6.0 revision.";
  }


  container ipv6-acl-and-prefix-list {
    xr:xr-xml-map "ipv6_acl_oper:IPV6_ACLAndPrefixList";
    config false;
    description "Root class of IPv6 Oper schema tree";

    container access-list-manager {
      xr:xr-xml-map "ipv6_acl_ext_oper:AccessListManager";
      description
        "AccessListManager containing ACLs and prefix
        lists";

      container prefixes {
        xr:xr-xml-map "ipv6_acl_ext_oper:PrefixListTable";
        description "Table of prefix lists";

        list prefix {
          xr:xr-xml-map "ipv6_acl_ext_oper:PrefixList";
          key "prefix-list-name";
          description "Name of the prefix list";

          container prefix-list-sequences {
            xr:xr-xml-map "ipv6_acl_ext_oper:PrefixListSequenceTabl"+
              "e";
            description
              "Table of all the SequenceNumbers per prefix
              list";

            list prefix-list-sequence {
              xr:xr-xml-map "ipv6_acl_ext_oper:PrefixListSequence";
              key "sequence-number";
              description "Sequence Number of a prefix list entry";
              leaf sequence-number {
                xr:xr-xml-map "ipv6_acl_ext_oper:SequenceNumber";
                type dt2:Acl-sequence-number-range;
                description
                  "Sequence Number of the prefix list entry";
              }
              uses IPV6-PFX-EDM-ACE;
            }
          }
          leaf prefix-list-name {
            xr:xr-xml-map "ipv6_acl_ext_oper:PrefixListName";
            type dt1:Ipv6-acl-prefix-list-name;
            description "Name of the prefix list";
          }
        }
      }

      container usages {
        xr:xr-xml-map "ipv6_acl_ext_oper:UsageTable";
        description
          "Table of Usage statistics of ACLs at different
          nodes";

        list usage {
          xr:xr-xml-map "ipv6_acl_ext_oper:Usage";
          description "Usage statistics of an ACL at a node";
          leaf node-name {
            xr:xr-xml-map "ipv6_acl_ext_oper:NodeName";
            type xr:Node-id;
            description "Node where ACL is applied";
          }
          leaf application-id {
            xr:xr-xml-map "ipv6_acl_ext_oper:ApplicationID";
            type dt2:Acl-usage-app-id-enum;
            description "Application ID";
          }
          leaf access-list-name {
            xr:xr-xml-map "ipv6_acl_ext_oper:AccessListName";
            type dt1:Ipv6-acl-prefix-list-name;
            description "Name of the ACL";
          }
          leaf usage-details {
            xr:xr-xml-map "ipv6_acl_ext_oper:UsageDetails";
            type string;
            mandatory true;
            description "Usage Statistics Details";
          }
        }
      }

      container accesses {
        xr:xr-xml-map "ipv6_acl_ext_oper:AccessListTable";
        description "ACL class displaying Usage and Entries";

        list access {
          xr:xr-xml-map "ipv6_acl_ext_oper:AccessList";
          key "access-list-name";
          description "Name of the Access List";

          container access-list-sequences {
            xr:xr-xml-map "ipv6_acl_ext_oper:AccessListSequenceTabl"+
              "e";
            description "Table of all the sequence numbers per ACL";

            list access-list-sequence {
              xr:xr-xml-map "ipv6_acl_ext_oper:AccessListSequence";
              key "sequence-number";
              description "Sequence number of an ACL entry";
              leaf sequence-number {
                xr:xr-xml-map "ipv6_acl_ext_oper:SequenceNumber";
                type dt2:Acl-sequence-number-range;
                description "ACL entry sequence number";
              }
              uses IPV6-ACL-EDM-ACE;
            }
          }
          leaf access-list-name {
            xr:xr-xml-map "ipv6_acl_ext_oper:AccessListName";
            type dt1:Ipv6-acl-prefix-list-name;
            description "Name of the Access List";
          }
        }
      }
    }

    container oor {
      xr:xr-xml-map "ipv6_acl_oper:OOR";
      description
        "Out Of Resources, Limits to the resources
        allocatable";

      container details {
        xr:xr-xml-map "ipv6_acl_ext_oper:Details";
        description "Details of the overall out of resource limit";
        uses IPV6-ACL-EDM-OOR-DETAIL;
      }

      container prefix-list-summary {
        xr:xr-xml-map "ipv6_acl_ext_oper:PrefixListSummary";
        description
          "Summary of the prefix Lists resource
          utilization";

        container details {
          xr:xr-xml-map "ipv6_acl_ext_oper:Details";
          description
            "Summary Detail of the prefix list Resource
            Utilisation";
          uses IPV6-ACL-EDM-OOR-DETAIL;
        }
      }

      container oor-accesses {
        xr:xr-xml-map "ipv6_acl_ext_oper:OORAccessListTable";
        description "Resource occupation details for ACLs";

        list oor-access {
          xr:xr-xml-map "ipv6_acl_ext_oper:OORAccessList";
          key "access-list-name";
          description
            "Resource occupation details for a particular
            ACL";
          leaf access-list-name {
            xr:xr-xml-map "ipv6_acl_ext_oper:AccessListName";
            type dt1:Ipv6-acl-prefix-list-name;
            description "Name of the Access List";
          }
          uses IPV6-ACL-EDM-OOR-DETAIL;
        }
      }

      container oor-prefixes {
        xr:xr-xml-map "ipv6_acl_ext_oper:OORPrefixListTable";
        description "Resource occupation details for prefix lists";

        list oor-prefix {
          xr:xr-xml-map "ipv6_acl_ext_oper:OORPrefixList";
          key "prefix-list-name";
          description
            "Resource occupation details for a particular
            prefix list";
          leaf prefix-list-name {
            xr:xr-xml-map "ipv6_acl_ext_oper:PrefixListName";
            type dt1:Ipv6-acl-prefix-list-name;
            description "Name of a prefix list";
          }
          uses IPV6-ACL-EDM-OOR-DETAIL;
        }
      }

      container access-list-summary {
        xr:xr-xml-map "ipv6_acl_ext_oper:AccessListSummary";
        description "Resource Limits pertaining to ACLs only";

        container details {
          xr:xr-xml-map "ipv6_acl_ext_oper:Details";
          description
            "Details containing the resource limits of the
            ACLs";
          uses IPV6-ACL-EDM-OOR-DETAIL;
        }
      }
    }
  }
}
