module Cisco-IOS-XR-mpls-te-cfg {

  /*** NAMESPACE / PREFIX DEFINITION ***/

  namespace "http://cisco.com/ns/yang/Cisco-IOS-XR-mpls-te-cfg";


  prefix "mpls-te-cfg";

  /*** LINKAGE (IMPORTS / INCLUDES) ***/

  import ietf-inet-types { prefix "inet"; }

  import Cisco-IOS-XR-types { prefix "xr"; }

  import Cisco-IOS-XR-ifmgr-cfg { prefix "a1"; }

  import Cisco-IOS-XR-snmp-agent-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-te package configuration.

     This module contains definitions
     for the following management objects:
       mpls-te: The root of MPLS TE configuration

     This YANG module augments the
       Cisco-IOS-XR-ifmgr-cfg,
       Cisco-IOS-XR-snmp-agent-cfg
     modules with configuration data.

     Copyright (c) 2013-2015 by Cisco Systems, Inc.
     All rights reserved.";

  revision "2015-11-09" {
    description
      "IOS XR 6.0 revision.";
  }

  typedef Mpls-tesrlg-exclude {
    type enumeration {
      enum mandatory {
        value 1;
        description "SRLG Mandatory Exclude";
      }
      enum preferred {
        value 2;
        description "SRLG Preferred Exclude";
      }
      enum weighted {
        value 3;
        description "SRLG Weighted Exclude";
      }
    }
    description "Mpls tesrlg exclude";
  }
  typedef Mpls-te-affinity-value {
    type enumeration {
      enum hex-value {
        value 1;
        description "Affinity value in Hex number";
      }
      enum bit-position {
        value 2;
        description "Affinity value by Bit-Position";
      }
    }
    description "Mpls te affinity value";
  }
  typedef Destination-list-name-length {
    type xr:Cisco-ios-xr-string {
      length "0..32";
    }
    description "Destination list name length";
  }
  typedef Route-priority-role {
    type enumeration {
      enum route-priority-role-head-back-up {
        value 0;
        description "TE Route Priority Role Head Backup";
      }
      enum route-priority-role-head-primary {
        value 1;
        description "TE Route Priority Role Head Primary";
      }
      enum route-priority-role-middle {
        value 2;
        description "TE Route Priority Role Middle";
      }
    }
    description "Route priority role";
  }
  typedef Otn-signaled-bandwidth-flex-framing {
    type enumeration {
      enum cbr {
        value 20;
        description "CBR";
      }
      enum framed-gfp-fixed {
        value 21;
        description "GFP fixed framing type";
      }
      enum framed-gfp-resize {
        value 22;
        description "GFP resizeable framing type";
      }
    }
    description "Otn signaled bandwidth flex framing";
  }
  typedef Sr-prepend {
    type enumeration {
      enum none-type {
        value 0;
        description "NoneType";
      }
      enum next-label {
        value 1;
        description "Next Label";
      }
      enum bgp-n-hop {
        value 2;
        description "BGP NHOP";
      }
    }
    description "Sr prepend";
  }
  typedef Mpls-te-path-selection-tiebreaker {
    type enumeration {
      enum min-fill {
        value 1;
        description "Prefer the path with the least-utilized links";
      }
      enum max-fill {
        value 2;
        description "Prefer the path with the most-utilized links";
      }
      enum random {
        value 3;
        description "Prefer a path with links utilized randomly";
      }
    }
    description "Mpls te path selection tiebreaker";
  }
  typedef Attribute-set-name-length {
    type xr:Cisco-ios-xr-string {
      length "0..64";
    }
    description "Attribute set name length";
  }
  typedef Mpls-te-otn-aps-protection {
    type enumeration {
      enum 1plus1-unidir-no-aps {
        value 4;
        description "1PLUS1 UNIDIR NO APS";
      }
      enum 1plus1-unidir-aps {
        value 8;
        description "1PLUS1 UNIDIR APS";
      }
      enum 1plus1-bdir-aps {
        value 16;
        description "1PLUS1 BIDIR APS";
      }
    }
    description "Mpls te otn aps protection";
  }
  typedef Ospf-area-mode {
    type enumeration {
      enum ospf-int {
        value 0;
        description "OSPF area in integer format";
      }
      enum ospfip-addr {
        value 1;
        description "OSPF area in IP address format";
      }
    }
    description "Ospf area mode";
  }
  typedef Mpls-te-path-option-property {
    type enumeration {
      enum none {
        value 0;
        description "No property";
      }
      enum lockdown {
        value 1;
        description "Path is not a canditate forreoptimization";
      }
      enum verbatim {
        value 4;
        description
          "Explicit path does not require topology
          database";
      }
      enum pce {
        value 8;
        description "Dynamic path found by PCE server";
      }
      enum segment-routing {
        value 16;
        description "Segment Routing path";
      }
    }
    description "Mpls te path option property";
  }
  typedef Mpls-te-path-computation-method {
    type enumeration {
      enum not-set {
        value 0;
        description "NotSet";
      }
      enum dynamic {
        value 1;
        description "Dynamic";
      }
      enum pce {
        value 2;
        description "PCE";
      }
      enum explicit {
        value 3;
        description "Explicit";
      }
    }
    description "Mpls te path computation method";
  }
  typedef Mpls-te-signaled-label {
    type enumeration {
      enum not-set {
        value 0;
        description "Not Set";
      }
      enum dwdm {
        value 1;
        description "DWDM Label (RFC 6205), 50GHz channel spacing";
      }
    }
    description "Mpls te signaled label";
  }
  typedef Mpls-te-path-option-xro {
    type empty;
    description "Defined as attribute-set";
  }
  typedef Mpls-te-tunnel-affinity {
    type enumeration {
      enum include {
        value 1;
        description "Include Affinity";
      }
      enum include-strict {
        value 2;
        description "Strictly Include Affinity";
      }
      enum exclude {
        value 3;
        description "Exclude Affinity";
      }
      enum exclude-all {
        value 4;
        description "Exclude All Affinities";
      }
      enum ignore {
        value 5;
        description "Ignore Affinity";
      }
    }
    description "Mpls te tunnel affinity";
  }
  typedef Binding-segment-id {
    type enumeration {
      enum any-label {
        value 1;
        description "AnyLabel";
      }
      enum specified-label {
        value 2;
        description "SpecifiedLabel";
      }
    }
    description "Binding segment id";
  }
  typedef Mpls-te-switching-cap {
    type enumeration {
      enum psc1 {
        value 1;
        description "PSC1";
      }
      enum lsc {
        value 150;
        description "LSC";
      }
      enum fsc {
        value 200;
        description "FSC";
      }
    }
    description "Mpls te switching cap";
  }
  typedef Mpls-te-otn-aps-protection-mode {
    type enumeration {
      enum revertive {
        value 1;
        description "Revertive";
      }
      enum non-revertive {
        value 2;
        description "Non Revertive";
      }
    }
    description "Mpls te otn aps protection mode";
  }
  typedef Mpls-te-config-tunnel {
    type enumeration {
      enum p2p {
        value 0;
        description "P2P";
      }
      enum p2mp {
        value 1;
        description "P2MP";
      }
    }
    description "Mpls te config tunnel";
  }
  typedef Mpls-te-bfd-session-down-action {
    type enumeration {
      enum re-setup {
        value 1;
        description "Tear down and resetup";
      }
    }
    description "Mpls te bfd session down action";
  }
  typedef Mpls-te-log-frr-protection {
    type enumeration {
      enum frr-active-primary {
        value 1;
        description "Track only FRR active on primary LSP";
      }
      enum backup {
        value 256;
        description "backup tunnel";
      }
      enum frr-ready-primary {
        value 512;
        description "Track only FRR ready on primary LSP";
      }
      enum primary {
        value 513;
        description "primary LSP";
      }
      enum all {
        value 769;
        description "all";
      }
    }
    description "Mpls te log frr protection";
  }
  typedef Link-next-hop {
    type enumeration {
      enum none {
        value 1;
        description "No next hop";
      }
      enum ipv4-address {
        value 2;
        description "IPv4 next-hop address";
      }
    }
    description "Link next hop";
  }
  typedef Mpls-lcac-bandwidth-hold-timer-range {
    type uint32 {
      range "1..300";
    }
    description "Mpls lcac bandwidth hold timer range";
  }
  typedef Mpls-te-autoroute-metric {
    type enumeration {
      enum relative {
        value 1;
        description "Relative";
      }
      enum absolute {
        value 2;
        description "Absolute";
      }
      enum constant {
        value 3;
        description "Constant";
      }
    }
    description "Mpls te autoroute metric";
  }
  typedef Mpls-te-backup-bandwidth-pool {
    type enumeration {
      enum any-pool {
        value 1;
        description "Any Pool";
      }
      enum global-pool {
        value 2;
        description "Global Pool";
      }
      enum sub-pool {
        value 4;
        description "Sub Pool";
      }
    }
    description "Mpls te backup bandwidth pool";
  }
  typedef Bandwidth-constraint {
    type enumeration {
      enum bandwidth-constraint-maximum-allocation-model {
        value 1;
        description "Maximum Allocation Bandwidth Constaints Model";
      }
    }
    description "Bandwidth constraint";
  }
  typedef Otn-payload {
    type enumeration {
      enum unknown {
        value 0;
        description "Payload unknown";
      }
      enum bmp {
        value 50;
        description "Bmp Payload";
      }
      enum gfp-f {
        value 54;
        description "Gfp_F Payload";
      }
      enum gmp {
        value 55;
        description "GMP Payload";
      }
      enum gfp-f-ext {
        value 70;
        description "Gfp_F_EXT Payload";
      }
    }
    description "Otn payload";
  }
  typedef Mpls-te-otn-snc-mode {
    type enumeration {
      enum snc-n {
        value 1;
        description "SNC N";
      }
      enum snc-i {
        value 2;
        description "SNC I";
      }
      enum snc-s {
        value 3;
        description "SNC S";
      }
    }
    description "Mpls te otn snc mode";
  }
  typedef Mpls-te-path-selection-metric {
    type enumeration {
      enum igp {
        value 1;
        description "IGP Metric";
      }
      enum te {
        value 2;
        description "TE Metric";
      }
      enum delay {
        value 4;
        description "DELAY Metric";
      }
    }
    description "Mpls te path selection metric";
  }
  typedef Mpls-te-switching-encode {
    type enumeration {
      enum none {
        value 0;
        description "None";
      }
      enum packet {
        value 1;
        description "Packet";
      }
      enum ethernet {
        value 2;
        description "Ethernet";
      }
      enum sondet-sdh {
        value 5;
        description "SONET SDH";
      }
    }
    description "Mpls te switching encode";
  }
  typedef Mpls-te-path-option {
    type enumeration {
      enum not-set {
        value 0;
        description "Not Set";
      }
      enum dynamic {
        value 1;
        description "Dynamic";
      }
      enum explicit-name {
        value 3;
        description "Explicit, identified by name";
      }
      enum explicit-number {
        value 4;
        description "Explicit, identified by number";
      }
      enum no-ero {
        value 5;
        description "No ERO";
      }
      enum sr {
        value 6;
        description "Segment routing";
      }
    }
    description "Mpls te path option";
  }
  typedef Mpls-lcac-flooding-igp {
    type enumeration {
      enum ospf {
        value 0;
        description "OSPF";
      }
    }
    description "Mpls lcac flooding igp";
  }
  typedef Otn-protection-switch-lockout {
    type enumeration {
      enum none {
        value 0;
        description "No Lockout";
      }
      enum working {
        value 1;
        description "Lockout Working";
      }
    }
    description "Otn protection switch lockout";
  }
  typedef Mpls-te-tunnel-id {
    type enumeration {
      enum auto {
        value 0;
        description "Auto";
      }
      enum explicit {
        value 1;
        description "Explicit";
      }
    }
    description "Mpls te tunnel id";
  }
  typedef Otn-signaled-bandwidth {
    type enumeration {
      enum odu1 {
        value 1;
        description "Signalled BW for ODU1";
      }
      enum odu2 {
        value 2;
        description "Signalled BW for ODU2";
      }
      enum odu3 {
        value 3;
        description "Signalled BW for ODU3";
      }
      enum odu4 {
        value 4;
        description "Signalled BW for ODU4";
      }
      enum odu0 {
        value 10;
        description "Signalled BW for ODU0";
      }
      enum odu2e {
        value 11;
        description "Signalled BW for ODU2e";
      }
      enum od-uflex-cbr {
        value 20;
        description "Signalled BW for ODUflex CBR";
      }
      enum od-uflex-gfp-resize {
        value 21;
        description "Signalled BW for ODUflex GFP Resizable";
      }
      enum od-uflex-gfp-not-resize {
        value 22;
        description "Signalled BW for ODUflex GFP not Resizable";
      }
      enum odu1e {
        value 23;
        description "Signalled BW for ODU1e";
      }
      enum odu1f {
        value 24;
        description "Signalled BW for ODU1f";
      }
      enum odu2f {
        value 25;
        description "Signalled BW for ODU2f";
      }
      enum odu3e1 {
        value 26;
        description "Signalled BW for ODU3e1";
      }
      enum odu3e2 {
        value 27;
        description "Signalled BW for ODU3e2";
      }
    }
    description "Otn signaled bandwidth";
  }
  typedef Mpls-flooding-threshold-percent-range {
    type uint32 {
      range "0..100";
    }
    description "Mpls flooding threshold percent range";
  }
  typedef Mpls-te-bandwidth-dste {
    type enumeration {
      enum standard-dste {
        value 0;
        description "IETF-Standard DSTE";
      }
      enum pre-standard-dste {
        value 1;
        description "Pre-Standard DSTE";
      }
    }
    description "Mpls te bandwidth dste";
  }
  typedef Mpls-te-path-selection-invalidation-timer-expire {
    type enumeration {
      enum tunnel-action-tear {
        value 1;
        description "Tear down tunnel.";
      }
      enum tunnel-action-drop {
        value 2;
        description "Drop tunnel traffic.";
      }
    }
    description "Mpls te path selection invalidation timer expire";
  }
  typedef Mpls-te-path-diversity-conformance {
    type enumeration {
      enum strict {
        value 0;
        description "Strict";
      }
      enum best-effort {
        value 1;
        description "Best effort";
      }
    }
    description "Mpls te path diversity conformance";
  }
  typedef Mpls-te-backup-bandwidth-class {
    type enumeration {
      enum class0 {
        value 0;
        description "Class 0";
      }
      enum class1 {
        value 1;
        description "Class 1";
      }
      enum any-class {
        value 9;
        description "Any Class";
      }
    }
    description "Mpls te backup bandwidth class";
  }
  typedef Mpls-lcac-flooding-threshold-percent-range {
    type uint32 {
      range "0..100";
    }
    description "Mpls lcac flooding threshold percent range";
  }
  typedef Ietf-mode {
    type enumeration {
      enum standard {
        value 3;
        description "IETF Standard";
      }
    }
    description "Ietf mode";
  }
  typedef Mpls-te-otn-aps-restoration-style {
    type enumeration {
      enum keep-failed-lsp {
        value 1;
        description "Keep Failed Lsp";
      }
      enum delete-failed-lsp {
        value 2;
        description "Delete Failed Lsp";
      }
    }
    description "Mpls te otn aps restoration style";
  }
  typedef Mpls-te-path-selection-segment-routing-adjacency-protection {
    type enumeration {
      enum not-set {
        value 0;
        description "Any segment can be used in a path.";
      }
      enum adj-unprotected {
        value 1;
        description
          "Only unprotected adjacency segments can be used
          in a path.";
      }
      enum adj-protected {
        value 2;
        description
          "Only protected adjacency segments can be used
          in a path.";
      }
    }
    description
      "Mpls te path selection segment routing adjacency
      protection";
  }
  typedef Mpls-te-path-option-protection {
    type enumeration {
      enum active {
        value 0;
        description "Active path";
      }
      enum protecting {
        value 1;
        description "Protecting Path";
      }
    }
    description "Mpls te path option protection";
  }
  typedef Gmplstti-mode {
    type enumeration {
      enum sm {
        value 1;
        description "Section Monitoring";
      }
      enum pm {
        value 2;
        description "Path Monitoring";
      }
      enum tcm {
        value 3;
        description "Tandem Connection";
      }
    }
    description "Gmplstti mode";
  }
  typedef Mpls-te-switching-encoding {
    type enumeration {
      enum packet {
        value 1;
        description "Packet";
      }
      enum ethernet {
        value 2;
        description "Ethernet";
      }
      enum sondet-sdh {
        value 5;
        description "SONET SDH";
      }
    }
    description "Mpls te switching encoding";
  }
  typedef Mpls-te-sig-name-option {
    type enumeration {
      enum none {
        value 0;
        description "None";
      }
      enum address {
        value 1;
        description "Address";
      }
      enum name {
        value 2;
        description "Name";
      }
    }
    description "Mpls te sig name option";
  }
  typedef Mpls-te-policy-class-range {
    type uint32 {
      range "1..8";
    }
    description "Mpls te policy class range";
  }
  typedef Mpls-te-bandwidth-limit {
    type enumeration {
      enum unlimited {
        value 64;
        description "Unlimited";
      }
      enum limited {
        value 128;
        description "Limited";
      }
    }
    description "Mpls te bandwidth limit";
  }
  typedef Mesh-group-id {
    type uint32 {
      range "0..4294967295";
    }
    description "Mesh group id";
  }
  typedef Path-invalidation-action {
    type enumeration {
      enum tear {
        value 1;
        description "Tear";
      }
      enum drop {
        value 2;
        description "Drop";
      }
    }
    description "Path invalidation action";
  }
  typedef Mpls-te-switching-index {
    type union {
      type enumeration {
        enum link {
          value 255;
          description "Link";
        }
      }
      type uint32 {
        range "1..255";
      }
    }
    description "Mpls te switching index";
  }
  typedef Mpls-te-igp-protocol {
    type enumeration {
      enum none {
        value 0;
        description "Not set";
      }
      enum isis {
        value 1;
        description "IS IS";
      }
      enum ospf {
        value 2;
        description "OSPF";
      }
    }
    description "Mpls te igp protocol";
  }

  grouping PCALC-FAILURE-MESSAGE {
    description "Common node of logging, auto-mesh-logging";
    leaf pcalc-failure-message {
      xr:xr-xml-map "mpls_te_tunnel_cfg:PCALCFailureMessage";
      type empty;
      description "Enable logging for path-calculation failures";
    }
  }

  grouping POLICY-CLASSES {
    description
      "Common node of tunnel-te-attributes,
      auto-mesh-attribute, auto-backup-attribute";

    container policy-classes {
      xr:xr-xml-map "mpls_te_tunnel_cfg:PolicyClasses";
      description "Policy classes for PBTS";
      leaf-list policy-class {
        xr:xr-xml-map "mpls_te_tunnel_cfg:TunnelClass";
        type Mpls-te-policy-class-range;
        max-elements "7";
        description "Array of Policy class";
      }
    }
  }

  grouping AFFINITY-MASK {
    description
      "Common node of tunnel-te-attributes,
      auto-mesh-attribute, auto-backup-attribute,
      path-option-attribute, p2mpte-attribute,
      p2p-te-attribute";

    container affinity-mask {
      xr:xr-xml-map "mpls_te_tunnel_cfg:AffinityMask";
      presence "Indicates a affinity-mask node is configured.";
      description "Set the affinity flags and mask";
      leaf affinity {
        xr:xr-xml-map "mpls_te_tunnel_cfg:Affinity";
        type xr:Hex-integer;
        mandatory true;
        description "Affinity flags";
      }
      leaf mask {
        xr:xr-xml-map "mpls_te_tunnel_cfg:Mask";
        type xr:Hex-integer;
        mandatory true;
        description "Affinity mask";
      }
    }
  }

  grouping BANDWIDTH-CHANGE-MESSAGE {
    description
      "Common node of logging, auto-backup-logging,
      auto-mesh-logging";
    leaf bandwidth-change-message {
      xr:xr-xml-map "mpls_te_tunnel_cfg:BandwidthChangeMessage";
      type empty;
      description "Log tunnel messages for bandwidth change";
    }
  }

  grouping REOPTIMIZE-ATTEMPTS-MESSAGE {
    description
      "Common node of logging, auto-backup-logging,
      auto-mesh-logging";
    leaf reoptimize-attempts-message {
      xr:xr-xml-map "mpls_te_tunnel_cfg:ReoptimizeAttemptsMessage";
      type empty;
      description "Log tunnel reoptimization attempts messages";
    }
  }

  grouping TIMERS {
    description "Common node of backup, mesh";

    container timers {
      xr:xr-xml-map "mpls_te_autobackup_cfg:Timers";
      description "Configure auto-tunnel backup timers value";

      container removal {
        xr:xr-xml-map "mpls_te_autobackup_cfg:Removal";
        description
          "Configure auto-tunnel backup removal timers
          value";
        leaf unused {
          xr:xr-xml-map "mpls_te_autobackup_cfg:Unused";
          xr:xr-cli-map "traffic-eng backup timers removal unused <"+
            "number> ";
          xr:xr-cli-map "traffic-eng mesh timers removal unused <nu"+
            "mber> ";
          type uint32 {
            range "0..10080";
          }
          units "minute";
          default "3600";
          description
            "Auto-tunnel backup unused timeout in minutes
            (0=never timeout)";
        }
      }
    }
  }

  grouping TUNNEL-PATH-SELECTION {
    description
      "Common node of tunnel-te-attributes,
      tunnel-attributes";

    container tunnel-path-selection {
      xr:xr-xml-map "mpls_te_tunnel_cfg:TunnelPathSelection";
      description "Configure path selection properties";
      leaf tiebreaker {
        xr:xr-xml-map "mpls_te_tunnel_cfg:Tiebreaker";
        type Mpls-te-path-selection-tiebreaker;
        description "CSPF tiebreaker to use in path calculation";
      }
      leaf path-selection-hop-limit {
        xr:xr-xml-map "mpls_te_tunnel_cfg:PathSelectionHopLimit";
        type uint32 {
          range "1..255";
        }
        description
          "Path selection hop limit configuration for this
          specific tunnel";
      }
      uses INVALIDATION;
      uses PATH-SELECTION-COST-LIMIT;
    }
  }

  grouping INVALIDATION {
    description
      "Common node of tunnel-path-selection,
      att-path-option-path-selection";

    container invalidation {
      xr:xr-xml-map "mpls_te_tunnel_cfg:Invalidation";
      presence "enable invalidation";
      description
        "Path invalidation configuration for this
        specific tunnel";
      leaf path-invalidation-timeout {
        xr:xr-xml-map "mpls_te_tunnel_cfg:PathInvalidationTimeout";
        type uint32 {
          range "0..60000";
        }
        description "Path Invalidation Timeout";
      }
      leaf path-invalidation-action {
        xr:xr-xml-map "mpls_te_tunnel_cfg:PathInvalidationAction";
        type Path-invalidation-action;
        description "Path Invalidation Action";
      }
    }
  }

  grouping PRECEDENCE {
    description "Common node of peer, pce-attributes";
    leaf precedence {
      xr:xr-xml-map "mpls_te_cfg:Precedence";
      xr:xr-cli-map "precedence <number> ";
      type uint32 {
        range "0..255";
      }
      description "Precedence order";
    }
  }

  grouping SOFT-PREEMPTION {
    description
      "Common node of tunnel-attributes,
      tunnel-te-attributes, auto-mesh-attribute";
    leaf soft-preemption {
      xr:xr-xml-map "mpls_te_tunnel_cfg:SoftPreemption";
      xr:xr-cli-map "traffic-eng named-tunnels tunnel-te <string> s"+
        "oft-preemption ";
      type empty;
      description
        "Enable the soft-preemption feature on the tunnel";
    }
  }

  grouping PATH-SELECTION-COST-LIMIT {
    description
      "Common node of tunnel-path-selection,
      att-path-option-path-selection";
    leaf path-selection-cost-limit {
      xr:xr-xml-map "mpls_te_tunnel_cfg:PathSelectionCostLimit";
      type uint32 {
        range "1..4294967295";
      }
      description
        "Path selection cost limit configuration for this
        specific tunnel";
    }
  }

  grouping AUTO-BANDWIDTH {
    description
      "Common node of tunnel-attributes,
      tunnel-te-attributes";

    container auto-bandwidth {
      xr:xr-xml-map "mpls_te_tunnel_cfg:AutoBandwidth";
      description
        "Tunnel Interface Auto-bandwidth configuration
        data";

      container underflow {
        xr:xr-xml-map "mpls_te_tunnel_cfg:Underflow";
        presence "Indicates a underflow node is configured.";
        description "Configuring the tunnel underflow detection";
        leaf underflow-threshold-percent {
          xr:xr-xml-map "mpls_te_tunnel_cfg:UnderflowThresholdPerce"+
            "nt";
          type uint32 {
            range "1..100";
          }
          units "percentage";
          mandatory true;
          description
            "Bandwidth change percent to trigger an
            underflow";
        }
        leaf underflow-threshold-value {
          xr:xr-xml-map "mpls_te_tunnel_cfg:UnderflowThresholdValue";
          type uint32 {
            range "10..4294967295";
          }
          units "kbit/s";
          mandatory true;
          description
            "Bandwidth change value to trigger an underflow
            (kbps)";
        }
        leaf underflow-threshold-limit {
          xr:xr-xml-map "mpls_te_tunnel_cfg:UnderflowThresholdLimit";
          type uint32 {
            range "1..10";
          }
          mandatory true;
          description
            "Number of consecutive collections exceeding
            threshold";
        }
      }

      container overflow {
        xr:xr-xml-map "mpls_te_tunnel_cfg:Overflow";
        presence "Indicates a overflow node is configured.";
        description "Configuring the tunnel overflow detection";
        leaf overflow-threshold-percent {
          xr:xr-xml-map "mpls_te_tunnel_cfg:OverflowThresholdPercen"+
            "t";
          type uint32 {
            range "1..100";
          }
          units "percentage";
          mandatory true;
          description
            "Bandwidth change percent to trigger an
            overflow";
        }
        leaf overflow-threshold-value {
          xr:xr-xml-map "mpls_te_tunnel_cfg:OverflowThresholdValue";
          type uint32 {
            range "10..4294967295";
          }
          units "kbit/s";
          mandatory true;
          description
            "Bandwidth change value to trigger an overflow
            (kbps)";
        }
        leaf overflow-threshold-limit {
          xr:xr-xml-map "mpls_te_tunnel_cfg:OverflowThresholdLimit";
          type uint32 {
            range "1..10";
          }
          mandatory true;
          description
            "Number of consecutive collections exceeding
            threshold";
        }
      }

      container bandwidth-limits {
        xr:xr-xml-map "mpls_te_tunnel_cfg:BandwidthLimits";
        presence "Indicates a bandwidth-limits node is configured.";
        description
          "Set min/max bandwidth auto-bw can apply on a
          tunnel";
        leaf bandwidth-min-limit {
          xr:xr-xml-map "mpls_te_tunnel_cfg:BandwidthMinLimit";
          type uint32 {
            range "0..4294967295";
          }
          mandatory true;
          description
            "Set minimum bandwidth auto-bw can apply on a
            tunnel";
        }
        leaf bandwidth-max-limit {
          xr:xr-xml-map "mpls_te_tunnel_cfg:BandwidthMaxLimit";
          type uint32 {
            range "0..4294967295";
          }
          mandatory true;
          description
            "Set maximum bandwidth auto-bw can apply on a
            tunnel";
        }
      }

      container adjustment-threshold {
        xr:xr-xml-map "mpls_te_tunnel_cfg:AdjustmentThreshold";
        presence "Indicates a adjustment-threshold node is"+
          " configured.";
        description
          "Set the bandwidth change threshold to trigger
          adjustment";
        leaf adjustment-threshold-percent {
          xr:xr-xml-map "mpls_te_tunnel_cfg:AdjustmentThresholdPerc"+
            "ent";
          type uint32 {
            range "1..100";
          }
          units "percentage";
          mandatory true;
          description
            "Bandwidth change percent to trigger adjustment";
        }
        leaf adjustment-threshold-value {
          xr:xr-xml-map "mpls_te_tunnel_cfg:AdjustmentThresholdValu"+
            "e";
          type uint32 {
            range "10..4294967295";
          }
          units "kbit/s";
          mandatory true;
          description
            "Bandwidth change value to trigger adjustment
            (kbps)";
        }
      }
      leaf underflow-enable {
        xr:xr-xml-map "mpls_te_tunnel_cfg:UnderflowEnable";
        type boolean;
        description "Enable auto bandwidth underflow detection";
      }
      leaf enabled {
        xr:xr-xml-map "mpls_te_tunnel_cfg:Enabled";
        type boolean;
        description
          "This object is only valid for tunnel interfaces
          and it controls whether that interface has
          auto-bw enabled on it or not.The object must be
          set before any other auto-bw configuration is
          supplied for the interface, and must be the
          last auto-bw configuration object to be removed
          .";
      }
      leaf application-frequency {
        xr:xr-xml-map "mpls_te_tunnel_cfg:ApplicationFrequency";
        xr:xr-cli-map "application <number> ";
        type uint32 {
          range "5..10080";
        }
        units "minute";
        description
          "Set the tunnel auto-bw application frequency in
          minutes";
      }
      leaf overflow-enable {
        xr:xr-xml-map "mpls_te_tunnel_cfg:OverflowEnable";
        type boolean;
        description "Enable auto bandwidth overflow detection";
      }
      uses COLLECTION-ONLY;
    }
  }

  grouping RECORD-ROUTE {
    description
      "Common node of tunnel-attributes,
      tunnel-te-attributes, auto-mesh-attribute,
      auto-backup-attribute, gmpls-unitunnel-head,
      p2mpte-attribute, tunnel-head";
    leaf record-route {
      xr:xr-xml-map "mpls_te_tunnel_cfg:RecordRoute";
      xr:xr-cli-map "traffic-eng named-tunnels tunnel-te <string> r"+
        "ecord-route ";
      xr:xr-cli-map "traffic-eng gmpls optical-uni controller tunne"+
        "l-properties record-route ";
      xr:xr-cli-map "traffic-eng gmpls optical-nni controller Odu-G"+
        "roup-Te <number> record-route ";
      type empty;
      description "Record the route used by the tunnel";
    }
  }

  grouping LOGGING {
    description
      "Common node of mte-tunnel-attributes,
      p2mpte-attribute";

    container logging {
      xr:xr-xml-map "mpls_mte_tunnel_cfg:Logging";
      description "Log tunnel LSP messages";
      leaf insufficient-bw-message {
        xr:xr-xml-map "mpls_mte_tunnel_cfg:InsufficientBWMessage";
        type empty;
        description
          "Log tunnel messages for insufficient bandwidth";
      }
      leaf reoptimized-message {
        xr:xr-xml-map "mpls_mte_tunnel_cfg:ReoptimizedMessage";
        type empty;
        description "Log tunnel reoptimized messages";
      }
      leaf bandwidth-change-message {
        xr:xr-xml-map "mpls_mte_tunnel_cfg:BandwidthChangeMessage";
        type empty;
        description "Log tunnel bandwidth change messages";
      }
      leaf all {
        xr:xr-xml-map "mpls_mte_tunnel_cfg:All";
        type empty;
        description "Log all events for a tunnel";
      }
      leaf pcalc-failure-message {
        xr:xr-xml-map "mpls_mte_tunnel_cfg:PCALCFailureMessage";
        type empty;
        description "Enable logging for path-calculation failures";
      }
      leaf state-message {
        xr:xr-xml-map "mpls_mte_tunnel_cfg:StateMessage";
        type empty;
        description "Log tunnel state messages";
      }
      leaf reoptimize-attempts-message {
        xr:xr-xml-map "mpls_mte_tunnel_cfg:ReoptimizeAttemptsMessag"+
          "e";
        type empty;
        description "Log tunnel reoptimization attempts messages";
      }
      leaf sub-lsp-state-message {
        xr:xr-xml-map "mpls_mte_tunnel_cfg:SubLSPStateMessage";
        type empty;
        description "Log all tunnel sub-LSP state messages";
      }
      leaf reroute-messsage {
        xr:xr-xml-map "mpls_mte_tunnel_cfg:RerouteMesssage";
        type empty;
        description "Log tunnel rereoute messages";
      }
    }
  }

  grouping COLLECTION-ONLY {
    description
      "Common node of auto-bandwidth,
      auto-mesh-attribute";
    leaf collection-only {
      xr:xr-xml-map "mpls_te_tunnel_cfg:CollectionOnly";
      xr:xr-cli-map "collect-bw-only ";
      type empty;
      description
        "Enable bandwidth collection only, no auto-bw
        adjustment";
    }
  }

  grouping DESTINATION {
    description
      "Common node of tunnel-te-attributes,
      tunnel-attributes";
    leaf destination {
      xr:xr-xml-map "mpls_te_tunnel_cfg:Destination";
      xr:xr-cli-map "traffic-eng named-tunnels tunnel-te <string> d"+
        "estination <IPv4 address> ";
      type inet:ipv4-address-no-zone;
      description "Set the destination of the tunnel";
    }
  }

  grouping STATE-MESSAGE {
    description
      "Common node of logging, logging,
      auto-backup-logging, auto-mesh-logging";
    leaf state-message {
      xr:xr-xml-map "mpls_te_tunnel_cfg:StateMessage";
      type empty;
      description "Log tunnel state messages";
    }
  }

  grouping LOAD-SHARE {
    description
      "Common node of tunnel-te-attributes,
      auto-mesh-attribute";
    leaf load-share {
      xr:xr-xml-map "mpls_te_tunnel_cfg:LoadShare";
      type uint32 {
        range "1..4294967295";
      }
      description "Tunnel loadsharing metric";
    }
  }

  grouping PATH-SELECTION {
    description
      "Common node of auto-mesh-attribute, xro-attribute
      , auto-backup-attribute, p2mpte-attribute,
      otn-pp-attribute";

    container path-selection {
      xr:xr-xml-map "mpls_te_attr_set_cfg:PathSelection";
      description "Configure path selection properties";
      leaf enable {
        xr:xr-xml-map "mpls_te_attr_set_cfg:Enable";
        type empty;
        description "Enable path selection";
      }
    }
  }

  grouping SIGNALLED-NAME {
    description
      "Common node of tunnel-te-attributes,
      gmpls-unitunnel-head, tunnel-head";
    leaf signalled-name {
      xr:xr-xml-map "mpls_te_tunnel_cfg:SignalledName";
      xr:xr-cli-map "traffic-eng gmpls optical-uni controller tunne"+
        "l-properties signalled-name <string> ";
      xr:xr-cli-map "traffic-eng gmpls optical-nni controller Odu-G"+
        "roup-Te <number> signalled-name <string> ";
      type xr:Cisco-ios-xr-string {
        length "0..254";
      }
      description
        "The name of the tunnel to be included in
        signalling messages";
    }
  }

  grouping REOPTIMIZED-MESSAGE {
    description
      "Common node of logging, auto-backup-logging,
      auto-mesh-logging";
    leaf reoptimized-message {
      xr:xr-xml-map "mpls_te_tunnel_cfg:ReoptimizedMessage";
      type empty;
      description "Log tunnel reoptimized messages";
    }
  }

  grouping NEW-STYLE-AFFINITY-TABLE {
    description
      "Common node of tunnel-attributes,
      tunnel-te-attributes, path-option-attribute,
      auto-backup-attribute, auto-mesh-attribute,
      p2mpte-attribute, p2p-te-attribute";

    container new-style-affinity-affinity-types {
      xr:xr-xml-map "mpls_te_tunnel_cfg:NewStyleAffinityTable";
      description "Tunnel new style affinity attributes table";

      list new-style-affinity-affinity-type {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type";
        description "Tunnel new style affinity attribute";
        leaf affinity-type {
          xr:xr-xml-map "mpls_te_tunnel_cfg:AffinityType";
          type Mpls-te-tunnel-affinity;
          description "The type of the affinity entry";
        }
      }

      list new-style-affinity-affinity-type-affinity1 {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
      }

      list new-style-affinity-affinity-type-affinity1-affinity2 {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
      }

      list "new-style-affinity-affinity-type-affinity1-affinity2"+
        "-affinity3" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
      }

      list "new-style-affinity-affinity-type-affinity1-affinity2"+
        "-affinity3-affinity4" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3 affinity4";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
        leaf affinity4 {
          xr:xr-xml-map "mpls_te_tunnel_cfg:Affinity4";
          type xr:Cisco-ios-xr-string;
          description "The name of the fourth affinity";
        }
      }

      list "new-style-affinity-affinity-type-affinity1-affinity2"+
        "-affinity3-affinity4-affinity5" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3 affinity4"+
          " affinity5";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
        leaf affinity4 {
          xr:xr-xml-map "mpls_te_tunnel_cfg:Affinity4";
          type xr:Cisco-ios-xr-string;
          description "The name of the fourth affinity";
        }
        leaf affinity5 {
          xr:xr-xml-map "mpls_te_tunnel_cfg:Affinity5";
          type xr:Cisco-ios-xr-string;
          description "The name of the fifth affinity";
        }
      }

      list "new-style-affinity-affinity-type-affinity1-affinity2"+
        "-affinity3-affinity4-affinity5-affinity6" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3 affinity4"+
          " affinity5 affinity6";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
        leaf affinity4 {
          xr:xr-xml-map "mpls_te_tunnel_cfg:Affinity4";
          type xr:Cisco-ios-xr-string;
          description "The name of the fourth affinity";
        }
        leaf affinity5 {
          xr:xr-xml-map "mpls_te_tunnel_cfg:Affinity5";
          type xr:Cisco-ios-xr-string;
          description "The name of the fifth affinity";
        }
        leaf affinity6 {
          xr:xr-xml-map "mpls_te_tunnel_cfg:Affinity6";
          type xr:Cisco-ios-xr-string;
          description "The name of the sixth affinity";
        }
      }

      list "new-style-affinity-affinity-type-affinity1-affinity2"+
        "-affinity3-affinity4-affinity5-affinity6-affinity7" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3 affinity4"+
          " affinity5 affinity6 affinity7";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
        leaf affinity4 {
          xr:xr-xml-map "mpls_te_tunnel_cfg:Affinity4";
          type xr:Cisco-ios-xr-string;
          description "The name of the fourth affinity";
        }
        leaf affinity5 {
          xr:xr-xml-map "mpls_te_tunnel_cfg:Affinity5";
          type xr:Cisco-ios-xr-string;
          description "The name of the fifth affinity";
        }
        leaf affinity6 {
          xr:xr-xml-map "mpls_te_tunnel_cfg:Affinity6";
          type xr:Cisco-ios-xr-string;
          description "The name of the sixth affinity";
        }
        leaf affinity7 {
          xr:xr-xml-map "mpls_te_tunnel_cfg:Affinity7";
          type xr:Cisco-ios-xr-string;
          description "The name of the seventh affinity";
        }
      }

      list "new-style-affinity-affinity-type-affinity1-affinity2"+
        "-affinity3-affinity4-affinity5-affinity6-affinity7"+
        "-affinity8" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3 affinity4"+
          " affinity5 affinity6 affinity7 affinity8";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
        leaf affinity4 {
          xr:xr-xml-map "mpls_te_tunnel_cfg:Affinity4";
          type xr:Cisco-ios-xr-string;
          description "The name of the fourth affinity";
        }
        leaf affinity5 {
          xr:xr-xml-map "mpls_te_tunnel_cfg:Affinity5";
          type xr:Cisco-ios-xr-string;
          description "The name of the fifth affinity";
        }
        leaf affinity6 {
          xr:xr-xml-map "mpls_te_tunnel_cfg:Affinity6";
          type xr:Cisco-ios-xr-string;
          description "The name of the sixth affinity";
        }
        leaf affinity7 {
          xr:xr-xml-map "mpls_te_tunnel_cfg:Affinity7";
          type xr:Cisco-ios-xr-string;
          description "The name of the seventh affinity";
        }
        leaf affinity8 {
          xr:xr-xml-map "mpls_te_tunnel_cfg:Affinity8";
          type xr:Cisco-ios-xr-string;
          description "The name of the eighth affinity";
        }
      }

      list "new-style-affinity-affinity-type-affinity1-affinity2"+
        "-affinity3-affinity4-affinity5-affinity6-affinity7"+
        "-affinity8-affinity9" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3 affinity4"+
          " affinity5 affinity6 affinity7 affinity8 affinity9";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
        leaf affinity4 {
          xr:xr-xml-map "mpls_te_tunnel_cfg:Affinity4";
          type xr:Cisco-ios-xr-string;
          description "The name of the fourth affinity";
        }
        leaf affinity5 {
          xr:xr-xml-map "mpls_te_tunnel_cfg:Affinity5";
          type xr:Cisco-ios-xr-string;
          description "The name of the fifth affinity";
        }
        leaf affinity6 {
          xr:xr-xml-map "mpls_te_tunnel_cfg:Affinity6";
          type xr:Cisco-ios-xr-string;
          description "The name of the sixth affinity";
        }
        leaf affinity7 {
          xr:xr-xml-map "mpls_te_tunnel_cfg:Affinity7";
          type xr:Cisco-ios-xr-string;
          description "The name of the seventh affinity";
        }
        leaf affinity8 {
          xr:xr-xml-map "mpls_te_tunnel_cfg:Affinity8";
          type xr:Cisco-ios-xr-string;
          description "The name of the eighth affinity";
        }
        leaf affinity9 {
          xr:xr-xml-map "mpls_te_tunnel_cfg:Affinity9";
          type xr:Cisco-ios-xr-string;
          description "The name of the nineth affinity";
        }
      }

      list "new-style-affinity-affinity-type-affinity1-affinity2"+
        "-affinity3-affinity4-affinity5-affinity6-affinity7"+
        "-affinity8-affinity9-affinity10" {
        xr:xr-cli-map "traffic-eng named-tunnels tunnel-te <string>"+
          " affinity ([include] <string>{10})|(include-strict)|(exc"+
          "lude)|(ignore)|(exclude-all)|(traffic-eng named-tunnels "+
          "tunnel-te <string> <number> mask <number>) ";
        key "affinity-type affinity1 affinity2 affinity3 affinity4"+
          " affinity5 affinity6 affinity7 affinity8 affinity9"+
          " affinity10";
        description "Tunnel new style affinity attribute";
        leaf affinity-type {
          xr:xr-xml-map "mpls_te_tunnel_cfg:AffinityType";
          type Mpls-te-tunnel-affinity;
          description "The type of the affinity entry";
        }
        leaf affinity1 {
          xr:xr-xml-map "mpls_te_tunnel_cfg:Affinity1";
          type xr:Cisco-ios-xr-string;
          description "The name of the first affinity";
        }
        leaf affinity2 {
          xr:xr-xml-map "mpls_te_tunnel_cfg:Affinity2";
          type xr:Cisco-ios-xr-string;
          description "The name of the second affinity";
        }
        leaf affinity3 {
          xr:xr-xml-map "mpls_te_tunnel_cfg:Affinity3";
          type xr:Cisco-ios-xr-string;
          description "The name of the third affinity";
        }
        leaf affinity4 {
          xr:xr-xml-map "mpls_te_tunnel_cfg:Affinity4";
          type xr:Cisco-ios-xr-string;
          description "The name of the fourth affinity";
        }
        leaf affinity5 {
          xr:xr-xml-map "mpls_te_tunnel_cfg:Affinity5";
          type xr:Cisco-ios-xr-string;
          description "The name of the fifth affinity";
        }
        leaf affinity6 {
          xr:xr-xml-map "mpls_te_tunnel_cfg:Affinity6";
          type xr:Cisco-ios-xr-string;
          description "The name of the sixth affinity";
        }
        leaf affinity7 {
          xr:xr-xml-map "mpls_te_tunnel_cfg:Affinity7";
          type xr:Cisco-ios-xr-string;
          description "The name of the seventh affinity";
        }
        leaf affinity8 {
          xr:xr-xml-map "mpls_te_tunnel_cfg:Affinity8";
          type xr:Cisco-ios-xr-string;
          description "The name of the eighth affinity";
        }
        leaf affinity9 {
          xr:xr-xml-map "mpls_te_tunnel_cfg:Affinity9";
          type xr:Cisco-ios-xr-string;
          description "The name of the nineth affinity";
        }
        leaf affinity10 {
          xr:xr-xml-map "mpls_te_tunnel_cfg:Affinity10";
          type xr:Cisco-ios-xr-string;
          description "The name of the tenth affinity";
        }
      }
    }
  }

  grouping FAST-REROUTE {
    description
      "Common node of tunnel-attributes,
      tunnel-te-attributes, auto-mesh-attribute,
      p2mpte-attribute";

    container fast-reroute {
      xr:xr-xml-map "mpls_te_tunnel_cfg:FastReroute";
      presence "Indicates a fast-reroute node is configured.";
      description "Specify MPLS tunnel can be fast-rerouted";
      leaf bandwidth-protection {
        xr:xr-xml-map "mpls_te_tunnel_cfg:BandwidthProtection";
        type uint32 {
          range "0..1";
        }
        mandatory true;
        description "Bandwidth Protection";
      }
      leaf node-protection {
        xr:xr-xml-map "mpls_te_tunnel_cfg:NodeProtection";
        type uint32 {
          range "0..1";
        }
        mandatory true;
        description "Node Protection";
      }
    }
  }

  grouping TUNNEL-RANGE {
    description
      "Common node of backup, mesh, p2mp-auto-tunnel,
      p2p-auto-tunnel, pcc";

    container tunnel-range {
      xr:xr-xml-map "mpls_te_autobackup_cfg:TunnelRange";
      description
        "Configure tunnel ID range for auto-tunnel
        features";
      leaf min-tunnel-id {
        xr:xr-xml-map "mpls_te_autobackup_cfg:MinTunnelID";
        type uint32 {
          range "0..65535";
        }
        description "Minimum tunnel ID for auto-tunnels";
      }
      leaf max-tunnel-id {
        xr:xr-xml-map "mpls_te_autobackup_cfg:MaxTunnelID";
        type uint32 {
          range "0..65535";
        }
        description "Maximum tunnel ID for auto-tunnels";
      }
    }
  }

  grouping ADMIN-WEIGHT {
    description "Common node of value, name";
    leaf admin-weight {
      xr:xr-xml-map "mpls_te_cfg:AdminWeight";
      xr:xr-cli-map "traffic-eng srlg name <string> admin-weight <n"+
        "umber> ";
      xr:xr-cli-map "traffic-eng srlg value <number> admin-weight <"+
        "number> ";
      type int32;
      description "Administrative weight for the SRLG value";
    }
  }

  grouping ENABLE {
    description
      "Common node of path-selection,
      att-path-option-path-selection";
    leaf enable {
      xr:xr-xml-map "mpls_te_tunnel_cfg:Enable";
      type empty;
      description "Enter path selection configuration";
    }
  }

  grouping MPLS-TE-ATTR-SET-CFG-ENABLE {
    description
      "Common node of path-option-attribute,
      auto-mesh-attribute, xro-attribute,
      auto-backup-attribute, p2mpte-attribute,
      otn-pp-attribute, p2p-te-attribute";
    leaf enable {
      xr:xr-xml-map "mpls_te_attr_set_cfg:Enable";
      type empty;
      description
        "Attribute-set enable object that controls
        whether this attribute-set is configured or not
        .This object must be set before other
        configuration supplied for this attribute-set";
    }
  }

  grouping AUTOROUTE {
    description
      "Common node of tunnel-attributes,
      tunnel-te-attributes";

    container autoroute {
      xr:xr-xml-map "mpls_te_tunnel_cfg:Autoroute";
      description "Parameters for IGP routing over tunnel";

      container metric {
        xr:xr-xml-map "mpls_te_tunnel_cfg:Metric";
        description "Specify MPLS tunnel metric";
        leaf metric-type {
          xr:xr-xml-map "mpls_te_tunnel_cfg:MetricType";
          type Mpls-te-autoroute-metric;
          description "Autoroute tunnel metric type";
        }
        leaf absolute-metric {
          xr:xr-xml-map "mpls_te_tunnel_cfg:AbsoluteMetric";
          when "../metric-type = 'absolute'" {
            description "../MetricType = Absolute";
          }
          type uint32 {
            range "1..2147483647";
          }
          description "The absolute metric value";
        }
        leaf relative-metric {
          xr:xr-xml-map "mpls_te_tunnel_cfg:RelativeMetric";
          when "../metric-type = 'relative'" {
            description "../MetricType = Relative";
          }
          type int32 {
            range "-10..10";
          }
          description "The value of the adjustment";
        }
        leaf constant-metric {
          xr:xr-xml-map "mpls_te_tunnel_cfg:ConstantMetric";
          when "../metric-type = 'constant'" {
            description "../MetricType = Constant";
          }
          type uint32 {
            range "1..2147483647";
          }
          description "The constant metric value";
        }
      }

      container autoroute-announce {
        xr:xr-xml-map "mpls_te_tunnel_cfg:AutorouteAnnounce";
        description "Announce tunnel to IGP";

        container metric {
          xr:xr-xml-map "mpls_te_tunnel_cfg:Metric";
          description "Specify MPLS tunnel metric";
          leaf metric-type {
            xr:xr-xml-map "mpls_te_tunnel_cfg:MetricType";
            type Mpls-te-autoroute-metric;
            description "Autoroute tunnel metric type";
          }
          leaf absolute-metric {
            xr:xr-xml-map "mpls_te_tunnel_cfg:AbsoluteMetric";
            when "../metric-type = 'absolute'" {
              description "../MetricType = Absolute";
            }
            type uint32 {
              range "1..2147483647";
            }
            description "The absolute metric value";
          }
          leaf relative-metric {
            xr:xr-xml-map "mpls_te_tunnel_cfg:RelativeMetric";
            when "../metric-type = 'relative'" {
              description "../MetricType = Relative";
            }
            type int32 {
              range "-10..10";
            }
            description "The value of the adjustment";
          }
          leaf constant-metric {
            xr:xr-xml-map "mpls_te_tunnel_cfg:ConstantMetric";
            when "../metric-type = 'constant'" {
              description "../MetricType = Constant";
            }
            type uint32 {
              range "1..2147483647";
            }
            description "The constant metric value";
          }
        }
        leaf enable {
          xr:xr-xml-map "mpls_te_tunnel_cfg:Enable";
          type empty;
          description "Enable autoroute announce";
        }
        leaf include-ipv6 {
          xr:xr-xml-map "mpls_te_tunnel_cfg:IncludeIPv6";
          type empty;
          description
            "Specify that the tunnel should be an IPv6
            autoroute announce also";
        }
      }

      container destination-xr {
        xr:xr-xml-map "mpls_te_tunnel_cfg:DestinationTable";
        description "Tunnel Autoroute Destination(s)";

        list destination {
          xr:xr-xml-map "mpls_te_tunnel_cfg:Destination";
          xr:xr-cli-map "traffic-eng named-tunnels tunnel-te <strin"+
            "g> autoroute destination <IPv4 address> ";
          key "destination-address";
          description "Destination address to add in RIB";
          leaf destination-address {
            xr:xr-xml-map "mpls_te_tunnel_cfg:DestinationAddress";
            type inet:ipv4-address-no-zone;
            description "IP address of destination";
          }
        }
      }
      leaf destination {
        xr:xr-xml-map "mpls_te_tunnel_cfg:Destination";
        type empty;
        description "Deprecated: do NOT use";
      }
    }
  }

  grouping REROUTE-MESSSAGE {
    description "Common node of logging, auto-mesh-logging";
    leaf reroute-messsage {
      xr:xr-xml-map "mpls_te_tunnel_cfg:RerouteMesssage";
      type empty;
      description "Log tunnel rereoute messages";
    }
  }

  grouping CACHE-TIMER {
    description
      "Common node of mpls-te-mib, mpls-frr-mib,
      mpls-p2mp-mib, mpls-te-ext-mib,
      mpls-te-ext-std-mib";
    leaf cache-timer {
      xr:xr-xml-map "mpls_temib_cfg:CacheTimer";
      type uint32 {
        range "0..600";
      }
      units "second";
      default "60";
      description "Configure the cache time for the mib.";
    }
  }

  grouping PATH-SELECTION-METRIC {
    description
      "Common node of tunnel-attributes,
      tunnel-te-attributes";
    leaf path-selection-metric {
      xr:xr-xml-map "mpls_te_tunnel_cfg:PathSelectionMetric";
      type Mpls-te-path-selection-metric;
      description
        "Path selection metric to use in path calculation";
    }
  }

  grouping PASSWORD {
    description "Common node of peer, pce-attributes";
    leaf password {
      xr:xr-xml-map "mpls_te_cfg:Password";
      xr:xr-cli-map "password (clear <text>)|(encrypted <text>) ";
      xr:xr-cli-map "traffic-eng pce password (clear <text>)|(encry"+
        "pted <text>) ";
      type xr:Proprietary-password;
      description "MD5 password";
    }
  }

  grouping BANDWIDTH {
    description
      "Common node of tunnel-attributes,
      tunnel-te-attributes, auto-mesh-attribute,
      path-option-attribute, p2mpte-attribute";

    container bandwidth {
      xr:xr-xml-map "mpls_te_tunnel_cfg:Bandwidth";
      presence "Indicates a bandwidth node is configured.";
      description "Tunnel bandwidth requirement";
      leaf dste-type {
        xr:xr-xml-map "mpls_te_tunnel_cfg:DSTEType";
        type Mpls-te-bandwidth-dste;
        mandatory true;
        description "DSTE-standard flag";
      }
      leaf class-or-pool-type {
        xr:xr-xml-map "mpls_te_tunnel_cfg:ClassOrPoolType";
        type uint32 {
          range "0..1";
        }
        mandatory true;
        description "Class type for the bandwith allocation";
      }
      leaf bandwidth {
        xr:xr-xml-map "mpls_te_tunnel_cfg:Bandwidth";
        type uint32 {
          range "0..4294967295";
        }
        units "kbit/s";
        mandatory true;
        description
          "The value of the bandwidth reserved by this
          tunnel in kbps";
      }
    }
  }

  grouping INTERFACE-BANDWIDTH {
    description
      "Common node of auto-mesh-attribute,
      p2mpte-attribute";
    leaf interface-bandwidth {
      xr:xr-xml-map "mpls_te_attr_set_cfg:InterfaceBandwidth";
      type uint32 {
        range "0..4294967295";
      }
      units "kbit/s";
      description "The bandwidth of the interface in kbps";
    }
  }

  grouping FORWARD-CLASS {
    description
      "Common node of tunnel-attributes,
      tunnel-te-attributes, auto-mesh-attribute";
    leaf forward-class {
      xr:xr-xml-map "mpls_te_tunnel_cfg:ForwardClass";
      xr:xr-cli-map "traffic-eng named-tunnels tunnel-te <string> f"+
        "orward-class <number> ";
      type uint32 {
        range "1..7";
      }
      description "Forward class value";
    }
  }

  grouping INSUFFICIENT-BW-MESSAGE {
    description "Common node of logging, auto-mesh-logging";
    leaf insufficient-bw-message {
      xr:xr-xml-map "mpls_te_tunnel_cfg:InsufficientBWMessage";
      type empty;
      description "Log tunnel messages for insufficient bandwidth";
    }
  }

  grouping KEYCHAIN {
    description "Common node of peer, pce-attributes";
    leaf keychain {
      xr:xr-xml-map "mpls_te_cfg:Keychain";
      xr:xr-cli-map "keychain <string> ";
      xr:xr-cli-map "traffic-eng pce keychain <string> ";
      type string {
        length "0..32";
      }
      description "Keychain based authentication";
    }
  }

  grouping PRIORITY {
    description
      "Common node of tunnel-te-attributes,
      tunnel-attributes, auto-mesh-attribute,
      gmpls-unitunnel-head, auto-backup-attribute,
      p2mpte-attribute";

    container priority {
      xr:xr-xml-map "mpls_te_tunnel_cfg:Priority";
      presence "Indicates a priority node is configured.";
      description "Tunnel Setup and Hold Priorities";
      leaf setup-priority {
        xr:xr-xml-map "mpls_te_tunnel_cfg:SetupPriority";
        type uint32 {
          range "0..7";
        }
        mandatory true;
        description "Setup Priority";
      }
      leaf hold-priority {
        xr:xr-xml-map "mpls_te_tunnel_cfg:HoldPriority";
        type uint32 {
          range "0..7";
        }
        mandatory true;
        description "Hold Priority";
      }
    }
  }

  container mpls-te {
    xr:xr-xml-map "mpls_te_cfg:MPLS_TE";
    description "The root of MPLS TE configuration";

    container diff-serv-traffic-engineering {
      xr:xr-xml-map "mpls_te_cfg:DiffServTrafficEngineering";
      description "Configure Diff-Serv Traffic-Engineering";

      container classes {
        xr:xr-xml-map "mpls_te_cfg:ClassTable";
        description
          "Configure Diff-Serv Traffic-Engineering Classes";

        list class {
          xr:xr-xml-map "mpls_te_cfg:Class";
          xr:xr-cli-map "traffic-eng te-classes te-class <number> ("+
            "unused)|(class-type <number> priority <number>) ";
          key "class-number";
          description "DSTE class number";
          leaf class-number {
            xr:xr-xml-map "mpls_te_cfg:ClassNumber";
            type uint32 {
              range "0..7";
            }
            description "DS-TE class number";
          }
          leaf class-type {
            xr:xr-xml-map "mpls_te_cfg:ClassType";
            when "../unused = 0" {
              description "../Unused = <expr>";
            }
            type uint32 {
              range "0..1";
            }
            description "Class type number";
          }
          leaf class-priority {
            xr:xr-xml-map "mpls_te_cfg:ClassPriority";
            when "../unused = 0" {
              description "../Unused = <expr>";
            }
            type uint32 {
              range "0..7";
            }
            description "Class-type priority";
          }
          leaf unused {
            xr:xr-xml-map "mpls_te_cfg:Unused";
            type boolean;
            description
              "TRUE to skip classtype and class priority
              provisioning FALSE to provision them";
          }
        }
      }
      leaf bandwidth-constraint-model {
        xr:xr-xml-map "mpls_te_cfg:BandwidthConstraintModel";
        xr:xr-cli-map "traffic-eng bc-model mam ";
        type Bandwidth-constraint;
        description
          "Diff-Serv Traffic-Engineering Bandwidth
          Constraint Model";
      }
      leaf mode-ietf {
        xr:xr-xml-map "mpls_te_cfg:ModeIETF";
        xr:xr-cli-map "traffic-eng mode ietf ";
        type Ietf-mode;
        description "Diff-Serv Traffic-Engineering IETF mode";
      }
    }

    container named-tunnels {
      xr:xr-xml-map "mpls_te_tunnel_cfg:NamedTunnels";
      description "Configure MPLS TE tunnel";

      container tunnels {
        xr:xr-xml-map "mpls_te_tunnel_cfg:TunnelTable";
        description "Configure MPLS TE tunnel";

        list tunnel {
          xr:xr-xml-map "mpls_te_tunnel_cfg:Tunnel";
          key "tunnel-name tunnel-type";
          description "Configure a MPLS TE tunnel";

          container tunnel-attributes {
            xr:xr-xml-map "mpls_te_tunnel_cfg:TunnelAttributes";
            description "MPLS tunnel attributes";

            container path-setups {
              xr:xr-xml-map "mpls_te_tunnel_cfg:PathSetupTable";
              description "Tunnel path setup table";

              list path-setup {
                xr:xr-xml-map "mpls_te_tunnel_cfg:PathSetup";
                key "path-setup-name";
                description "Tunnel path setup";

                container path-computation {
                  xr:xr-xml-map "mpls_te_tunnel_cfg:PathComputation";
                  presence "Indicates a path-computation node is"+
                    " configured.";
                  description "Path computation method";
                  leaf path-computation-method {
                    xr:xr-xml-map "mpls_te_tunnel_cfg:PathComputati"+
                      "onMethod";
                    type Mpls-te-path-computation-method;
                    mandatory true;
                    description "Path computation method";
                  }
                  leaf explicit-path-name {
                    xr:xr-xml-map "mpls_te_tunnel_cfg:ExplicitPathN"+
                      "ame";
                    type string;
                    description "Explicit Path Name";
                  }
                  leaf path-computation-server {
                    xr:xr-xml-map "mpls_te_tunnel_cfg:PathComputati"+
                      "onServer";
                    type inet:ipv4-address-no-zone;
                    default "0.0.0.0";
                    description "Path Computation Server Address";
                  }
                }
                leaf preference {
                  xr:xr-xml-map "mpls_te_tunnel_cfg:Preference";
                  xr:xr-cli-map "traffic-eng named-tunnels tunnel-t"+
                    "e <string> path-option <string> preference <nu"+
                    "mber> ";
                  type int32;
                  description "Path preference level";
                }
                leaf enable {
                  xr:xr-xml-map "mpls_te_tunnel_cfg:Enable";
                  type empty;
                  description "Always set to true";
                }
                leaf path-setup-name {
                  xr:xr-xml-map "mpls_te_tunnel_cfg:PathSetupName";
                  type xr:Cisco-ios-xr-string;
                  description "Path Name";
                }
              }
            }
            uses FORWARD-CLASS;
            uses TUNNEL-PATH-SELECTION;
            uses AUTO-BANDWIDTH;
            uses PRIORITY;
            uses DESTINATION;
            uses RECORD-ROUTE;
            uses BANDWIDTH;
            uses AUTOROUTE;
            uses PATH-SELECTION-METRIC;
            uses NEW-STYLE-AFFINITY-TABLE;
            uses SOFT-PREEMPTION;
            uses FAST-REROUTE;
          }

          container tunnel-id {
            xr:xr-xml-map "mpls_te_tunnel_cfg:TunnelID";
            presence "Indicates a tunnel-id node is configured.";
            description "Set the tunnel ID";
            leaf tunnel-id-type {
              xr:xr-xml-map "mpls_te_tunnel_cfg:TunnelIDType";
              type Mpls-te-tunnel-id;
              mandatory true;
              description "Tunnel ID Type";
            }
            leaf tunnel-id {
              xr:xr-xml-map "mpls_te_tunnel_cfg:TunnelID";
              type uint32 {
                range "0..65535";
              }
              description "Tunnel ID";
            }
          }
          leaf enable {
            xr:xr-xml-map "mpls_te_tunnel_cfg:Enable";
            type empty;
            description "Always set to true";
          }
          leaf tunnel-name {
            xr:xr-xml-map "mpls_te_tunnel_cfg:TunnelName";
            type xr:Cisco-ios-xr-string {
              length "0..62";
            }
            description "Tunnel name";
          }
          leaf tunnel-type {
            xr:xr-xml-map "mpls_te_tunnel_cfg:TunnelType";
            type Mpls-te-config-tunnel;
            description "Tunnel Type";
          }
        }
      }
      leaf enable {
        xr:xr-xml-map "mpls_te_tunnel_cfg:Enable";
        type empty;
        description "Enable Named Tunnels";
      }
    }

    container gmpls-uni {
      xr:xr-xml-map "mpls_te_gmpls_cfg:GMPLS_UNI";
      description "GMPLS-UNI configuration";

      container timers {
        xr:xr-xml-map "mpls_te_gmpls_cfg:Timers";
        description "GMPLS-UNI timer configuration";

        container path-option-timers {
          xr:xr-xml-map "mpls_te_gmpls_cfg:PathOptionTimers";
          description "GMPLS-UNI path-option timer configuration";

          container holddown {
            xr:xr-xml-map "mpls_te_gmpls_cfg:Holddown";
            description
              "GMPLS-UNI path-option holddown timer
              configuration";
            leaf minimum {
              xr:xr-xml-map "mpls_te_gmpls_cfg:Minimum";
              type uint32 {
                range "5..3600";
              }
              units "second";
              description "Minimum holddown (seconds)";
            }
            leaf maximum {
              xr:xr-xml-map "mpls_te_gmpls_cfg:Maximum";
              type uint32 {
                range "5..3600";
              }
              units "second";
              description "Maximum holddown (seconds)";
            }
          }
        }
      }

      container controllers {
        xr:xr-xml-map "mpls_te_gmpls_cfg:ControllerTable";
        description "GMPLS-UNI controllers";

        list controller {
          xr:xr-xml-map "mpls_te_gmpls_cfg:Controller";
          key "controller-name";
          description "Configure a GMPLS controller";

          container announce {
            xr:xr-xml-map "mpls_te_gmpls_cfg:Announce";
            description
              "Announce discovered tunnel properties to
              system";
            leaf srl-gs {
              xr:xr-xml-map "mpls_te_gmpls_cfg:SRLGs";
              xr:xr-cli-map "traffic-eng gmpls optical-uni controll"+
                "er announce srlgs ";
              type empty;
              description "Enable announcement of discovered SRLGs";
            }
          }

          container controller-logging {
            xr:xr-xml-map "mpls_te_gmpls_cfg:ControllerLogging";
            description "Controller logging";
            leaf discovered-srlg-change-logging {
              xr:xr-xml-map "mpls_te_gmpls_cfg:DiscoveredSRLGChange"+
                "Logging";
              type empty;
              description
                "Enable logging of changes to of discovered
                SRLGs";
            }
          }

          container gmpls-unitunnel-head {
            xr:xr-xml-map "mpls_te_gmpls_cfg:GMPLS_UNITunnelHead";
            description "GMPLS-UNI tunnel-head properties";

            container path-options {
              xr:xr-xml-map "mpls_te_gmpls_cfg:PathOptionTable";
              description "Path-option configuration";

              list path-option {
                xr:xr-xml-map "mpls_te_gmpls_cfg:PathOption";
                xr:xr-cli-map "traffic-eng gmpls optical-uni contro"+
                  "ller tunnel-properties path-option <number> (no-"+
                  "ero)|(explicit (identifier <number>)|(name <stri"+
                  "ng>)) [xro-attribute-set <string>|signaled-label"+
                  " dwdm wavelength <number>] (lockdown)|(verbatim)"+
                  "] ";
                key "preference-level";
                description "A Path-option";
                leaf preference-level {
                  xr:xr-xml-map "mpls_te_gmpls_cfg:PreferenceLevel";
                  type uint32 {
                    range "1..1000";
                  }
                  description
                    "Preference level for this path option";
                }
                leaf path-type {
                  xr:xr-xml-map "mpls_te_gmpls_cfg:PathType";
                  type Mpls-te-path-option;
                  mandatory true;
                  description "The type of the path option";
                }
                leaf path-id {
                  xr:xr-xml-map "mpls_te_gmpls_cfg:PathID";
                  type uint32 {
                    range "1..65535";
                  }
                  default "1";
                  description
                    "The ID of the explicit path associated
                    with this option";
                }
                leaf path-name {
                  xr:xr-xml-map "mpls_te_gmpls_cfg:PathName";
                  type string;
                  description
                    "The name of the explicit path associated
                    with this option";
                }
                leaf xro-type {
                  xr:xr-xml-map "mpls_te_gmpls_cfg:XROType";
                  type Mpls-te-path-option-xro;
                  mandatory true;
                  description "The route-exclusion type";
                }
                leaf xro-attribute-set-name {
                  xr:xr-xml-map "mpls_te_gmpls_cfg:XROAttributeSetN"+
                    "ame";
                  type Attribute-set-name-length;
                  description
                    "The name of the XRO attribute set to be
                    used for this path-option";
                }
                leaf lockdown {
                  xr:xr-xml-map "mpls_te_gmpls_cfg:Lockdown";
                  type Mpls-te-path-option-property;
                  mandatory true;
                  description
                    "Path option properties: must be Lockdown";
                }
                leaf verbatim {
                  xr:xr-xml-map "mpls_te_gmpls_cfg:Verbatim";
                  type Mpls-te-path-option-property;
                  default "none";
                  description
                    "Path option properties: must be verbatim
                    if set";
                }
                leaf signaled-label {
                  xr:xr-xml-map "mpls_te_gmpls_cfg:SignaledLabel";
                  type Mpls-te-signaled-label;
                  default "not-set";
                  description "Signaled label type";
                }
                leaf dwdm-channel {
                  xr:xr-xml-map "mpls_te_gmpls_cfg:DWDMChannel";
                  type uint32 {
                    range "1..89";
                  }
                  default "1";
                  description "DWDM channel number";
                }
              }
            }

            container recording {
              xr:xr-xml-map "mpls_te_gmpls_cfg:Recording";
              description "Tunnel property recording";
              leaf srlg {
                xr:xr-xml-map "mpls_te_gmpls_cfg:SRLG";
                xr:xr-cli-map "traffic-eng gmpls optical-uni contro"+
                  "ller tunnel-properties record srlg ";
                type empty;
                description
                  "Enable SRLG-recording during signaling";
              }
            }

            container logging {
              xr:xr-xml-map "mpls_te_gmpls_cfg:Logging";
              description "Tunnel event logging";
              uses STATE-MESSAGE;
            }
            leaf tunnel-id {
              xr:xr-xml-map "mpls_te_gmpls_cfg:TunnelID";
              xr:xr-cli-map "traffic-eng gmpls optical-uni controll"+
                "er tunnel-properties tunnel-id <number> ";
              type uint32 {
                range "0..65535";
              }
              description "GMPLS-UNI head tunnel-id";
            }
            leaf enable {
              xr:xr-xml-map "mpls_te_gmpls_cfg:Enable";
              type empty;
              description "Set link as a GMPLS tunnel head";
            }
            leaf destination {
              xr:xr-xml-map "mpls_te_gmpls_cfg:Destination";
              xr:xr-cli-map "traffic-eng gmpls optical-uni controll"+
                "er tunnel-properties destination ipv4 unicast <IPv"+
                "4 address> ";
              type inet:ipv4-address-no-zone;
              description "Set the destination of the tunnel";
            }
            uses PRIORITY;
            uses RECORD-ROUTE;
            uses SIGNALLED-NAME;
          }
          leaf enable {
            xr:xr-xml-map "mpls_te_gmpls_cfg:Enable";
            type empty;
            description "Enable GMPLS-UNI on the link";
          }
          leaf controller-name {
            xr:xr-xml-map "mpls_te_gmpls_cfg:ControllerName";
            type xr:Interface-name;
            description "Controller name";
          }
        }
      }
    }

    container global-attributes {
      xr:xr-xml-map "mpls_te_cfg:GlobalAttributes";
      description "Configure MPLS TE global attributes";

      container auto-tunnel {
        xr:xr-xml-map "mpls_te_cfg:AutoTunnel";
        description "Configure auto-tunnels feature";

        container pcc {
          xr:xr-xml-map "mpls_te_autopcc_cfg:PCC";
          description
            "Configure auto-tunnel PCC (Path Computation
            Client) feature";
          uses TUNNEL-RANGE;
        }

        container p2p-auto-tunnel {
          xr:xr-xml-map "mpls_te_auto_p2p_cfg:P2PAutoTunnel";
          description "Configure P2P auto-tunnel feature";
          uses TUNNEL-RANGE;
        }

        container backup {
          xr:xr-xml-map "mpls_te_autobackup_cfg:Backup";
          description "Configure auto-tunnel backup feature";
          leaf affinity-ignore {
            xr:xr-xml-map "mpls_te_autobackup_cfg:AffinityIgnore";
            xr:xr-cli-map "traffic-eng backup affinity ignore ";
            type empty;
            description
              "Ignore affinity during CSPF for auto backup
              tunnels";
          }
          uses TIMERS;
          uses TUNNEL-RANGE;
        }

        container mesh {
          xr:xr-xml-map "mpls_te_automesh_cfg:Mesh";
          description "Configure auto-tunnel mesh feature";

          container mesh-groups {
            xr:xr-xml-map "mpls_te_automesh_cfg:MeshGroupTable";
            description "Configure auto-tunnel mesh group";

            list mesh-group {
              xr:xr-xml-map "mpls_te_automesh_cfg:MeshGroup";
              key "mesh-group-id";
              description "Auto-mesh group identifier";
              leaf destination-list {
                xr:xr-xml-map "mpls_te_automesh_cfg:DestinationList";
                type Destination-list-name-length;
                description
                  "The name of prefix-list to be applied to
                  this destination-list";
              }
              leaf disable {
                xr:xr-xml-map "mpls_te_automesh_cfg:Disable";
                type empty;
                description "Disables mesh group";
              }
              leaf attribute-set {
                xr:xr-xml-map "mpls_te_automesh_cfg:AttributeSet";
                type Attribute-set-name-length;
                description
                  "The name of auto-mesh attribute set to be
                  applied to this group";
              }
              leaf create {
                xr:xr-xml-map "mpls_te_automesh_cfg:Create";
                type empty;
                description
                  "Auto-mesh group enable object that controls
                  whether this group is configured or not
                  .This object must be set before other
                  configuration supplied for this group";
              }
              leaf one-hop {
                xr:xr-xml-map "mpls_te_automesh_cfg:OneHop";
                type empty;
                description
                  "Automatically create tunnel to all
                  next-hops";
              }
              leaf mesh-group-id {
                xr:xr-xml-map "mpls_te_automesh_cfg:MeshGroupID";
                type Mesh-group-id;
                description "Mesh group ID";
              }
            }
          }
          uses TIMERS;
          uses TUNNEL-RANGE;
        }

        container p2mp-auto-tunnel {
          xr:xr-xml-map "mpls_te_auto_p2mp_cfg:P2MPAutoTunnel";
          description "Configure P2MP auto-tunnel feature";
          uses TUNNEL-RANGE;
        }
      }

      container secondary-router-ids {
        xr:xr-xml-map "mpls_te_cfg:SecondaryRouterIDTable";
        description "Configure MPLS TE Secondary Router ID";

        list secondary-router-id {
          xr:xr-xml-map "mpls_te_cfg:SecondaryRouterID";
          xr:xr-cli-map "traffic-eng router-id secondary <IPv4 addr"+
            "ess> ";
          key "secondary-router-id-value";
          description "Secondary Router ID";
          leaf secondary-router-id-value {
            xr:xr-xml-map "mpls_te_cfg:SecondaryRouterIDValue";
            type inet:ipv4-address-no-zone;
            description "Secondary TE Router ID";
          }
        }
      }

      container srlg {
        xr:xr-xml-map "mpls_te_cfg:SRLG";
        description "Configure SRLG values and MPLS-TE properties";

        container names {
          xr:xr-xml-map "mpls_te_cfg:NameTable";
          description "Configure SRLG identified by names";

          list name {
            xr:xr-xml-map "mpls_te_cfg:Name";
            key "srlg-name";
            description "SRLG name and its MPLS-TE properties";

            container static-srlg-members {
              xr:xr-xml-map "mpls_te_cfg:StaticSRLGMembersList";
              description "Configure static SRLG members list";

              list static-srlg-member {
                xr:xr-xml-map "mpls_te_cfg:StaticSRLGMember";
                xr:xr-cli-map "traffic-eng srlg name <string> stati"+
                  "c ipv4 address <IPv4 address> next-hop ipv4 addr"+
                  "ess <IPv4 address> ";
                key "from-address";
                description
                  "A mapping of the local static SRLG member";
                leaf from-address {
                  xr:xr-xml-map "mpls_te_cfg:FromAddress";
                  type inet:ipv4-address-no-zone;
                  description "From address";
                }
                leaf to-address {
                  xr:xr-xml-map "mpls_te_cfg:ToAddress";
                  type inet:ipv4-address-no-zone;
                  mandatory true;
                  description "To Addres";
                }
              }
            }
            leaf srlg-name {
              xr:xr-xml-map "mpls_te_cfg:SRLGName";
              type xr:Cisco-ios-xr-string {
                length "0..64";
              }
              description "SRLG membership name";
            }
            uses ADMIN-WEIGHT;
          }
        }

        container values {
          xr:xr-xml-map "mpls_te_cfg:ValueTable";
          description
            "Configure SRLG values and MPLS-TE properties";

          list value {
            xr:xr-xml-map "mpls_te_cfg:Value";
            key "srlg-number";
            description "SRLG value and its MPLS-TE properties";

            container ipv4-address-maps {
              xr:xr-xml-map "mpls_te_cfg:IPv4AddressMapTable";
              description
                "Configure outgoing and remote link addresses
                for a given SRLG value";

              list ipv4-address-map {
                xr:xr-xml-map "mpls_te_cfg:IPv4AddressMap";
                xr:xr-cli-map "traffic-eng srlg value <number> stat"+
                  "ic ipv4 address <IPv4 address> next-hop ipv4 add"+
                  "ress <IPv4 address> ";
                key "outgoing-ipv4-address remote-ipv4-address";
                description
                  "A mapping of the remote and local addresses
                  of a link to an SRLG value";
                leaf outgoing-ipv4-address {
                  xr:xr-xml-map "mpls_te_cfg:OutgoingIPv4Address";
                  type inet:ipv4-address-no-zone;
                  description "Outgoing v4 address";
                }
                leaf remote-ipv4-address {
                  xr:xr-xml-map "mpls_te_cfg:RemoteIPv4Address";
                  type inet:ipv4-address-no-zone;
                  description "Remote v4 address";
                }
              }
            }
            leaf srlg-number {
              xr:xr-xml-map "mpls_te_cfg:SRLGNumber";
              type uint32 {
                range "0..4294967295";
              }
              description "SRLG membership number";
            }
            uses ADMIN-WEIGHT;
          }
        }
        leaf default-admin-weight {
          xr:xr-xml-map "mpls_te_cfg:DefaultAdminWeight";
          xr:xr-cli-map "traffic-eng srlg admin-weight <number> ";
          type int32;
          default "1";
          description
            "Default Admin weight any SRLG value that does
            not have one";
        }
        leaf enable {
          xr:xr-xml-map "mpls_te_cfg:Enable";
          type empty;
          description "Enter SRLG property configuration";
        }
      }

      container queues {
        xr:xr-xml-map "mpls_te_cfg:RoutePriority";
        description "Configure MPLS TE route priority";

        list queue {
          xr:xr-xml-map "mpls_te_cfg:Queue";
          xr:xr-cli-map "traffic-eng route-priority role (head (pri"+
            "mary)|(backup))|(middle) queue <number> ";
          key "role";
          description "Configure route priority queue value";
          leaf role {
            xr:xr-xml-map "mpls_te_cfg:Role";
            type Route-priority-role;
            description "Route Priority Tunnel Role";
          }
          leaf value {
            xr:xr-xml-map "mpls_te_cfg:Value";
            type uint32 {
              range "0..12";
            }
            mandatory true;
            description "Route priority queue value";
          }
        }
      }

      container mib {
        xr:xr-xml-map "mpls_te_cfg:MIB";
        description "MPLS-TE MIB properties";
        leaf midpoint-lsp-stats-collection-disable {
          xr:xr-xml-map "mpls_te_cfg:MidpointLSPStatsCollectionDisa"+
            "ble";
          xr:xr-cli-map "traffic-eng mib midstats disable ";
          type empty;
          description
            "Disables mib midpoint LSP traffic stats
            collection";
        }
      }

      container attribute-set {
        xr:xr-xml-map "mpls_te_attr_set_cfg:AttributeSet";
        description "Attribute AttributeSets";

        container path-option-attributes {
          xr:xr-xml-map "mpls_te_attr_set_cfg:PathOptionAttributeTa"+
            "ble";
          description "Path Option Attribute-Set Table";

          list path-option-attribute {
            xr:xr-xml-map "mpls_te_attr_set_cfg:PathOptionAttribute";
            key "attribute-set-name";
            description "Path Option Attribute";

            container att-path-option-path-selection {
              xr:xr-xml-map "mpls_te_tunnel_cfg:AttPathOptionPathSe"+
                "lection";
              description "Configure path selection properties";
              leaf path-selection-exclude-list {
                xr:xr-xml-map "mpls_te_tunnel_cfg:PathSelectionExcl"+
                  "udeList";
                type xr:Cisco-ios-xr-string {
                  length "0..64";
                }
                description
                  "Path selection exclude list name
                  configuration";
              }
              uses ENABLE;
              uses INVALIDATION;
              uses PATH-SELECTION-COST-LIMIT;
            }
            leaf attribute-set-name {
              xr:xr-xml-map "mpls_te_attr_set_cfg:AttributeSetName";
              type Attribute-set-name-length;
              description "Attribute Set Name";
            }
            uses MPLS-TE-ATTR-SET-CFG-ENABLE;
            uses AFFINITY-MASK;
            uses BANDWIDTH;
            uses NEW-STYLE-AFFINITY-TABLE;
          }
        }

        container p2mpte-attributes {
          xr:xr-xml-map "mpls_te_attr_set_cfg:P2MPTEAttributeTable";
          description "P2MP-TE Tunnel AttributeSets Table";

          list p2mpte-attribute {
            xr:xr-xml-map "mpls_te_attr_set_cfg:P2MPTEAttribute";
            key "attribute-set-name";
            description "P2MP-TE Tunnel Attribute";
            leaf attribute-set-name {
              xr:xr-xml-map "mpls_te_attr_set_cfg:AttributeSetName";
              type Attribute-set-name-length;
              description "Attribute Set Name";
            }
            uses INTERFACE-BANDWIDTH;
            uses PRIORITY;
            uses MPLS-TE-ATTR-SET-CFG-ENABLE;
            uses RECORD-ROUTE;
            uses AFFINITY-MASK;
            uses BANDWIDTH;
            uses PATH-SELECTION;
            uses NEW-STYLE-AFFINITY-TABLE;
            uses FAST-REROUTE;
            uses LOGGING;
          }
        }

        container p2p-te-attributes {
          xr:xr-xml-map "mpls_te_attr_set_cfg:P2P_TEAttributeTable";
          description "P2P-TE Tunnel AttributeSets Table";

          list p2p-te-attribute {
            xr:xr-xml-map "mpls_te_attr_set_cfg:P2P_TEAttribute";
            key "attribute-set-name";
            description "P2P-TE Tunnel Attribute";

            container path-selection {
              xr:xr-xml-map "mpls_te_tunnel_cfg:PathSelection";
              description "Configure path selection properties";

              container segment-routing-prepend {
                xr:xr-xml-map "mpls_te_tunnel_cfg:SegmentRoutingPre"+
                  "pend";
                description
                  "Path selection segment routing prepend
                  configuration";

                container indexes {
                  xr:xr-xml-map "mpls_te_tunnel_cfg:IndexTable";
                  description "Segment routing prepend index table";

                  list index {
                    xr:xr-xml-map "mpls_te_tunnel_cfg:Index";
                    key "index-number";
                    description "Prepend index information";
                    leaf index-number {
                      xr:xr-xml-map "mpls_te_tunnel_cfg:IndexNumber";
                      type uint32 {
                        range "1..10";
                      }
                      description "Index number";
                    }
                    leaf prepend-type {
                      xr:xr-xml-map "mpls_te_tunnel_cfg:PrependType";
                      type Sr-prepend;
                      default "none-type";
                      description "Prepend type";
                    }
                    leaf mpls-label {
                      xr:xr-xml-map "mpls_te_tunnel_cfg:MPLSLabel";
                      type int32;
                      default "1048577";
                      description "MPLS Label";
                    }
                  }
                }
                leaf enable {
                  xr:xr-xml-map "mpls_te_tunnel_cfg:Enable";
                  type empty;
                  description
                    "Enter path selection segment routing
                    prepend submode";
                }
              }

              container invalidation {
                xr:xr-xml-map "mpls_te_tunnel_cfg:Invalidation";
                description
                  "Path selection invalidation configuration";
                leaf invalidation-timer {
                  xr:xr-xml-map "mpls_te_tunnel_cfg:InvalidationTim"+
                    "er";
                  type uint32 {
                    range "0..60000";
                  }
                  units "millisecond";
                  description
                    "Path selection invalidation timer value
                    (milliseconds)";
                }
                leaf invalidation-timer-expire-type {
                  xr:xr-xml-map "mpls_te_tunnel_cfg:InvalidationTim"+
                    "erExpireType";
                  type Mpls-te-path-selection-invalidation-timer-expire;
                  default "tunnel-action-tear";
                  description
                    "Path selection invalidation timer expire
                    type";
                }
              }
              leaf path-selection-metric {
                xr:xr-xml-map "mpls_te_tunnel_cfg:PathSelectionMetr"+
                  "ic";
                type Mpls-te-path-selection-metric;
                description
                  "Path selection metric to use in path
                  calculation";
              }
              leaf path-selection-segment-routing-adjacency-protection {
                xr:xr-xml-map "mpls_te_tunnel_cfg:PathSelectionSegm"+
                  "entRoutingAdjacencyProtection";
                type Mpls-te-path-selection-segment-routing-adjacency-protection;
                description
                  "Segment routing adjacency protection type
                  to use in path calculation";
              }
              uses ENABLE;
            }

            container logging {
              xr:xr-xml-map "mpls_te_tunnel_cfg:Logging";
              description "Log tunnel LSP messages";
              leaf lsp-switch-over-change-message {
                xr:xr-xml-map "mpls_te_tunnel_cfg:LSPSwitchOverChan"+
                  "geMessage";
                type empty;
                description
                  "Log tunnel messages for bandwidth change";
              }
              leaf all {
                xr:xr-xml-map "mpls_te_tunnel_cfg:All";
                type empty;
                description "Log all events for a tunnel";
              }
              leaf record-route-messsage {
                xr:xr-xml-map "mpls_te_tunnel_cfg:RecordRouteMesssa"+
                  "ge";
                type empty;
                description "Log tunnel record-route messages";
              }
              leaf bfd-state-message {
                xr:xr-xml-map "mpls_te_tunnel_cfg:BFDStateMessage";
                type empty;
                description "Enable BFD session state change alarm";
              }
              uses BANDWIDTH-CHANGE-MESSAGE;
              uses REOPTIMIZE-ATTEMPTS-MESSAGE;
              uses REROUTE-MESSSAGE;
              uses STATE-MESSAGE;
              uses INSUFFICIENT-BW-MESSAGE;
              uses REOPTIMIZED-MESSAGE;
              uses PCALC-FAILURE-MESSAGE;
            }
            leaf attribute-set-name {
              xr:xr-xml-map "mpls_te_attr_set_cfg:AttributeSetName";
              type Attribute-set-name-length;
              description "Attribute Set Name";
            }
            uses MPLS-TE-ATTR-SET-CFG-ENABLE;
            uses AFFINITY-MASK;
            uses NEW-STYLE-AFFINITY-TABLE;
          }
        }

        container auto-backup-attributes {
          xr:xr-xml-map "mpls_te_attr_set_cfg:AutoBackupAttributeTa"+
            "ble";
          description "Auto-backup Tunnel Attribute Table";

          list auto-backup-attribute {
            xr:xr-xml-map "mpls_te_attr_set_cfg:AutoBackupAttribute";
            key "attribute-set-name";
            description "Auto-backup Tunnel Attribute";

            container signalled-name {
              xr:xr-xml-map "mpls_te_attr_set_cfg:SignalledName";
              description "Signalled name";
              leaf name {
                xr:xr-xml-map "mpls_te_attr_set_cfg:Name";
                type string;
                description "Signalled name";
              }
              leaf source-type {
                xr:xr-xml-map "mpls_te_attr_set_cfg:SourceType";
                type Mpls-te-sig-name-option;
                description "Source address or name";
              }
              leaf protected-interface-type {
                xr:xr-xml-map "mpls_te_attr_set_cfg:ProtectedInterf"+
                  "aceType";
                type Mpls-te-sig-name-option;
                description "Protected-interface address or name";
              }
              leaf mp-address {
                xr:xr-xml-map "mpls_te_attr_set_cfg:MPAddress";
                type boolean;
                description
                  "Set if merge-point address is to be
                  appended";
              }
            }

            container auto-backup-logging {
              xr:xr-xml-map "mpls_te_tunnel_cfg:AutoBackupLogging";
              description "Log tunnel LSP messages";
              uses BANDWIDTH-CHANGE-MESSAGE;
              uses REOPTIMIZE-ATTEMPTS-MESSAGE;
              uses STATE-MESSAGE;
              uses REOPTIMIZED-MESSAGE;
            }
            leaf attribute-set-name {
              xr:xr-xml-map "mpls_te_attr_set_cfg:AttributeSetName";
              type Attribute-set-name-length;
              description "Attribute Set Name";
            }
            uses PRIORITY;
            uses MPLS-TE-ATTR-SET-CFG-ENABLE;
            uses RECORD-ROUTE;
            uses AFFINITY-MASK;
            uses PATH-SELECTION;
            uses POLICY-CLASSES;
            uses NEW-STYLE-AFFINITY-TABLE;
          }
        }

        container otn-pp-attributes {
          xr:xr-xml-map "mpls_te_attr_set_cfg:OTN_PPAttributeTable";
          description "OTN Path Protection Attributes table";

          list otn-pp-attribute {
            xr:xr-xml-map "mpls_te_attr_set_cfg:OTN_PPAttribute";
            key "attribute-set-name";
            description "OTN Path Protection Attribute";

            container revert-schedule-names {
              xr:xr-xml-map "mpls_te_attr_set_cfg:RevertSchedule";
              description "Specify APS revert schedule";

              list revert-schedule-name {
                xr:xr-xml-map "mpls_te_attr_set_cfg:RevertScheduleN"+
                  "ame";
                key "schedule-name";
                description "Name Identifier for revert schedule";

                container schedule-duration {
                  xr:xr-xml-map "mpls_te_attr_set_cfg:ScheduleDurat"+
                    "ion";
                  presence "Indicates a schedule-duration node is"+
                    " configured.";
                  description "Set duration in format hh:mm";
                  leaf hour {
                    xr:xr-xml-map "mpls_te_attr_set_cfg:Hour";
                    type uint32 {
                      range "0..167";
                    }
                    mandatory true;
                    description "Hour of day";
                  }
                  leaf minutes {
                    xr:xr-xml-map "mpls_te_attr_set_cfg:Minutes";
                    type uint32 {
                      range "0..59";
                    }
                    mandatory true;
                    description "Minute of the hour";
                  }
                }

                container schedule-date {
                  xr:xr-xml-map "mpls_te_attr_set_cfg:ScheduleDate";
                  presence "Indicates a schedule-date node is"+
                    " configured.";
                  description
                    "Set date in format hh:mm MMM DD YYYY";
                  leaf hour {
                    xr:xr-xml-map "mpls_te_attr_set_cfg:Hour";
                    type uint32 {
                      range "0..23";
                    }
                    mandatory true;
                    description "Hour of day";
                  }
                  leaf minutes {
                    xr:xr-xml-map "mpls_te_attr_set_cfg:Minutes";
                    type uint32 {
                      range "0..59";
                    }
                    mandatory true;
                    description "Minute of the hour";
                  }
                  leaf month {
                    xr:xr-xml-map "mpls_te_attr_set_cfg:Month";
                    type uint32 {
                      range "0..11";
                    }
                    mandatory true;
                    description "Month of the year";
                  }
                  leaf day {
                    xr:xr-xml-map "mpls_te_attr_set_cfg:Day";
                    type uint32 {
                      range "1..31";
                    }
                    mandatory true;
                    description "Day of the month";
                  }
                  leaf year {
                    xr:xr-xml-map "mpls_te_attr_set_cfg:Year";
                    type uint32 {
                      range "2015..2035";
                    }
                    mandatory true;
                    description "Year";
                  }
                }
                leaf revert-schedule-max-tries {
                  xr:xr-xml-map "mpls_te_attr_set_cfg:RevertSchedul"+
                    "eMaxTries";
                  type uint32 {
                    range "1..2016";
                  }
                  description "Revert Schedule Max tries";
                }
                leaf sch-name-enable {
                  xr:xr-xml-map "mpls_te_attr_set_cfg:SchNameEnable";
                  type empty;
                  description "Schedule name enable object";
                }
                leaf revert-schedule-frequency {
                  xr:xr-xml-map "mpls_te_attr_set_cfg:RevertSchedul"+
                    "eFrequency";
                  type uint32 {
                    range "1..3";
                  }
                  description
                    "Frequency set as Once, Daily, Weekly";
                }
                leaf schedule-name {
                  xr:xr-xml-map "mpls_te_attr_set_cfg:ScheduleName";
                  type xr:Cisco-ios-xr-string {
                    length "0..254";
                  }
                  description
                    "Enter 64 characters for revert schedule
                    name";
                }
              }
            }

            container sub-network-connection-mode {
              xr:xr-xml-map "mpls_te_attr_set_cfg:SubNetworkConnect"+
                "ionMode";
              description "Sub-network connection mode";
              leaf connection-mode {
                xr:xr-xml-map "mpls_te_attr_set_cfg:ConnectionMode";
                type Mpls-te-otn-snc-mode;
                description "The sub-network connection mode";
              }
              leaf connection-monitoring-mode {
                xr:xr-xml-map "mpls_te_attr_set_cfg:ConnectionMonit"+
                  "oringMode";
                type uint32 {
                  range "1..6";
                }
                description
                  "Tandem Connection Monitoring ID for the
                  interface";
              }
            }

            container timers {
              xr:xr-xml-map "mpls_te_attr_set_cfg:Timers";
              description "Timers";
              leaf aps-wait-to-restore {
                xr:xr-xml-map "mpls_te_attr_set_cfg:APSWaitToRestor"+
                  "e";
                type uint32 {
                  range "0..720";
                }
                units "second";
                description
                  "G.709 OTN path protection wait to restore
                  timer in seconds";
              }
              leaf aps-hold-off {
                xr:xr-xml-map "mpls_te_attr_set_cfg:APSHoldOff";
                type uint32 {
                  range "100..10000";
                }
                units "millisecond";
                description
                  "G.709 OTN path protection hold-off timer in
                  milliseconds";
              }
            }
            leaf aps-protection-mode {
              xr:xr-xml-map "mpls_te_attr_set_cfg:APSProtectionMode";
              type Mpls-te-otn-aps-protection-mode;
              description "The APS protecion mode";
            }
            leaf aps-restoration-style {
              xr:xr-xml-map "mpls_te_attr_set_cfg:APSRestorationSty"+
                "le";
              type Mpls-te-otn-aps-restoration-style;
              description "The APS restoration style";
            }
            leaf aps-protection-type {
              xr:xr-xml-map "mpls_te_attr_set_cfg:APSProtectionType";
              type Mpls-te-otn-aps-protection;
              description "The APS protecion type";
            }
            leaf attribute-set-name {
              xr:xr-xml-map "mpls_te_attr_set_cfg:AttributeSetName";
              type Attribute-set-name-length;
              description "Attribute Set Name";
            }
            uses MPLS-TE-ATTR-SET-CFG-ENABLE;
            uses PATH-SELECTION;
          }
        }

        container auto-mesh-attributes {
          xr:xr-xml-map "mpls_te_attr_set_cfg:AutoMeshAttributeTabl"+
            "e";
          description "Auto-mesh Tunnel AttributeSets Table";

          list auto-mesh-attribute {
            xr:xr-xml-map "mpls_te_attr_set_cfg:AutoMeshAttribute";
            key "attribute-set-name";
            description "Auto-mesh Tunnel Attribute";

            container auto-mesh-logging {
              xr:xr-xml-map "mpls_te_tunnel_cfg:AutoMeshLogging";
              description "Log tunnel LSP messages";
              uses BANDWIDTH-CHANGE-MESSAGE;
              uses REOPTIMIZE-ATTEMPTS-MESSAGE;
              uses REROUTE-MESSSAGE;
              uses STATE-MESSAGE;
              uses INSUFFICIENT-BW-MESSAGE;
              uses REOPTIMIZED-MESSAGE;
              uses PCALC-FAILURE-MESSAGE;
            }
            leaf autoroute-announce {
              xr:xr-xml-map "mpls_te_attr_set_cfg:AutorouteAnnounce";
              type empty;
              description "Enable autoroute announce";
            }
            leaf attribute-set-name {
              xr:xr-xml-map "mpls_te_attr_set_cfg:AttributeSetName";
              type Attribute-set-name-length;
              description "Attribute Set Name";
            }
            uses INTERFACE-BANDWIDTH;
            uses FORWARD-CLASS;
            uses PRIORITY;
            uses MPLS-TE-ATTR-SET-CFG-ENABLE;
            uses RECORD-ROUTE;
            uses AFFINITY-MASK;
            uses BANDWIDTH;
            uses PATH-SELECTION;
            uses COLLECTION-ONLY;
            uses POLICY-CLASSES;
            uses NEW-STYLE-AFFINITY-TABLE;
            uses SOFT-PREEMPTION;
            uses FAST-REROUTE;
            uses LOAD-SHARE;
          }
        }

        container xro-attributes {
          xr:xr-xml-map "mpls_te_attr_set_cfg:XROAttributeTable";
          description "XRO Tunnel Attributes table";

          list xro-attribute {
            xr:xr-xml-map "mpls_te_attr_set_cfg:XROAttribute";
            key "attribute-set-name";
            description "XRO Attribute";

            container path-diversity {
              xr:xr-xml-map "mpls_te_gmpls_cfg:PathDiversity";
              description "Path diversity";

              container srlgs {
                xr:xr-xml-map "mpls_te_gmpls_cfg:SRLGTable";
                description "SRLG-based path diversity";

                list srlg {
                  xr:xr-xml-map "mpls_te_gmpls_cfg:SRLG";
                  key "srlg";
                  description "SRLG-based path-diversity element";
                  leaf srlg {
                    xr:xr-xml-map "mpls_te_gmpls_cfg:SRLG";
                    type uint32 {
                      range "0..4294967295";
                    }
                    description "SRLG";
                  }
                  leaf conformance {
                    xr:xr-xml-map "mpls_te_gmpls_cfg:Conformance";
                    type Mpls-te-path-diversity-conformance;
                    mandatory true;
                    description
                      "The diversity conformance requirements";
                  }
                }
              }

              container lsp {
                xr:xr-xml-map "mpls_te_gmpls_cfg:LSP";
                description "LSP-based path diversity";

                container fecs {
                  xr:xr-xml-map "mpls_te_gmpls_cfg:FECTable";
                  description "FEC LSP-based path diversity";

                  list fec {
                    xr:xr-xml-map "mpls_te_gmpls_cfg:FEC";
                    key "source destination tunnel-id"+
                      " extended-tunnel-id lsp-id";
                    description
                      "LSP-based path-diversity, referenced by
                      FEC";
                    leaf source {
                      xr:xr-xml-map "mpls_te_gmpls_cfg:Source";
                      type inet:ipv4-address-no-zone;
                      description "Source address";
                    }
                    leaf destination {
                      xr:xr-xml-map "mpls_te_gmpls_cfg:Destination";
                      type inet:ipv4-address-no-zone;
                      description "Destination address";
                    }
                    leaf tunnel-id {
                      xr:xr-xml-map "mpls_te_gmpls_cfg:TunnelID";
                      type uint32 {
                        range "0..65535";
                      }
                      description "Tunnel id";
                    }
                    leaf extended-tunnel-id {
                      xr:xr-xml-map "mpls_te_gmpls_cfg:ExtendedTunn"+
                        "elID";
                      type inet:ipv4-address-no-zone;
                      description "Extended tunnel-id";
                    }
                    leaf lsp-id {
                      xr:xr-xml-map "mpls_te_gmpls_cfg:LSP_ID";
                      type uint32 {
                        range "0..65535";
                      }
                      description "LSP id";
                    }
                    leaf conformance {
                      xr:xr-xml-map "mpls_te_gmpls_cfg:Conformance";
                      type Mpls-te-path-diversity-conformance;
                      mandatory true;
                      description
                        "The diversity conformance requirements";
                    }
                  }
                }
              }
            }
            leaf attribute-set-name {
              xr:xr-xml-map "mpls_te_attr_set_cfg:AttributeSetName";
              type Attribute-set-name-length;
              description "Attribute Set Name";
            }
            uses MPLS-TE-ATTR-SET-CFG-ENABLE;
            uses PATH-SELECTION;
          }
        }
      }

      container bfd-over-lsp {
        xr:xr-xml-map "mpls_te_cfg:BFDOverLSP";
        description "BFD over MPLS TE Global Configurations";

        container tail {
          xr:xr-xml-map "mpls_te_cfg:Tail";
          description "BFD over LSP Tail Global Configurations";
          leaf multiplier {
            xr:xr-xml-map "mpls_te_cfg:Multiplier";
            xr:xr-cli-map "traffic-eng bfd lsp tail multiplier <num"+
              "ber> ";
            type uint32 {
              range "3..10";
            }
            description "Specify BFD over LSP tail multiplier";
          }
          leaf minimum-interval {
            xr:xr-xml-map "mpls_te_cfg:MinimumInterval";
            xr:xr-cli-map "traffic-eng bfd lsp tail minimum-interva"+
              "l <number> ";
            type uint32 {
              range "100..30000";
            }
            description
              "Specify BFD over LSP tail minimum interval";
          }
        }

        container head {
          xr:xr-xml-map "mpls_te_cfg:Head";
          description "BFD over LSP Head Global Configurations";
          leaf reopt-timeout {
            xr:xr-xml-map "mpls_te_cfg:ReoptTimeout";
            xr:xr-cli-map "traffic-eng bfd lsp head down-action reo"+
              "ptimize timeout <number> ";
            type uint32 {
              range "120..4294967295";
            }
            description "BFD session down reopt timeout";
          }
          leaf down-action {
            xr:xr-xml-map "mpls_te_cfg:DownAction";
            xr:xr-cli-map "traffic-eng bfd lsp head down-action res"+
              "etup ";
            type Mpls-te-bfd-session-down-action;
            description "Specify BFD session down action";
          }
        }
      }

      container pce-attributes {
        xr:xr-xml-map "mpls_te_cfg:PCEAttributes";
        description "Configuration MPLS TE PCE attributes";

        container pce-stateful {
          xr:xr-xml-map "mpls_te_cfg:PCEStateful";
          description "PCE Stateful";

          container stateful-timers {
            xr:xr-xml-map "mpls_te_cfg:StatefulTimers";
            description
              "Configure Stateful PCE (Path Computation
              Element) timers";
            leaf redelegation-timeout {
              xr:xr-xml-map "mpls_te_cfg:RedelegationTimeout";
              xr:xr-cli-map "traffic-eng pce stateful-client timers"+
                " redelegation-timeout <number> ";
              type uint32 {
                range "0..3600";
              }
              units "second";
              default "180";
              description
                "Timer for static tunnel redelegation in
                seconds, default is 180 seconds";
            }
            leaf state-timeout {
              xr:xr-xml-map "mpls_te_cfg:StateTimeout";
              xr:xr-cli-map "traffic-eng pce stateful-client timers"+
                " state-timeout <number> ";
              type uint32 {
                range "0..3600";
              }
              units "second";
              default "180";
              description
                "State timeout for LSPs without delegation in
                seconds, zero means immediate removal,
                default is 180 seconds";
            }
          }
          leaf fast-repair {
            xr:xr-xml-map "mpls_te_cfg:FastRepair";
            type empty;
            description
              "Enable reoptimization by PCC after path
              failures";
          }
          leaf instantiation {
            xr:xr-xml-map "mpls_te_cfg:Instantiation";
            type empty;
            description "PCE stateful instantiation capability";
          }
          leaf cisco-extension {
            xr:xr-xml-map "mpls_te_cfg:CiscoExtension";
            type empty;
            description "Enable processing of PCEP Cisco extension";
          }
          leaf delegation {
            xr:xr-xml-map "mpls_te_cfg:Delegation";
            type empty;
            description
              "Delegate all statically configured tunnels";
          }
          leaf report {
            xr:xr-xml-map "mpls_te_cfg:Report";
            type empty;
            description "Report all statically configured tunnels";
          }
          leaf enable {
            xr:xr-xml-map "mpls_te_cfg:Enable";
            type empty;
            description "PCE stateful capability";
          }
        }

        container timer {
          xr:xr-xml-map "mpls_te_cfg:Timer";
          description
            "Configure PCE (Path Computation Element)
            timers";
        }

        container peers {
          xr:xr-xml-map "mpls_te_cfg:PeerTable";
          description "Configure PCE peers";

          list peer {
            xr:xr-xml-map "mpls_te_cfg:Peer";
            key "pce-peer-address";
            description "PCE peer";
            leaf enable {
              xr:xr-xml-map "mpls_te_cfg:Enable";
              type empty;
              description
                "Enabled PCE peer (default source address
                uses local)";
            }
            leaf pce-peer-address {
              xr:xr-xml-map "mpls_te_cfg:PCEPeerAddress";
              type inet:ipv4-address-no-zone;
              description "Address of PCE Peer";
            }
            uses PASSWORD;
            uses KEYCHAIN;
            uses PRECEDENCE;
          }
        }

        container logging {
          xr:xr-xml-map "mpls_te_cfg:Logging";
          description
            "Configure PCE (Path Computation Element)
            logging feature";

          container events {
            xr:xr-xml-map "mpls_te_cfg:Events";
            description "Configure logging events";
            leaf peer-status {
              xr:xr-xml-map "mpls_te_cfg:PeerStatus";
              xr:xr-cli-map "traffic-eng pce logging events peer-st"+
                "atus ";
              type empty;
              description "Peer status changes logging";
            }
          }
        }
        leaf request-timeout {
          xr:xr-xml-map "mpls_te_cfg:RequestTimeout";
          xr:xr-cli-map "traffic-eng pce request-timeout <number> ";
          type uint32 {
            range "5..100";
          }
          units "second";
          default "10";
          description "Request timeout value in seconds";
        }
        leaf reoptimize-period {
          xr:xr-xml-map "mpls_te_cfg:ReoptimizePeriod";
          xr:xr-cli-map "traffic-eng pce reoptimize <number> ";
          type uint32 {
            range "60..604800";
          }
          units "second";
          default "60";
          description
            "PCE reoptimization period for PCE-based paths";
        }
        leaf address {
          xr:xr-xml-map "mpls_te_cfg:Address";
          xr:xr-cli-map "traffic-eng pce address ipv4 <IPv4 address"+
            "> ";
          type inet:ipv4-address-no-zone;
          description "Address of this PCE";
        }
        leaf deadtimer {
          xr:xr-xml-map "mpls_te_cfg:Deadtimer";
          xr:xr-cli-map "traffic-eng pce deadtimer <number> ";
          type uint32 {
            range "0..255";
          }
          units "second";
          default "120";
          description "Deadtimer interval in seconds";
        }
        leaf keepalive {
          xr:xr-xml-map "mpls_te_cfg:Keepalive";
          xr:xr-cli-map "traffic-eng pce keepalive <number> ";
          type uint32 {
            range "0..255";
          }
          units "second";
          default "30";
          description "Keepalive interval in seconds";
        }
        leaf keepalive-tolerance {
          xr:xr-xml-map "mpls_te_cfg:KeepaliveTolerance";
          xr:xr-cli-map "traffic-eng pce tolerance keepalive <numbe"+
            "r> ";
          type uint32 {
            range "0..255";
          }
          units "second";
          default "10";
          description "Keepalive interval tolerance in seconds";
        }
        leaf peer-source-addr {
          xr:xr-xml-map "mpls_te_cfg:PeerSourceAddr";
          xr:xr-cli-map "traffic-eng pce peer source ipv4 <IPv4 add"+
            "ress> ";
          type inet:ipv4-address-no-zone;
          description "PCE Peer Source Address";
        }
        leaf speaker-entity-id {
          xr:xr-xml-map "mpls_te_cfg:SpeakerEntityID";
          xr:xr-cli-map "traffic-eng pce node-identifier <string> ";
          type string {
            length "0..256";
          }
          description "PCE speaker entity identifier";
        }
        leaf segment-routing {
          xr:xr-xml-map "mpls_te_cfg:SegmentRouting";
          type empty;
          description "PCE segment routing capability";
        }
        uses PASSWORD;
        uses KEYCHAIN;
        uses PRECEDENCE;
      }

      container soft-preemption {
        xr:xr-xml-map "mpls_te_cfg:SoftPreemption";
        description "Soft preemption configuration data";
        leaf timeout {
          xr:xr-xml-map "mpls_te_cfg:Timeout";
          xr:xr-cli-map "traffic-eng soft-preemption timeout <numbe"+
            "r> ";
          type uint32 {
            range "1..300";
          }
          units "second";
          default "60";
          description
            "This object sets the timeout in seconds before
            hard preemption is triggered.";
        }
        leaf frr-rewrite {
          xr:xr-xml-map "mpls_te_cfg:FRRRewrite";
          xr:xr-cli-map "traffic-eng soft-preemption frr-rewrite ";
          type empty;
          description
            "This object controls whether FRR rewrite
            during soft preemption is enabled.";
        }
        leaf enable {
          xr:xr-xml-map "mpls_te_cfg:Enable";
          type boolean;
          description
            "This object controls whether soft preemption
            is enabled. This object must be set before
            setting any other objects under the
            SoftPreemption class.";
        }
      }

      container fast-reroute {
        xr:xr-xml-map "mpls_te_cfg:FastReroute";
        description "Configure fast reroute attributes";

        container timers {
          xr:xr-xml-map "mpls_te_cfg:Timers";
          description "Configure fast reroute timers";
          leaf hold-backup {
            xr:xr-xml-map "mpls_te_cfg:HoldBackup";
            xr:xr-cli-map "traffic-eng hold-backup <number> ";
            type uint32 {
              range "0..604800";
            }
            units "second";
            description
              "Seconds before backup declared UP (0 disables
              hold-timer)";
          }
          leaf promotion {
            xr:xr-xml-map "mpls_te_cfg:Promotion";
            xr:xr-cli-map "traffic-eng promotion <number> ";
            type uint32 {
              range "0..604800";
            }
            units "second";
            description
              "The value of the promotion timer in seconds";
          }
        }
      }

      container path-selection {
        xr:xr-xml-map "mpls_te_cfg:PathSelection";
        description "Path selection configuration";

        container loose-metrics {
          xr:xr-xml-map "mpls_te_cfg:LooseMetricClass";
          description
            "Path selection Loose ERO Metric Class
            configuration";

          list loose-metric {
            xr:xr-xml-map "mpls_te_cfg:LooseMetric";
            xr:xr-cli-map "traffic-eng path-selection loose-expansi"+
              "on metric (te)|(igp) [class-type <number>] ";
            key "class-type";
            description
              "Path selection Loose ERO Metric configuration";
            leaf class-type {
              xr:xr-xml-map "mpls_te_cfg:ClassType";
              type uint32 {
                range "0..7";
              }
              description "Path Selection class Type";
            }
            leaf metric-type {
              xr:xr-xml-map "mpls_te_cfg:MetricType";
              type Mpls-te-path-selection-metric;
              mandatory true;
              description "Metric to use for ERO Expansion";
            }
          }
        }

        container invalidation {
          xr:xr-xml-map "mpls_te_cfg:Invalidation";
          description
            "Path invalidation configuration for all
            tunnels";
          leaf path-invalidation-timeout {
            xr:xr-xml-map "mpls_te_cfg:PathInvalidationTimeout";
            type uint32 {
              range "0..60000";
            }
            description "Path Invalidation Timeout";
          }
          leaf path-invalidation-action {
            xr:xr-xml-map "mpls_te_cfg:PathInvalidationAction";
            type Path-invalidation-action;
            description "Path Invalidation Action";
          }
        }

        container ignore-overload-role {
          xr:xr-xml-map "mpls_te_cfg:IgnoreOverloadRole";
          description
            "Path selection to ignore overload node during
            CSPF";
          leaf head {
            xr:xr-xml-map "mpls_te_cfg:Head";
            type boolean;
            description
              "Set if the OL-bit is to be applied to tunnel
              heads";
          }
          leaf mid {
            xr:xr-xml-map "mpls_te_cfg:Mid";
            type boolean;
            description
              "Set if the OL-bit is to be applied to tunnel
              midpoints";
          }
          leaf tail {
            xr:xr-xml-map "mpls_te_cfg:Tail";
            type boolean;
            description
              "Set if the OL-bit is to be applied to tunnel
              tails";
          }
        }

        container loose-affinities {
          xr:xr-xml-map "mpls_te_cfg:LooseAffinityClass";
          description
            "Path selection Loose ERO Affinity Class
            configuration";

          list loose-affinity {
            xr:xr-xml-map "mpls_te_cfg:LooseAffinity";
            xr:xr-cli-map "traffic-eng path-selection loose-expansi"+
              "on affinity <number> mask <number> [class-type <numb"+
              "er>] ";
            key "class-type";
            description
              "Path selection Loose ERO Affinity
              configuration";
            leaf class-type {
              xr:xr-xml-map "mpls_te_cfg:ClassType";
              type uint32 {
                range "0..7";
              }
              description "Path Selection class Type";
            }
            leaf affinity {
              xr:xr-xml-map "mpls_te_cfg:Affinity";
              type xr:Hex-integer;
              description "Affinity flags";
            }
            leaf mask {
              xr:xr-xml-map "mpls_te_cfg:Mask";
              type xr:Hex-integer;
              description "Affinity mask";
            }
          }
        }
        leaf cost-limit {
          xr:xr-xml-map "mpls_te_cfg:CostLimit";
          xr:xr-cli-map "traffic-eng path-selection cost-limit <num"+
            "ber> ";
          type uint32 {
            range "1..4294967295";
          }
          description
            "Path selection cost limit configuration for
            all tunnels";
        }
        leaf tiebreaker {
          xr:xr-xml-map "mpls_te_cfg:Tiebreaker";
          xr:xr-cli-map "traffic-eng path-selection tiebreaker (min"+
            "-fill)|(max-fill)|(random) ";
          type Mpls-te-path-selection-tiebreaker;
          description "CSPF tiebreaker to use in path calculation";
        }
        leaf metric {
          xr:xr-xml-map "mpls_te_cfg:Metric";
          xr:xr-cli-map "traffic-eng path-selection metric (igp)|(t"+
            "e) ";
          type Mpls-te-path-selection-metric;
          description "Metric to use in path calculation";
        }
        leaf loose-domain-match {
          xr:xr-xml-map "mpls_te_cfg:LooseDomainMatch";
          xr:xr-cli-map "traffic-eng path-selection loose-expansion"+
            " domain-match ";
          type boolean;
          description
            "Use only the IGP instance of the incoming
            interface";
        }
      }

      container affinity-mappings {
        xr:xr-xml-map "mpls_te_cfg:AffinityMappingTable";
        description "Affinity Mapping Table configuration";

        list affinity-mapping {
          xr:xr-xml-map "mpls_te_cfg:AffinityMapping";
          xr:xr-cli-map "traffic-eng affinity-map <string> (<number"+
            ">)|(bit-position <number>) ";
          key "affinity-name";
          description "Affinity Mapping configuration";
          leaf affinity-name {
            xr:xr-xml-map "mpls_te_cfg:AffinityName";
            type xr:Cisco-ios-xr-string {
              length "0..32";
            }
            description "Affinity Name";
          }
          leaf value-type {
            xr:xr-xml-map "mpls_te_cfg:ValueType";
            type Mpls-te-affinity-value;
            description "Affinity value type";
          }
          leaf value {
            xr:xr-xml-map "mpls_te_cfg:Value";
            type xr:Hex-integer;
            description
              "Affinity Value in Hex number or by Bit
              position";
          }
        }
      }
      leaf log-nsr-status {
        xr:xr-xml-map "mpls_te_cfg:LogNSRStatus";
        type empty;
        description "Log NSR status messages";
      }
      leaf log-issu-status {
        xr:xr-xml-map "mpls_te_cfg:LogISSUStatus";
        type empty;
        description "Log ISSU status messages";
      }
      leaf reoptimize-link-up {
        xr:xr-xml-map "mpls_te_cfg:ReoptimizeLinkUp";
        xr:xr-cli-map "traffic-eng reoptimize events link-up ";
        type empty;
        description "Enable reoptimization based on link-up events";
      }
      leaf reoptimize-delay-cleanup-timer {
        xr:xr-xml-map "mpls_te_cfg:ReoptimizeDelayCleanupTimer";
        xr:xr-cli-map "traffic-eng reoptimize timers delay cleanup "+
          "<number> ";
        type uint32 {
          range "0..300";
        }
        units "second";
        description "Reoptimization Delay Cleanup Value (seconds)";
      }
      leaf disable-reoptimize-affinity-failure {
        xr:xr-xml-map "mpls_te_cfg:DisableReoptimizeAffinityFailure";
        xr:xr-cli-map "traffic-eng reoptimize disable affinity-fail"+
          "ure ";
        type empty;
        description
          "Disable reoptimization after affinity failures";
      }
      leaf maximum-tunnels {
        xr:xr-xml-map "mpls_te_cfg:MaximumTunnels";
        xr:xr-cli-map "traffic-eng maximum tunnels <number> ";
        type uint32 {
          range "1..65536";
        }
        default "4096";
        description
          "The maximum number of tunnel heads that will be
          allowed.";
      }
      leaf link-holddown-timer {
        xr:xr-xml-map "mpls_te_cfg:LinkHolddownTimer";
        xr:xr-cli-map "traffic-eng topology holddown sigerr <number"+
          "> ";
        type uint32 {
          range "0..300";
        }
        units "second";
        default "10";
        description
          "Holddown time for links which had Path Errors
          in seconds";
      }
      leaf fault-oam {
        xr:xr-xml-map "mpls_te_cfg:FaultOAM";
        xr:xr-cli-map "traffic-eng fault-oam ";
        type empty;
        description
          "Enable Fault-OAM functionality for
          bidirectional tunnels";
      }
      leaf enable-unequal-load-balancing {
        xr:xr-xml-map "mpls_te_cfg:EnableUnequalLoadBalancing";
        xr:xr-cli-map "traffic-eng load-share unequal ";
        type empty;
        description
          "Enable unequal load-balancing over tunnels to
          the same destination";
      }
      leaf log-tail {
        xr:xr-xml-map "mpls_te_cfg:LogTail";
        type empty;
        description "Log all tail tunnel events";
      }
      leaf reoptimize-delay-after-frr-timer {
        xr:xr-xml-map "mpls_te_cfg:ReoptimizeDelayAfterFRRTimer";
        xr:xr-cli-map "traffic-eng reoptimize timers delay after-fr"+
          "r <number> ";
        type uint32 {
          range "0..120";
        }
        units "second";
        description
          "Reoptimization Delay After FRR Value (seconds)";
      }
      leaf auto-bandwidth-collect-frequency {
        xr:xr-xml-map "mpls_te_cfg:AutoBandwidthCollectFrequency";
        xr:xr-cli-map "traffic-eng auto-bw collect frequency <numbe"+
          "r> ";
        type uint32 {
          range "1..10080";
        }
        units "minute";
        default "5";
        description
          "Auto-bandwidth global collection frequency in
          minutes";
      }
      leaf reopt-delay-path-protect-switchover-timer {
        xr:xr-xml-map "mpls_te_cfg:ReoptDelayPathProtectSwitchoverT"+
          "imer";
        xr:xr-cli-map "traffic-eng reoptimize timers delay path-pro"+
          "tection <number> ";
        type uint32 {
          range "0..604800";
        }
        units "second";
        default "180";
        description
          "Seconds between path protect switchover and
          tunnel re-optimization. Set to 0 to disable";
      }
      leaf log-all {
        xr:xr-xml-map "mpls_te_cfg:LogAll";
        type empty;
        description "Always set to true";
      }
      leaf loose-path-retry-period {
        xr:xr-xml-map "mpls_te_cfg:LoosePathRetryPeriod";
        xr:xr-cli-map "traffic-eng loose-path retry-period <number>"+
          " ";
        type uint32 {
          range "30..600";
        }
        default "120";
        description
          "Signalling retry for tunnels terminating
          outside the headend area";
      }
      leaf reoptimize-load-balancing {
        xr:xr-xml-map "mpls_te_cfg:ReoptimizeLoadBalancing";
        xr:xr-cli-map "traffic-eng reoptimize load-balance ";
        type empty;
        description "Load balance bandwidth during reoptimization";
      }
      leaf log-head {
        xr:xr-xml-map "mpls_te_cfg:LogHead";
        type empty;
        description "Log all head tunnel events";
      }
      leaf path-selection-ignore-overload {
        xr:xr-xml-map "mpls_te_cfg:PathSelectionIgnoreOverload";
        type empty;
        description "Deprecated - do not use";
      }
      leaf graceful-preemption-on-bandwidth-reduction {
        xr:xr-xml-map "mpls_te_cfg:GracefulPreemptionOnBandwidthRed"+
          "uction";
        xr:xr-cli-map "traffic-eng preemption-graceful bw-reduction"+
          " ";
        type empty;
        description
          "Enable graceful preemption when there is a
          bandwidth reduction";
      }
      leaf advertise-explicit-nulls {
        xr:xr-xml-map "mpls_te_cfg:AdvertiseExplicitNulls";
        type empty;
        description "Enable explicit-null advertising to PHOP";
      }
      leaf reoptimize-delay-install-timer {
        xr:xr-xml-map "mpls_te_cfg:ReoptimizeDelayInstallTimer";
        xr:xr-cli-map "traffic-eng reoptimize timers delay installa"+
          "tion <number> ";
        type uint32 {
          range "0..3600";
        }
        units "second";
        description "Reoptimization Delay Install Value (seconds)";
      }
      leaf reoptimize-delay-after-affinity-failure-timer {
        xr:xr-xml-map "mpls_te_cfg:ReoptimizeDelayAfterAffinityFail"+
          "ureTimer";
        xr:xr-cli-map "traffic-eng reoptimize timers delay after-af"+
          "finity-failure <number> ";
        type uint32 {
          range "1..604800";
        }
        units "second";
        description
          "Delay reoptimizing current LSP after affinity
          failures";
      }
      leaf log-frr-protection {
        xr:xr-xml-map "mpls_te_cfg:LogFRRProtection";
        type Mpls-te-log-frr-protection;
        description "Log FRR Protection messages";
      }
      leaf reoptimize-timer-frequency {
        xr:xr-xml-map "mpls_te_cfg:ReoptimizeTimerFrequency";
        xr:xr-cli-map "traffic-eng reoptimize <number> ";
        type uint32 {
          range "0..604800";
        }
        units "second";
        default "3600";
        description "Reoptimize timers period in seconds";
      }
      leaf log-mid {
        xr:xr-xml-map "mpls_te_cfg:LogMid";
        type empty;
        description "Log all mid tunnel events";
      }
      leaf log-preemption {
        xr:xr-xml-map "mpls_te_cfg:LogPreemption";
        type empty;
        description "Log tunnel preemption messages";
      }
    }

    container transport-profile {
      xr:xr-xml-map "mpls_te_tp_cfg:TransportProfile";
      description "MPLS transport profile configuration data";

      container fault {
        xr:xr-xml-map "mpls_te_tp_cfg:Fault";
        description "Fault management";

        container protection-trigger {
          xr:xr-xml-map "mpls_te_tp_cfg:ProtectionTrigger";
          description
            "OAM events that trigger protection switching";

          container ldi {
            xr:xr-xml-map "mpls_te_tp_cfg:LDI";
            description "Protection switching due to LDI event";
            leaf disable {
              xr:xr-xml-map "mpls_te_tp_cfg:Disable";
              xr:xr-cli-map "protection-trigger ldi disable ";
              type empty;
              description
                "Disable protection switching due to LDI
                event";
            }
          }

          container lkr {
            xr:xr-xml-map "mpls_te_tp_cfg:LKR";
            description "Protection switching due to LKR event";
            leaf disable {
              xr:xr-xml-map "mpls_te_tp_cfg:Disable";
              xr:xr-cli-map "protection-trigger lkr disable ";
              type empty;
              description
                "Disable protection switching due to LKR
                event";
            }
          }
          leaf ais {
            xr:xr-xml-map "mpls_te_tp_cfg:AIS";
            xr:xr-cli-map "protection-trigger ais ";
            type empty;
            description
              "Enable protection switching due to AIS event";
          }
        }
        leaf wait-to-restore-interval {
          xr:xr-xml-map "mpls_te_tp_cfg:WaitToRestoreInterval";
          xr:xr-cli-map "wait-to-restore interval <number> ";
          type uint32 {
            range "0..2147483647";
          }
          units "second";
          default "0";
          description "Waiting time before restoring working LSP";
        }
        leaf refresh-interval {
          xr:xr-xml-map "mpls_te_tp_cfg:RefreshInterval";
          xr:xr-cli-map "oam interval <number> ";
          type uint32 {
            range "1..20";
          }
          units "second";
          default "20";
          description
            "Periodic refresh interval for fault OAM
            messages";
        }
      }

      container alarm {
        xr:xr-xml-map "mpls_te_tp_cfg:Alarm";
        description "Alarm management";

        container suppress-event {
          xr:xr-xml-map "mpls_te_tp_cfg:SuppressEvent";
          description "Suppress all tunnel/LSP alarms";
          leaf disable {
            xr:xr-xml-map "mpls_te_tp_cfg:Disable";
            xr:xr-cli-map "suppression disable ";
            type empty;
            description "Disable alarm suppression";
          }
        }
        leaf soak-time {
          xr:xr-xml-map "mpls_te_tp_cfg:SoakTime";
          xr:xr-cli-map "soak-time <number> ";
          type uint32 {
            range "0..10";
          }
          units "second";
          default "3";
          description "Duration of soaking alarms";
        }
        leaf enable-alarm {
          xr:xr-xml-map "mpls_te_tp_cfg:EnableAlarm";
          type empty;
          description "Enable Transport Profile Alarm";
        }
      }

      container bfd {
        xr:xr-xml-map "mpls_te_tp_cfg:BFD";
        description "Configure BFD parameters";

        container min-interval-standby {
          xr:xr-xml-map "mpls_te_tp_cfg:MinIntervalStandby";
          description
            "Hello interval for standby transport profile
            LSPs, either in milli-seconds or in
            micro-seconds";
          leaf interval-standby-ms {
            xr:xr-xml-map "mpls_te_tp_cfg:IntervalStandbyMs";
            type uint32 {
              range "3..5000";
            }
            units "millisecond";
            description "Hello interval in milli-seconds";
          }
          leaf interval-standby-us {
            xr:xr-xml-map "mpls_te_tp_cfg:IntervalStandbyUs";
            type uint32 {
              range "3000..5000000";
            }
            units "microsecond";
            description "Hello interval in micro-seconds";
          }
        }

        container min-interval {
          xr:xr-xml-map "mpls_te_tp_cfg:MinInterval";
          description
            "Hello interval, either in milli-seconds or in
            micro-seconds";
          leaf interval-ms {
            xr:xr-xml-map "mpls_te_tp_cfg:IntervalMs";
            type uint32 {
              range "3..5000";
            }
            units "millisecond";
            description "Hello interval in milli-seconds";
          }
          leaf interval-us {
            xr:xr-xml-map "mpls_te_tp_cfg:IntervalUs";
            type uint32 {
              range "3000..5000000";
            }
            units "microsecond";
            description "Hello interval in micro-seconds";
          }
        }
        leaf detection-multiplier-standby {
          xr:xr-xml-map "mpls_te_tp_cfg:DetectionMultiplierStandby";
          xr:xr-cli-map "multiplier standby <number> ";
          type uint32 {
            range "2..10";
          }
          description
            "Detect multiplier for standby transport
            profile LSP";
        }
        leaf detection-multiplier {
          xr:xr-xml-map "mpls_te_tp_cfg:DetectionMultiplier";
          xr:xr-cli-map "multiplier <number> ";
          type uint32 {
            range "2..10";
          }
          description "Detect multiplier";
        }
      }

      container midpoints {
        xr:xr-xml-map "mpls_te_tp_cfg:MidpointTable";
        description "MPLS-TP tunnel mid-point table";

        list midpoint {
          xr:xr-xml-map "mpls_te_tp_cfg:Midpoint";
          key "midpoint-name";
          description "Transport profile mid-point identifier";

          container source {
            xr:xr-xml-map "mpls_te_tp_cfg:Source";
            presence "Indicates a source node is configured.";
            description
              "Node identifier, tunnel identifier and
              optional global identifier of the source of
              the LSP";
            leaf node-id {
              xr:xr-xml-map "mpls_te_tp_cfg:NodeID";
              type inet:ipv4-address-no-zone;
              description "Node identifier in IPv4 address format";
            }
            leaf tunnel-id {
              xr:xr-xml-map "mpls_te_tp_cfg:TunnelID";
              type uint32 {
                range "0..65535";
              }
              mandatory true;
              description "Tunnel identifier in numeric value";
            }
            leaf global-id {
              xr:xr-xml-map "mpls_te_tp_cfg:GlobalID";
              type uint32 {
                range "1..65535";
              }
              description "Global identifier in numeric value";
            }
          }

          container destination {
            xr:xr-xml-map "mpls_te_tp_cfg:Destination";
            presence "Indicates a destination node is configured.";
            description
              "Node identifier, tunnel identifier and
              optional global identifier of the destination
              of the LSP";
            leaf node-id {
              xr:xr-xml-map "mpls_te_tp_cfg:NodeID";
              type inet:ipv4-address-no-zone;
              description "Node identifier in IPv4 address format";
            }
            leaf tunnel-id {
              xr:xr-xml-map "mpls_te_tp_cfg:TunnelID";
              type uint32 {
                range "0..65535";
              }
              mandatory true;
              description "Tunnel identifier in numeric value";
            }
            leaf global-id {
              xr:xr-xml-map "mpls_te_tp_cfg:GlobalID";
              type uint32 {
                range "1..65535";
              }
              description "Global identifier in numeric value";
            }
          }

          container forward-lsp {
            xr:xr-xml-map "mpls_te_tp_cfg:ForwardLSP";
            description "Forward transport profile LSP";

            container forward-io-map {
              xr:xr-xml-map "mpls_te_tp_cfg:ForwardIOMap";
              presence "Indicates a forward-io-map node is"+
                " configured.";
              description
                "Label cross-connect of forward transport
                profile LSP";
              leaf in-label {
                xr:xr-xml-map "mpls_te_tp_cfg:InLabel";
                type uint32 {
                  range "16..4015";
                }
                description "MPLS label";
              }
              leaf out-label {
                xr:xr-xml-map "mpls_te_tp_cfg:OutLabel";
                type uint32 {
                  range "16..1048575";
                }
                mandatory true;
                description "Outgoing MPLS label";
              }
              leaf out-link {
                xr:xr-xml-map "mpls_te_tp_cfg:OutLink";
                type uint32 {
                  range "1..65535";
                }
                mandatory true;
                description
                  "Transport profile identifier of outgoing
                  link";
              }
            }
            leaf forward-bandwidth {
              xr:xr-xml-map "mpls_te_tp_cfg:ForwardBandwidth";
              xr:xr-cli-map "bandwidth <number> ";
              type uint32 {
                range "0..4294967295";
              }
              units "kbit/s";
              description
                "Bandwidth of forward transport profile LSP";
            }
          }

          container reverse-lsp {
            xr:xr-xml-map "mpls_te_tp_cfg:ReverseLSP";
            description "none";

            container reverse-io-map {
              xr:xr-xml-map "mpls_te_tp_cfg:ReverseIOMap";
              presence "Indicates a reverse-io-map node is"+
                " configured.";
              description
                "Label cross-connect of reverse transport
                profile LSP";
              leaf in-label {
                xr:xr-xml-map "mpls_te_tp_cfg:InLabel";
                type uint32 {
                  range "16..4015";
                }
                description "MPLS label";
              }
              leaf out-label {
                xr:xr-xml-map "mpls_te_tp_cfg:OutLabel";
                type uint32 {
                  range "16..1048575";
                }
                mandatory true;
                description "Outgoing MPLS label";
              }
              leaf out-link {
                xr:xr-xml-map "mpls_te_tp_cfg:OutLink";
                type uint32 {
                  range "1..65535";
                }
                mandatory true;
                description
                  "Transport profile identifier of outgoing
                  link";
              }
            }
            leaf reverse-bandwidth {
              xr:xr-xml-map "mpls_te_tp_cfg:ReverseBandwidth";
              xr:xr-cli-map "bandwidth <number> ";
              type uint32 {
                range "0..4294967295";
              }
              units "kbit/s";
              description
                "Bandwidth of reverse transport profile LSP";
            }
          }
          leaf tunnel-name {
            xr:xr-xml-map "mpls_te_tp_cfg:TunnelName";
            xr:xr-cli-map "traffic-eng tp mid <string> tunnel-name "+
              "<string> ";
            type string;
            description "Tunnel Name";
          }
          leaf lsp-protect {
            xr:xr-xml-map "mpls_te_tp_cfg:LSPProtect";
            xr:xr-cli-map "traffic-eng tp mid <string> fast-protect"+
              " ";
            type empty;
            description "Enable LSP protection";
          }
          leaf lsp-id {
            xr:xr-xml-map "mpls_te_tp_cfg:LSP_ID";
            xr:xr-cli-map "traffic-eng tp mid <string> lsp-number <"+
              "number> ";
            type uint32 {
              range "0..65535";
            }
            description "Numeric identifier";
          }
          leaf midpoint-name {
            xr:xr-xml-map "mpls_te_tp_cfg:MidpointName";
            type xr:Cisco-ios-xr-string {
              length "0..64";
            }
            description "Name of mid-point";
          }
        }
      }
      leaf global-id {
        xr:xr-xml-map "mpls_te_tp_cfg:GlobalID";
        xr:xr-cli-map "traffic-eng tp global-id <number> ";
        type uint32 {
          range "1..65535";
        }
        description "Transport profile global identifier";
      }
      leaf node-id {
        xr:xr-xml-map "mpls_te_tp_cfg:NodeID";
        xr:xr-cli-map "traffic-eng tp node-id <IPv4 address> ";
        type inet:ipv4-address-no-zone;
        description "Node identifier in IPv4 address format";
      }
    }

    container interfaces {
      xr:xr-xml-map "mpls_te_cfg:InterfaceTable";
      description "Configure MPLS TE interfaces";

      list interface {
        xr:xr-xml-map "mpls_te_cfg:Interface";
        key "interface-name";
        description "Configure an MPLS TE interface";

        container transport-profile-link {
          xr:xr-xml-map "mpls_te_tp_link_cfg:TransportProfileLink";
          description "MPLS transport profile capable link";

          container links {
            xr:xr-xml-map "mpls_te_tp_link_cfg:LinkTable";
            description "Transport profile link table";

            list link {
              xr:xr-xml-map "mpls_te_tp_link_cfg:Link";
              xr:xr-cli-map "traffic-eng interface <interface> tp l"+
                "ink <number> [next-hop ipv4 <IPv4 address>] ";
              key "link-id";
              description "Transport profile link";
              leaf link-id {
                xr:xr-xml-map "mpls_te_tp_link_cfg:LinkID";
                type uint32 {
                  range "1..65535";
                }
                description "Numeric link identifier";
              }
              leaf next-hop-type {
                xr:xr-xml-map "mpls_te_tp_link_cfg:NextHopType";
                type Link-next-hop;
                default "ipv4-address";
                description "Next hop type";
              }
              leaf next-hop-address {
                xr:xr-xml-map "mpls_te_tp_link_cfg:NextHopAddress";
                when "../next-hop-type = 'ipv4-address'" {
                  description "../NextHopType = IPV4Address";
                }
                type inet:ipv4-address-no-zone;
                description "Next-hop address in IPv4 format";
              }
            }
          }
        }

        container lcac {
          xr:xr-xml-map "mpls_lcac_interface_cfg:LCAC";
          description "LCAC specific MPLS interface configuration";

          container switchings {
            xr:xr-xml-map "mpls_lcac_interface_cfg:SwitchingTable";
            description "Set the te-link switching attributes";

            list switching {
              xr:xr-xml-map "mpls_lcac_interface_cfg:Switching";
              key "switching-id";
              description "The te-link switching attributes";
              leaf encoding {
                xr:xr-xml-map "mpls_lcac_interface_cfg:Encoding";
                type Mpls-te-switching-encoding;
                description "Set the local encoding type";
              }
              leaf capability {
                xr:xr-xml-map "mpls_lcac_interface_cfg:Capability";
                type Mpls-te-switching-cap;
                description "Set the local switching capability";
              }
              leaf switching-id {
                xr:xr-xml-map "mpls_lcac_interface_cfg:SwitchingID";
                type Mpls-te-switching-index;
                description "Switching index";
              }
            }
          }

          container flood-area {
            xr:xr-xml-map "mpls_lcac_interface_cfg:FloodArea";
            description
              "Set the IGP instance into which this
              interface is to be flooded (GMPLS only)";
            leaf igp-type {
              xr:xr-xml-map "mpls_lcac_interface_cfg:IGPType";
              type Mpls-lcac-flooding-igp;
              description "IGP type";
            }
            leaf process-name {
              xr:xr-xml-map "mpls_lcac_interface_cfg:ProcessName";
              type xr:Cisco-ios-xr-string {
                length "0..32";
              }
              description "Process name";
            }
            leaf area-id {
              xr:xr-xml-map "mpls_lcac_interface_cfg:AreaID";
              type int32;
              description "Area ID";
            }
          }

          container attribute-name-xr {
            xr:xr-xml-map "mpls_lcac_interface_cfg:AttributeNames";
            description "Set the interface attribute names";
            leaf-list attribute-name {
              xr:xr-xml-map "mpls_lcac_interface_cfg:Values";
              type string;
              max-elements "32";
              description "Array of Attribute Names";
            }
          }

          container attribute-names {
            xr:xr-xml-map "mpls_lcac_interface_cfg:AttributeNamesTa"+
              "ble";
            description "Attribute name table";

            list attribute-name {
              xr:xr-xml-map "mpls_lcac_interface_cfg:AttributeNames";
              key "affinity-index";
              description "Set the interface attribute names";
              leaf affinity-index {
                xr:xr-xml-map "mpls_lcac_interface_cfg:AffinityInde"+
                  "x";
                type uint32 {
                  range "1..9";
                }
                description "Specify the entry index";
              }
              leaf-list value {
                xr:xr-xml-map "mpls_lcac_interface_cfg:Values";
                type string;
                min-elements "1";
                max-elements "32";
                description "Array of Attribute Names";
              }
            }
          }

          container srlgs {
            xr:xr-xml-map "mpls_lcac_interface_cfg:SRLGTable";
            description
              "Configure SRLG membership for the interface";

            list srlg {
              xr:xr-xml-map "mpls_lcac_interface_cfg:SRLG";
              xr:xr-cli-map "traffic-eng interface <interface> srlg"+
                " <number> ";
              key "srlg-number";
              description "SRLG membership number";
              leaf srlg-number {
                xr:xr-xml-map "mpls_lcac_interface_cfg:SRLGNumber";
                type uint32 {
                  range "0..4294967295";
                }
                description "SRLG membership number";
              }
            }
          }

          container up-thresholds {
            xr:xr-xml-map "mpls_lcac_interface_cfg:UpThresholds";
            description
              "Set thresholds for increased resource
              availability in %";
            leaf-list up-threshold {
              xr:xr-xml-map "mpls_lcac_interface_cfg:Values";
              type Mpls-lcac-flooding-threshold-percent-range;
              units "percentage";
              max-elements "14";
              description "Array of up threshold percentage";
            }
          }

          container down-thresholds {
            xr:xr-xml-map "mpls_lcac_interface_cfg:DownThresholds";
            description
              "Set thresholds for decreased resource
              availability in %";
            leaf-list down-threshold {
              xr:xr-xml-map "mpls_lcac_interface_cfg:Values";
              type Mpls-lcac-flooding-threshold-percent-range;
              units "percentage";
              max-elements "14";
              description "Array of down threshold percentage";
            }
          }
          leaf bfd {
            xr:xr-xml-map "mpls_lcac_interface_cfg:BFD";
            xr:xr-cli-map "traffic-eng interface <interface> bfd fa"+
              "st-detect ";
            type empty;
            description
              "Enable use of Bidirectional Forwarding
              Detection";
          }
          leaf fault-oam-lockout {
            xr:xr-xml-map "mpls_lcac_interface_cfg:FaultOAMLockout";
            xr:xr-cli-map "traffic-eng interface <interface> fault-"+
              "oam lockout ";
            type empty;
            description
              "Lockout protection on the interface for Flex
              LSP";
          }
          leaf attribute-flags {
            xr:xr-xml-map "mpls_lcac_interface_cfg:AttributeFlags";
            xr:xr-cli-map "traffic-eng interface <interface> attrib"+
              "ute-flags <number> ";
            type xr:Hex-integer;
            description
              "Set user defined interface attribute flags";
          }
          leaf enable {
            xr:xr-xml-map "mpls_lcac_interface_cfg:Enable";
            type empty;
            description "Enable MPLS-TE on the link";
          }
          leaf admin-weight {
            xr:xr-xml-map "mpls_lcac_interface_cfg:AdminWeight";
            xr:xr-cli-map "traffic-eng interface <interface> admin-"+
              "weight <number> ";
            type int32;
            description
              "Set administrative weight for the interface";
          }
        }

        container global-attributes {
          xr:xr-xml-map "mpls_te_interface_cfg:GlobalAttributes";
          description "MPLS TE global interface configuration";

          container auto-tunnel {
            xr:xr-xml-map "mpls_te_interface_cfg:AutoTunnel";
            description "Auto tunnel configuration";

            container backup {
              xr:xr-xml-map "mpls_te_interface_cfg:Backup";
              description "Auto tunnel backup configuration";

              container exclude {
                xr:xr-xml-map "mpls_te_interface_cfg:Exclude";
                description "Auto-tunnel backup exclusion criteria";
                leaf srlg-mode {
                  xr:xr-xml-map "mpls_te_interface_cfg:SRLGMode";
                  xr:xr-cli-map "traffic-eng interface <interface> "+
                    "auto-tunnel backup exclude srlg [preferred|wei"+
                    "ghted] ";
                  type Mpls-tesrlg-exclude;
                  description
                    "Set exclude SRLG mode for auto-tunnel
                    backup on this TE link";
                }
              }
              leaf enable {
                xr:xr-xml-map "mpls_te_interface_cfg:Enable";
                type empty;
                description
                  "Enable auto-tunnel backup on this TE link";
              }
              leaf attribute-set {
                xr:xr-xml-map "mpls_te_interface_cfg:AttributeSet";
                type Attribute-set-name-length;
                description
                  "The name of attribute set to be applied to
                  this auto backup lsp";
              }
              leaf next-hop-only {
                xr:xr-xml-map "mpls_te_interface_cfg:NextHopOnly";
                xr:xr-cli-map "traffic-eng interface <interface> au"+
                  "to-tunnel backup nhop-only ";
                type empty;
                description
                  "Enable NHOP-only mode for auto-tunnel
                  backup on this TE link";
              }
            }
          }

          container backup-paths {
            xr:xr-xml-map "mpls_te_interface_cfg:BackupPathTable";
            description
              "Configure MPLS TE backup tunnels for this
              interface";

            list backup-path {
              xr:xr-xml-map "mpls_te_interface_cfg:BackupPath";
              xr:xr-cli-map "traffic-eng interface <interface> back"+
                "up-path tunnel-te <number> ";
              key "tunnel-number";
              description "Tunnel interface number";
              leaf tunnel-number {
                xr:xr-xml-map "mpls_te_interface_cfg:TunnelNumber";
                type uint32 {
                  range "0..65535";
                }
                description "Tunnel interface number";
              }
            }
          }
        }
        leaf interface-name {
          xr:xr-xml-map "mpls_te_cfg:InterfaceName";
          type xr:Interface-name;
          description "Interface name";
        }
      }
    }

    container gmpls-nni {
      xr:xr-xml-map "mpls_te_gmpls_nni_cfg:GMPLS_NNI";
      description "GMPLS-NNI configuration";

      container topology-instances {
        xr:xr-xml-map "mpls_te_gmpls_nni_cfg:TopologyInstanceTable";
        description "GMPLS-NNI topology instance table";

        list topology-instance {
          xr:xr-xml-map "mpls_te_gmpls_nni_cfg:TopologyInstance";
          must "ospf-int or ospfip-addr" {
            description "OSPFInt or OSPFIPAddr must be present.";
          }
          key "ospf-area-type igp-instance-name igp-type";
          description "GMPLS-NNI topology instance configuration";

          grouping TOPOLOGY-INSTANCE-CONTENT {
            description "TOPOLOGY INSTANCE CONTENT";

            container controllers {
              description "GMPLS-NNI controllers";

              list controller {
                xr:xr-xml-map "mpls_te_gmpls_nni_cfg:Controller";
                key "controller-name";
                description "Configure a GMPLS NNI controller";

                container tti-mode {
                  xr:xr-xml-map "mpls_te_gmpls_nni_cfg:TTI_Mode";
                  description
                    "Set tandem connection monitoring for the
                    interface";
                  leaf tti-mode-type {
                    xr:xr-xml-map "mpls_te_gmpls_nni_cfg:TTIModeTyp"+
                      "e";
                    type Gmplstti-mode;
                    description "Type of Trail Trace Identifier";
                  }
                  leaf tcmid {
                    xr:xr-xml-map "mpls_te_gmpls_nni_cfg:TCMID";
                    when "../tti-mode-type = 'tcm'" {
                      description "../TTIModeType = TCM";
                    }
                    type uint32 {
                      range "1..6";
                    }
                    description
                      "Tandem Connection Monitoring ID for the
                      interface";
                  }
                }
                leaf admin-weight {
                  xr:xr-xml-map "mpls_te_gmpls_nni_cfg:AdminWeight";
                  type uint32 {
                    range "0..65535";
                  }
                  description
                    "Set administrative weight for the
                    interface";
                }
                leaf enable {
                  xr:xr-xml-map "mpls_te_gmpls_nni_cfg:Enable";
                  type empty;
                  description "Enable GMPLS-NNI on the link";
                }
                leaf delay {
                  xr:xr-xml-map "mpls_te_gmpls_nni_cfg:Delay";
                  type uint32 {
                    range "1..16777215";
                  }
                  description "Set link delay for the interface";
                }
                leaf controller-name {
                  xr:xr-xml-map "mpls_te_gmpls_nni_cfg:ControllerNa"+
                    "me";
                  type xr:Interface-name;
                  description "Controller name";
                }
              }
            }
          }
          leaf igp-type {
            xr:xr-xml-map "mpls_te_gmpls_nni_cfg:IGPType";
            type Mpls-te-igp-protocol;
            description "IGP type";
          }
          leaf igp-instance-name {
            xr:xr-xml-map "mpls_te_gmpls_nni_cfg:IGPInstanceName";
            type xr:Cisco-ios-xr-string {
              length "0..40";
            }
            description "Name of IGP instance";
          }
          leaf ospf-area-type {
            xr:xr-xml-map "mpls_te_gmpls_nni_cfg:OSPFAreaType";
            type Ospf-area-mode;
            description "OSPF area format";
          }

          list ospf-int {
            xr:xr-xml-map "mpls_te_gmpls_nni_cfg:ControllerTable";
            when "../ospf-area-type = 'ospf-int'" {
              description "../OSPFAreaType = OSPFInt";
            }
            key "igp-area";
            description "ospf int";
            leaf igp-area {
              xr:xr-xml-map "mpls_te_gmpls_nni_cfg:IGPArea";
              type int32;
              description "IGP area";
            }
            uses TOPOLOGY-INSTANCE-CONTENT;
          }

          list ospfip-addr {
            xr:xr-xml-map "mpls_te_gmpls_nni_cfg:ControllerTable";
            when "../ospf-area-type = 'ospfip-addr'" {
              description "../OSPFAreaType = OSPFIPAddr";
            }
            key "address";
            description "ospfip addr";
            leaf address {
              xr:xr-xml-map "mpls_te_gmpls_nni_cfg:Address";
              type inet:ipv4-address-no-zone;
              description "Area ID if in IP address format";
            }
            uses TOPOLOGY-INSTANCE-CONTENT;
          }
        }
      }

      container tunnel-heads {
        xr:xr-xml-map "mpls_te_cfg_gmpls_nni_tunnel:TunnelHeadTable";
        description "GMPLS-NNI tunnel-head table";

        list tunnel-head {
          xr:xr-xml-map "mpls_te_cfg_gmpls_nni_tunnel:TunnelHead";
          key "tunnel-id";
          description
            "The configuration for a GMPLS NNI tunnel
            head-end";

          container signalled-bandwidth {
            xr:xr-xml-map "mpls_te_cfg_gmpls_nni_tunnel:SignalledBa"+
              "ndwidth";
            description
              "The existence of this configuration indicates
              the signalled bandwidth has been set for the
              tunnel";
            leaf signalled-bandwidth-type {
              xr:xr-xml-map "mpls_te_cfg_gmpls_nni_tunnel:Signalled"+
                "BandwidthType";
              type Otn-signaled-bandwidth;
              description "The g.709 signal type requested";
            }
            leaf bitrate {
              xr:xr-xml-map "mpls_te_cfg_gmpls_nni_tunnel:Bitrate";
              when "../signalled-bandwidth-type = 'od-uflex-cbr'"+
                " or ../signalled-bandwidth-type ="+
                " 'od-uflex-gfp-resize' or"+
                " ../signalled-bandwidth-type ="+
                " 'od-uflex-gfp-not-resize'" {
                  description
                    "../SignalledBandwidthType = ODUflexCBR or 
                    ../SignalledBandwidthType =
                    ODUflexGFPResize or .
                    ./SignalledBandwidthType =
                    ODUflexGFPNotResize";
              }
              type int32;
              units "kbit/s";
              description
                "Bitrate value in Kbps for ODUflex framing
                type";
            }
            leaf od-uflex-framing-type {
              xr:xr-xml-map "mpls_te_cfg_gmpls_nni_tunnel:ODUflexFr"+
                "amingType";
              when "../signalled-bandwidth-type = 'od-uflex-cbr'"+
                " or ../signalled-bandwidth-type ="+
                " 'od-uflex-gfp-resize' or"+
                " ../signalled-bandwidth-type ="+
                " 'od-uflex-gfp-not-resize'" {
                  description
                    "../SignalledBandwidthType = ODUflexCBR or 
                    ../SignalledBandwidthType =
                    ODUflexGFPResize or .
                    ./SignalledBandwidthType =
                    ODUflexGFPNotResize";
              }
              type Otn-signaled-bandwidth-flex-framing;
              description
                "Framing type in case of ODUflex signal type";
            }
          }

          container protection-switching {
            xr:xr-xml-map "mpls_te_cfg_gmpls_nni_tunnel:ProtectionS"+
              "witching";
            description
              "The configuration for a GMPLS NNI tunnel
              protection switch";
            leaf lockout {
              xr:xr-xml-map "mpls_te_cfg_gmpls_nni_tunnel:Lockout";
              xr:xr-cli-map "traffic-eng gmpls optical-nni controll"+
                "er Odu-Group-Te <number> protection-switching lock"+
                "out working ";
              type Otn-protection-switch-lockout;
              description
                "The configuration is used to prevent switch
                over for a particular path type in tunnel";
            }
          }

          container logging {
            xr:xr-xml-map "mpls_te_cfg_gmpls_nni_tunnel:Logging";
            description "Tunnel event logging";
            leaf active-lsp-message {
              xr:xr-xml-map "mpls_te_cfg_gmpls_nni_tunnel:ActiveLSP"+
                "Message";
              type empty;
              description
                "Log all tunnel messages for changes in
                Active LSP";
            }
            leaf homepath-state-message {
              xr:xr-xml-map "mpls_te_cfg_gmpls_nni_tunnel:HomepathS"+
                "tateMessage";
              type empty;
              description
                "Log all messages for changes in state of
                Homepath of Working LSP";
            }
            leaf signalling-state-message {
              xr:xr-xml-map "mpls_te_cfg_gmpls_nni_tunnel:Signallin"+
                "gStateMessage";
              type empty;
              description "Log all tunnel sub-LSP state messages";
            }
            leaf path-change-message {
              xr:xr-xml-map "mpls_te_cfg_gmpls_nni_tunnel:PathChang"+
                "eMessage";
              type empty;
              description
                "Log all tunnel messages for changes in
                path-change";
            }
            leaf static-cross-connect-message {
              xr:xr-xml-map "mpls_te_cfg_gmpls_nni_tunnel:StaticCro"+
                "ssConnectMessage";
              type empty;
              description
                "Log all tunnel messages for static
                cross-connect messages";
            }
            leaf insufficient-bw-message {
              xr:xr-xml-map "mpls_te_cfg_gmpls_nni_tunnel:Insuffici"+
                "entBWMessage";
              type empty;
              description
                "Log tunnel messages for insufficient
                bandwidth";
            }
          }

          container path-options {
            xr:xr-xml-map "mpls_te_cfg_gmpls_nni_tunnel:PathOptionT"+
              "able";
            description "GMPLS NNI path options";

            list path-option {
              xr:xr-xml-map "mpls_te_cfg_gmpls_nni_tunnel:PathOptio"+
                "n";
              xr:xr-cli-map "traffic-eng gmpls optical-nni controll"+
                "er Odu-Group-Te <number> path-option <number> (dyn"+
                "amic)|(explicit (identifier <number>)|(name <strin"+
                "g>)) [protected-by (<number>)|(none)] [restored-fr"+
                "om <number>] [xro-attribute-set <string>] [lockdow"+
                "n] ";
              key "preference-level";
              description
                "The existence of this configuration
                indicates the path options have been set for
                the tunnel";
              leaf preference-level {
                xr:xr-xml-map "mpls_te_cfg_gmpls_nni_tunnel:Prefere"+
                  "nceLevel";
                type uint32 {
                  range "1..1000";
                }
                description "Preference level for this path option";
              }
              leaf path-type {
                xr:xr-xml-map "mpls_te_cfg_gmpls_nni_tunnel:PathTyp"+
                  "e";
                type Mpls-te-path-option;
                description "The type of the path option";
              }
              leaf path-id {
                xr:xr-xml-map "mpls_te_cfg_gmpls_nni_tunnel:PathID";
                type uint32 {
                  range "1..65535";
                }
                description
                  "The ID of the IP explicit path associated
                  with this option";
              }
              leaf path-name {
                xr:xr-xml-map "mpls_te_cfg_gmpls_nni_tunnel:PathNam"+
                  "e";
                type string;
                description
                  "The name of the IP explicit path associated
                  with this option";
              }
              leaf protected-by-preference-level {
                xr:xr-xml-map "mpls_te_cfg_gmpls_nni_tunnel:Protect"+
                  "edByPreferenceLevel";
                type uint32 {
                  range "1..1001";
                }
                description
                  "Preference level of the protecting explicit
                  path. ";
              }
              leaf restore-by-preference-level {
                xr:xr-xml-map "mpls_te_cfg_gmpls_nni_tunnel:Restore"+
                  "ByPreferenceLevel";
                type uint32 {
                  range "1..1000";
                }
                description
                  "Preference level of the restore path. ";
              }
              leaf xro-type {
                xr:xr-xml-map "mpls_te_cfg_gmpls_nni_tunnel:XROType";
                type Mpls-te-path-option-xro;
                mandatory true;
                description "The route-exclusion type";
              }
              leaf xro-attribute-set-name {
                xr:xr-xml-map "mpls_te_cfg_gmpls_nni_tunnel:XROAttr"+
                  "ibuteSetName";
                type Attribute-set-name-length;
                description
                  "The name of the XRO attribute set to be
                  used for this path-option";
              }
              leaf lockdown {
                xr:xr-xml-map "mpls_te_cfg_gmpls_nni_tunnel:Lockdow"+
                  "n";
                type Mpls-te-path-option-property;
                description "Lockdown properties";
              }
            }
          }

          container static-uni {
            xr:xr-xml-map "mpls_te_cfg_gmpls_nni_tunnel:StaticUNI";
            description
              "The existence of this configuration indicates
              the static UNI endpoints have been set for
              the tunnel";
            leaf ingress-controller-name {
              xr:xr-xml-map "mpls_te_cfg_gmpls_nni_tunnel:IngressCo"+
                "ntrollerName";
              type xr:Cisco-ios-xr-string {
                length "0..255";
              }
              description "Name of  ingress controller";
            }
            leaf egress-controller-if-index {
              xr:xr-xml-map "mpls_te_cfg_gmpls_nni_tunnel:EgressCon"+
                "trollerIFIndex";
              type int32;
              description "Interface index of Egress controller";
            }
          }
          leaf enable {
            xr:xr-xml-map "mpls_te_cfg_gmpls_nni_tunnel:Enable";
            type empty;
            description
              "The existence of this configuration indicates
              the a new GMPLS NNI tunnel has been enabled";
          }
          leaf restore-lsp-shutdown {
            xr:xr-xml-map "mpls_te_cfg_gmpls_nni_tunnel:RestoreLSPS"+
              "hutdown";
            xr:xr-cli-map "traffic-eng gmpls optical-nni controller"+
              " Odu-Group-Te <number> Lsp-type Restore ";
            type empty;
            description
              "The existence of this configuration indicates
              the restore LSP of tunnel is shutdown";
          }
          leaf destination {
            xr:xr-xml-map "mpls_te_cfg_gmpls_nni_tunnel:Destination";
            xr:xr-cli-map "traffic-eng gmpls optical-nni controller"+
              " Odu-Group-Te <number> destination ipv4 unicast <IPv"+
              "4 address> ";
            type inet:ipv4-address-no-zone;
            description
              "The existence of this configuration indicates
              the destination has been set for the tunnel";
          }
          leaf current-lsp-shutdown {
            xr:xr-xml-map "mpls_te_cfg_gmpls_nni_tunnel:CurrentLSPS"+
              "hutdown";
            xr:xr-cli-map "traffic-eng gmpls optical-nni controller"+
              " Odu-Group-Te <number> Lsp-type Current ";
            type empty;
            description
              "The existence of this configuration indicates
              the current/working LSP of tunnel is shutdown";
          }
          leaf path-selection-metric {
            xr:xr-xml-map "mpls_te_cfg_gmpls_nni_tunnel:PathSelecti"+
              "onMetric";
            xr:xr-cli-map "traffic-eng gmpls optical-nni controller"+
              " Odu-Group-Te <number> path-selection metric (te-met"+
              "ric)|(delay) ";
            type Mpls-te-path-selection-metric;
            description
              "Path selection configuration for this
              specific tunnel";
          }
          leaf payload {
            xr:xr-xml-map "mpls_te_cfg_gmpls_nni_tunnel:Payload";
            xr:xr-cli-map "traffic-eng gmpls optical-nni controller"+
              " Odu-Group-Te <number> payload <enum> ";
            type Otn-payload;
            description
              "The existence of this configuration indicates
              the Payload type have been set for the tunnel";
          }
          leaf standby-lsp-shutdown {
            xr:xr-xml-map "mpls_te_cfg_gmpls_nni_tunnel:StandbyLSPS"+
              "hutdown";
            xr:xr-cli-map "traffic-eng gmpls optical-nni controller"+
              " Odu-Group-Te <number> Lsp-type Standby ";
            type empty;
            description
              "The existence of this configuration indicates
              the standby/protect LSP of tunnel is shutdown";
          }
          leaf shutdown {
            xr:xr-xml-map "mpls_te_cfg_gmpls_nni_tunnel:Shutdown";
            type empty;
            description
              "The existence of this configuration indicates
              the tunnel is shutdown";
          }
          leaf path-protection-attribute-set-profile {
            xr:xr-xml-map "mpls_te_cfg_gmpls_nni_tunnel:PathProtect"+
              "ionAttributeSetProfile";
            xr:xr-cli-map "traffic-eng gmpls optical-nni controller"+
              " Odu-Group-Te <number> path-protection attribute-set"+
              " <string> ";
            type xr:Cisco-ios-xr-string {
              length "0..64";
            }
            description
              "The name of the path-protection profile to be
              included in signalling messages";
          }
          leaf tunnel-id {
            xr:xr-xml-map "mpls_te_cfg_gmpls_nni_tunnel:TunnelID";
            type uint32 {
              range "0..65535";
            }
            description "Tunnel ID";
          }
          uses RECORD-ROUTE;
          uses SIGNALLED-NAME;
        }
      }
      leaf path-selection-metric {
        xr:xr-xml-map "mpls_te_gmpls_nni_cfg:PathSelectionMetric";
        xr:xr-cli-map "traffic-eng gmpls optical-nni path-selection"+
          " metric (te-metric)|(delay) ";
        type Mpls-te-path-selection-metric;
        description
          "Path selection configuration for all gmpls nni
          tunnels";
      }
      leaf enable-gmpls-nni {
        xr:xr-xml-map "mpls_te_gmpls_nni_cfg:EnableGMPLS_NNI";
        type empty;
        description "Enable MPLS Traffic Engineering GMPLS-NNI";
      }
    }

    container lcac {
      xr:xr-xml-map "mpls_lcac_cfg:LCAC";
      description "LCAC specific MPLS global configuration";

      container bfd {
        xr:xr-xml-map "mpls_lcac_cfg:BFD";
        description "BFD configuration";
        leaf interval {
          xr:xr-xml-map "mpls_lcac_cfg:Interval";
          xr:xr-cli-map "traffic-eng bfd minimum-interval <number> ";
          type uint32 {
            range "15..200";
          }
          units "millisecond";
          description
            "Hello interval for BFD sessions created by TE";
        }
        leaf detection-multiplier {
          xr:xr-xml-map "mpls_lcac_cfg:DetectionMultiplier";
          xr:xr-cli-map "traffic-eng bfd multiplier <number> ";
          type uint32 {
            range "2..10";
          }
          description
            "Detection multiplier for BFD sessions created
            by TE";
        }
      }

      container flooding-threshold {
        xr:xr-xml-map "mpls_lcac_cfg:FloodingThreshold";
        description
          "Configure flooding threshold as percentage of
          total link bandwidth.";
        leaf up-stream {
          xr:xr-xml-map "mpls_lcac_cfg:UpStream";
          type Mpls-flooding-threshold-percent-range;
          units "percentage";
          description
            "Upward flooding Threshold in percentages of
            total bandwidth";
        }
        leaf down-stream {
          xr:xr-xml-map "mpls_lcac_cfg:DownStream";
          type Mpls-flooding-threshold-percent-range;
          units "percentage";
          description
            "Downward flooding Threshold in percentages of
            total bandwidth";
        }
      }
      leaf bandwidth-hold-timer {
        xr:xr-xml-map "mpls_lcac_cfg:BandwidthHoldTimer";
        xr:xr-cli-map "traffic-eng link-management timers bandwidth"+
          "-hold <number> ";
        type Mpls-lcac-bandwidth-hold-timer-range;
        units "second";
        description "Bandwidth hold timer value (seconds)";
      }
      leaf delay-preempt-bundle-capacity-timer {
        xr:xr-xml-map "mpls_lcac_cfg:DelayPreemptBundleCapacityTime"+
          "r";
        xr:xr-cli-map "traffic-eng link-management timers preemptio"+
          "n-delay bundle-capacity <number> ";
        type uint32 {
          range "0..300";
        }
        units "second";
        description
          "Bundle capacity preemption timer value
          (seconds)";
      }
      leaf periodic-flooding-timer {
        xr:xr-xml-map "mpls_lcac_cfg:PeriodicFloodingTimer";
        xr:xr-cli-map "traffic-eng link-management timers periodic-"+
          "flooding <number> ";
        type uint32 {
          range "0..3600";
        }
        units "second";
        description "Periodic flooding value (seconds)";
      }
    }
    leaf enable-traffic-engineering {
      xr:xr-xml-map "mpls_te_cfg:EnableTrafficEngineering";
      type empty;
      description "Enable MPLS Traffic Engineering";
    }
  }

  augment "/a1:interface-configurations/a1:interface-configuration" {

    container tunnel-te-attributes {
      xr:xr-xml-map "mpls_te_tunnel_cfg:TunnelTEAttributes";
      description "MPLS tunnel attributes";

      container backup-bandwidth {
        xr:xr-xml-map "mpls_te_tunnel_cfg:BackupBandwidth";
        description "Tunnel backup bandwidth requirement";
        leaf dste-type {
          xr:xr-xml-map "mpls_te_tunnel_cfg:DSTEType";
          type Mpls-te-bandwidth-dste;
          description "DSTE-standard flag";
        }
        leaf pool-type {
          xr:xr-xml-map "mpls_te_tunnel_cfg:PoolType";
          type Mpls-te-backup-bandwidth-pool;
          description
            "Backup bandwidth pool type, relevant only if
            DSTEType is PreStandardDSTE";
        }
        leaf class-type {
          xr:xr-xml-map "mpls_te_tunnel_cfg:ClassType";
          type Mpls-te-backup-bandwidth-class;
          description
            "Backup bandwidth class type, relevant only if
            DSTEType is StandardDSTE";
        }
        leaf limit-type {
          xr:xr-xml-map "mpls_te_tunnel_cfg:LimitType";
          type Mpls-te-bandwidth-limit;
          description "Backup bandwidth limit type";
        }
        leaf backup-bandwidth {
          xr:xr-xml-map "mpls_te_tunnel_cfg:BackupBandwidth";
          type uint32 {
            range "1..4294967295";
          }
          description
            "Backup bandwidth requested by this tunnel in
            kbps. Ignored if bandwidth limit type is
            unlimited.";
        }
      }

      container bfd-over-lsp {
        xr:xr-xml-map "mpls_te_tunnel_cfg:BFDOverLSP";
        description "BFD over TE LSP";
        leaf dampening-initial-wait {
          xr:xr-xml-map "mpls_te_tunnel_cfg:DampeningInitialWait";
          type uint32 {
            range "1..518400000";
          }
          description
            "Initial delay in milliseconds (default 16000)";
        }
        leaf fast-detect {
          xr:xr-xml-map "mpls_te_tunnel_cfg:FastDetect";
          type empty;
          description "Enable BFD Fast Detect On the tunnel";
        }
        leaf enable {
          xr:xr-xml-map "mpls_te_tunnel_cfg:Enable";
          type empty;
          description "Always set to true";
        }
        leaf multiplier {
          xr:xr-xml-map "mpls_te_tunnel_cfg:Multiplier";
          type uint32 {
            range "3..10";
          }
          description
            "Specify the multiplier for BFD failure
            detection";
        }
        leaf bringup-timeout {
          xr:xr-xml-map "mpls_te_tunnel_cfg:BringupTimeout";
          type uint32 {
            range "60..3600";
          }
          description
            "Wait for session to come up in seconds
            (default 60)";
        }
        leaf periodic-ping-disable {
          xr:xr-xml-map "mpls_te_tunnel_cfg:PeriodicPingDisable";
          type empty;
          description "Disable Periodic LSP Ping for BFD over LSP";
        }
        leaf dampening-secondary-wait {
          xr:xr-xml-map "mpls_te_tunnel_cfg:DampeningSecondaryWait";
          type uint32 {
            range "1..518400000";
          }
          description
            "Secondary delay in milliseconds (default
            20000)";
        }
        leaf periodic-ping-interval {
          xr:xr-xml-map "mpls_te_tunnel_cfg:PeriodicPingInterval";
          type uint32 {
            range "60..3600";
          }
          description
            "Periodic LSP Ping Interval in seconds (default
            120)";
        }
        leaf dampening-maximum-wait {
          xr:xr-xml-map "mpls_te_tunnel_cfg:DampeningMaximumWait";
          type uint32 {
            range "1..518400000";
          }
          description
            "Maximum delay in milliseconds (default 600000)";
        }
        leaf minimum-interval {
          xr:xr-xml-map "mpls_te_tunnel_cfg:MinimumInterval";
          type uint32 {
            range "3..30000";
          }
          description
            "Specify the minimum interval for BFD failure
            detection";
        }
        leaf encap-mode {
          xr:xr-xml-map "mpls_te_tunnel_cfg:EncapMode";
          type uint32 {
            range "0..1";
          }
          description "Specify BFD Encap Mode on the tunnel";
        }
      }

      container binding-segment-id-mpls {
        xr:xr-xml-map "mpls_te_tunnel_cfg:BindingSegmentID_MPLS";
        description "Allocate MPLS binding segment ID";
        leaf segment-id-type {
          xr:xr-xml-map "mpls_te_tunnel_cfg:SegmentIDType";
          type Binding-segment-id;
          description "MPLS label value type";
        }
        leaf label-value {
          xr:xr-xml-map "mpls_te_tunnel_cfg:LabelValue";
          when "../segment-id-type = 'specified-label'" {
            description "../SegmentIDType = SpecifiedLabel";
          }
          type uint32 {
            range "16..4015";
          }
          description "MPLS label";
        }
      }

      container forwarding-adjacency {
        xr:xr-xml-map "mpls_te_tunnel_cfg:ForwardingAdjacency";
        description "Forwarding adjacency announcement to IGP";
        leaf enable {
          xr:xr-xml-map "mpls_te_tunnel_cfg:Enable";
          type empty;
          description "Enable forwarding adjacency";
        }
        leaf include-ipv6 {
          xr:xr-xml-map "mpls_te_tunnel_cfg:IncludeIPv6";
          type empty;
          description
            "Specify that the tunnel should be an IPv6
            forwarding adjacency also";
        }
        leaf hold-time {
          xr:xr-xml-map "mpls_te_tunnel_cfg:HoldTime";
          type uint32 {
            range "0..20000";
          }
          description
            "Specify the holdtime for the tunnel as
            forwarding adjacency";
        }
      }

      container path-option-protects {
        xr:xr-xml-map "mpls_te_tunnel_cfg:PathOptionProtectTable";
        description "Tunnel path protection state";

        list path-option-protect {
          xr:xr-xml-map "mpls_te_tunnel_cfg:PathOptionProtect";
          key "protection";
          description "Tunnel path protection";

          container path-options {
            xr:xr-xml-map "mpls_te_tunnel_cfg:PathOptionTable";
            description "Tunnel path options";

            list path-option {
              xr:xr-xml-map "mpls_te_tunnel_cfg:PathOption";
              key "preference-level";
              description "A tunnel path option";
              leaf preference-level {
                xr:xr-xml-map "mpls_te_tunnel_cfg:PreferenceLevel";
                type uint32 {
                  range "1..1000";
                }
                description "Preference level for this path option";
              }
              leaf path-type {
                xr:xr-xml-map "mpls_te_tunnel_cfg:PathType";
                type Mpls-te-path-option;
                mandatory true;
                description "The type of the path option";
              }
              leaf path-id {
                xr:xr-xml-map "mpls_te_tunnel_cfg:PathID";
                type uint32 {
                  range "1..65535";
                }
                default "1";
                description
                  "The ID of the IP explicit path associated
                  with this option";
              }
              leaf path-name {
                xr:xr-xml-map "mpls_te_tunnel_cfg:PathName";
                type string;
                description
                  "The name of the IP explicit path associated
                  with this option";
              }
              leaf path-property {
                xr:xr-xml-map "mpls_te_tunnel_cfg:PathProperty";
                type int32;
                default "0";
                description "Deprecated";
              }
              leaf interface {
                xr:xr-xml-map "mpls_te_tunnel_cfg:Interface";
                type xr:Interface-name;
                description "Deprecated";
              }
              leaf output-label {
                xr:xr-xml-map "mpls_te_tunnel_cfg:OutputLabel";
                type int32;
                default "0";
                description "Deprecated";
              }
              leaf destination {
                xr:xr-xml-map "mpls_te_tunnel_cfg:Destination";
                type inet:ipv4-address-no-zone;
                default "0.0.0.0";
                description "Deprecated";
              }
              leaf lockdown {
                xr:xr-xml-map "mpls_te_tunnel_cfg:Lockdown";
                type Mpls-te-path-option-property;
                default "none";
                description "Lockdown properties";
              }
              leaf verbatim {
                xr:xr-xml-map "mpls_te_tunnel_cfg:Verbatim";
                type Mpls-te-path-option-property;
                default "none";
                description "Verbatim properties";
              }
              leaf pce {
                xr:xr-xml-map "mpls_te_tunnel_cfg:PCE";
                type Mpls-te-path-option-property;
                default "none";
                description "PCE properties";
              }
              leaf pce-address {
                xr:xr-xml-map "mpls_te_tunnel_cfg:PCEAddress";
                type inet:ipv4-address-no-zone;
                default "0.0.0.0";
                description "PCE address";
              }
              leaf igp-type {
                xr:xr-xml-map "mpls_te_tunnel_cfg:IGPType";
                type Mpls-te-igp-protocol;
                default "none";
                description "IGP type";
              }
              leaf igp-instance {
                xr:xr-xml-map "mpls_te_tunnel_cfg:IGPInstance";
                type string {
                  length "0..40";
                }
                description "IGP instance name";
              }
              leaf igp-area {
                xr:xr-xml-map "mpls_te_tunnel_cfg:IGPArea";
                type int32;
                default "0";
                description "IGP area ID in integer format";
              }
              leaf igp-area-ip-address-id {
                xr:xr-xml-map "mpls_te_tunnel_cfg:IGPAreaIPAddressI"+
                  "D";
                type inet:ipv4-address-no-zone;
                default "0.0.0.0";
                description "IGP area ID in IP address format";
              }
              leaf path-option-attribute-set-name {
                xr:xr-xml-map "mpls_te_tunnel_cfg:PathOptionAttribu"+
                  "teSetName";
                type string;
                description "Path option attribute set name";
              }
              leaf protected-by-preference-level {
                xr:xr-xml-map "mpls_te_tunnel_cfg:ProtectedByPrefer"+
                  "enceLevel";
                type uint32 {
                  range "1..1000";
                }
                default "1";
                description
                  "Preference level of the protecting explicit
                  path. Leave unset in order to not use an
                  explicit protecting path";
              }
              leaf segment-routing {
                xr:xr-xml-map "mpls_te_tunnel_cfg:SegmentRouting";
                type Mpls-te-path-option-property;
                default "none";
                description "SegmentRouting properties";
              }
            }
          }
          leaf protection {
            xr:xr-xml-map "mpls_te_tunnel_cfg:Protection";
            type Mpls-te-path-option-protection;
            description "Protection type for this path";
          }
        }
      }

      container bidirectional {
        xr:xr-xml-map "mpls_te_tunnel_cfg:Bidirectional";
        description
          "Tunnel Interface Bidirectional configuration
          data";

        container association-corouted-type {
          xr:xr-xml-map "mpls_te_tunnel_cfg:AssociationCoroutedType";
          description "Association Corouted Type";

          container fault-oam {
            xr:xr-xml-map "mpls_te_tunnel_cfg:FaultOAM";
            description "Tunnel Fault OAM";
            leaf enable {
              xr:xr-xml-map "mpls_te_tunnel_cfg:Enable";
              type empty;
              description
                "This object is only valid for bidirectional
                tunnel interfaces and it controls whether
                that interface has fault OAM enabled on it
                or not.";
            }
          }
          leaf wrap-protection-enable {
            xr:xr-xml-map "mpls_te_tunnel_cfg:WrapProtectionEnable";
            type empty;
            description
              "This object is only valid for bidirectional
              tunnel interfaces and it controls whether
              that interface has LSP Wrap protectionenabled
              on it or not.";
          }
          leaf enable {
            xr:xr-xml-map "mpls_te_tunnel_cfg:Enable";
            type empty;
            description
              "Controls whether association type is
              co-routed.";
          }
        }

        container association-parameters {
          xr:xr-xml-map "mpls_te_tunnel_cfg:AssociationParameters";
          presence "Indicates a association-parameters node is"+
            " configured.";
          description
            "Association ID, Source IP Address, and Global
            ID";
          leaf association-id {
            xr:xr-xml-map "mpls_te_tunnel_cfg:AssociationID";
            type uint32 {
              range "0..65535";
            }
            mandatory true;
            description "Association ID";
          }
          leaf association-source-address {
            xr:xr-xml-map "mpls_te_tunnel_cfg:AssociationSourceAddr"+
              "ess";
            type inet:ipv4-address-no-zone;
            mandatory true;
            description "Association Source IP Address";
          }
          leaf association-is-global-id-configured {
            xr:xr-xml-map "mpls_te_tunnel_cfg:AssociationIsGlobalID"+
              "Configured";
            type boolean;
            description "Is Association Global ID Configured";
          }
          leaf association-global-id {
            xr:xr-xml-map "mpls_te_tunnel_cfg:AssociationGlobalID";
            type uint32 {
              range "0..4294967295";
            }
            description "Association Global ID";
          }
        }
        leaf enabled {
          xr:xr-xml-map "mpls_te_tunnel_cfg:Enabled";
          type empty;
          description
            "This object is only valid for tunnel
            interfaces and it controls whether that
            interface has bidirectional enabled on it or
            not.";
        }
      }

      container admin-mode {
        xr:xr-xml-map "mpls_te_tunnel_cfg:AdminMode";
        description
          "Performs admin operations on the optical tunnel
          interface";
        leaf deactivate-tunnel {
          xr:xr-xml-map "mpls_te_tunnel_cfg:DeactivateTunnel";
          type empty;
          description
            "Performs signalling operation to deactivate
            optical tunnel";
        }
      }

      container switching {
        xr:xr-xml-map "mpls_te_tunnel_cfg:Switching";
        description
          "Specify tunnel LSPs switching capability
          descriptor";

        container transit {
          xr:xr-xml-map "mpls_te_tunnel_cfg:Transit";
          presence "Indicates a transit node is configured.";
          description
            "Specify transit switching descriptor
            parameters";
          leaf capability {
            xr:xr-xml-map "mpls_te_tunnel_cfg:Capability";
            type Mpls-te-switching-cap;
            mandatory true;
            description "Switching capability";
          }
          leaf encoding {
            xr:xr-xml-map "mpls_te_tunnel_cfg:Encoding";
            type Mpls-te-switching-encode;
            description "LSP encoding";
          }
        }

        container endpoint {
          xr:xr-xml-map "mpls_te_tunnel_cfg:Endpoint";
          presence "Indicates a endpoint node is configured.";
          description
            "Specify end point switching descriptor
            parameters";
          leaf capability {
            xr:xr-xml-map "mpls_te_tunnel_cfg:Capability";
            type Mpls-te-switching-cap;
            mandatory true;
            description "Switching capability";
          }
          leaf encoding {
            xr:xr-xml-map "mpls_te_tunnel_cfg:Encoding";
            type Mpls-te-switching-encode;
            description "LSP encoding";
          }
        }
      }

      container pce {
        xr:xr-xml-map "mpls_te_tunnel_cfg:PCE";
        description "PCE config";
        leaf enable {
          xr:xr-xml-map "mpls_te_tunnel_cfg:Enable";
          type empty;
          description "Always set to true";
        }
        leaf delegation {
          xr:xr-xml-map "mpls_te_tunnel_cfg:Delegation";
          type empty;
          description "Enable PCE Delegation";
        }
      }
      leaf path-protection {
        xr:xr-xml-map "mpls_te_tunnel_cfg:PathProtection";
        type empty;
        description "Specify MPLS tunnel to be path protected";
      }
      uses FORWARD-CLASS;
      uses TUNNEL-PATH-SELECTION;
      uses AUTO-BANDWIDTH;
      uses PRIORITY;
      uses DESTINATION;
      uses RECORD-ROUTE;
      uses AFFINITY-MASK;
      uses BANDWIDTH;
      uses AUTOROUTE;
      uses POLICY-CLASSES;
      uses PATH-SELECTION-METRIC;
      uses NEW-STYLE-AFFINITY-TABLE;
      uses SOFT-PREEMPTION;
      uses FAST-REROUTE;
      uses LOAD-SHARE;
      uses SIGNALLED-NAME;
    }
    description
      "This augment extends the configuration data of
      'Cisco-IOS-XR-ifmgr-cfg'";
  }

  augment "/a1:interface-configurations/a1:interface-configuration" {

    container transport-profile-tunnel {
      xr:xr-xml-map "mpls_te_tp_tunnel_cfg:TransportProfileTunnel";
      description "MPLS-TP tunnel attributes";

      container bfd {
        xr:xr-xml-map "mpls_te_tp_tunnel_cfg:BFD";
        description "Configure BFD parameters";

        container min-interval {
          xr:xr-xml-map "mpls_te_tp_tunnel_cfg:MinInterval";
          description
            "Hello interval, either in milli-seconds or in
            micro-seconds";
          leaf interval-ms {
            xr:xr-xml-map "mpls_te_tp_tunnel_cfg:IntervalMs";
            type uint32 {
              range "3..5000";
            }
            description "Hello interval in milli-seconds";
          }
          leaf interval-us {
            xr:xr-xml-map "mpls_te_tp_tunnel_cfg:IntervalUs";
            type uint32 {
              range "3000..5000000";
            }
            description "Hello interval in micro-seconds";
          }
        }

        container min-interval-standby {
          xr:xr-xml-map "mpls_te_tp_tunnel_cfg:MinIntervalStandby";
          description
            "Hello interval for standby transport profile
            LSP, either in milli-seconds or in
            micro-seconds";
          leaf interval-standby-ms {
            xr:xr-xml-map "mpls_te_tp_tunnel_cfg:IntervalStandbyMs";
            type uint32 {
              range "3..5000";
            }
            description "Hello interval in milli-seconds";
          }
          leaf interval-standby-us {
            xr:xr-xml-map "mpls_te_tp_tunnel_cfg:IntervalStandbyUs";
            type uint32 {
              range "3000..5000000";
            }
            description "Hello interval in micro-seconds";
          }
        }
        leaf detection-multiplier {
          xr:xr-xml-map "mpls_te_tp_tunnel_cfg:DetectionMultiplier";
          type uint32 {
            range "2..10";
          }
          description "Detect multiplier";
        }
        leaf enable {
          xr:xr-xml-map "mpls_te_tp_tunnel_cfg:Enable";
          type empty;
          description "Configure BFD parameters";
        }
        leaf multiplier-standby {
          xr:xr-xml-map "mpls_te_tp_tunnel_cfg:MultiplierStandby";
          type uint32 {
            range "2..10";
          }
          description
            "Detect multiplier for standby transport
            profile LSP";
        }
      }

      container working-lsp {
        xr:xr-xml-map "mpls_te_tp_tunnel_cfg:WorkingLSP";
        description "Working LSP";

        container out-label {
          xr:xr-xml-map "mpls_te_tp_tunnel_cfg:OutLabel";
          presence "Indicates a out-label node is configured.";
          description "Outgoing MPLS label of the working LSP";
          leaf label {
            xr:xr-xml-map "mpls_te_tp_tunnel_cfg:Label";
            type uint32 {
              range "16..1048575";
            }
            description "MPLS label";
          }
          leaf link {
            xr:xr-xml-map "mpls_te_tp_tunnel_cfg:Link";
            type uint32 {
              range "1..65535";
            }
            mandatory true;
            description
              "Transport profile identifier of outgoing link";
          }
        }
        leaf in-label {
          xr:xr-xml-map "mpls_te_tp_tunnel_cfg:InLabel";
          type uint32 {
            range "16..4015";
          }
          description "Incoming MPLS label of the working LSP";
        }
        leaf lockout {
          xr:xr-xml-map "mpls_te_tp_tunnel_cfg:Lockout";
          type empty;
          description "Enable lockout of working LSP";
        }
        leaf lsp-id {
          xr:xr-xml-map "mpls_te_tp_tunnel_cfg:LSP_ID";
          type uint32 {
            range "0..65535";
          }
          default "0";
          description "LSP Identifier of the working LSP";
        }
      }

      container destination {
        xr:xr-xml-map "mpls_te_tp_tunnel_cfg:Destination";
        description
          "Node identifier and optional global identifier
          and tunnel identifier at destination";
        leaf node-id {
          xr:xr-xml-map "mpls_te_tp_tunnel_cfg:NodeID";
          type inet:ipv4-address-no-zone;
          description "Node identifier in IPv4 address format";
        }
        leaf global-id {
          xr:xr-xml-map "mpls_te_tp_tunnel_cfg:GlobalID";
          type uint32 {
            range "1..65535";
          }
          description "Numeric global identifier";
        }
        leaf tunnel-id {
          xr:xr-xml-map "mpls_te_tp_tunnel_cfg:TunnelID";
          type uint32 {
            range "0..65535";
          }
          description "Numeric tunnel identifier";
        }
      }

      container fault {
        xr:xr-xml-map "mpls_te_tp_tunnel_cfg:Fault";
        description "Fault management";

        container protection-trigger {
          xr:xr-xml-map "mpls_te_tp_tunnel_cfg:ProtectionTrigger";
          description
            "OAM events that trigger protection switching";
          leaf ldi {
            xr:xr-xml-map "mpls_te_tp_tunnel_cfg:LDI";
            type boolean;
            description
              "Enable protection switching due to LDI event";
          }
          leaf ais {
            xr:xr-xml-map "mpls_te_tp_tunnel_cfg:AIS";
            type boolean;
            description
              "Enable protection switching due to AIS event";
          }
          leaf lkr {
            xr:xr-xml-map "mpls_te_tp_tunnel_cfg:LKR";
            type boolean;
            description
              "Enable protection switching due to LKR event";
          }
        }
        leaf enable {
          xr:xr-xml-map "mpls_te_tp_tunnel_cfg:Enable";
          type empty;
          description
            "Enter transport profile tunnel fault
            configuration";
        }
      }

      container protect-lsp {
        xr:xr-xml-map "mpls_te_tp_tunnel_cfg:ProtectLSP";
        description "Protect LSP";

        container out-label {
          xr:xr-xml-map "mpls_te_tp_tunnel_cfg:OutLabel";
          presence "Indicates a out-label node is configured.";
          description "Outgoing MPLS label of the protect LSP";
          leaf label {
            xr:xr-xml-map "mpls_te_tp_tunnel_cfg:Label";
            type uint32 {
              range "16..1048575";
            }
            description "MPLS label";
          }
          leaf link {
            xr:xr-xml-map "mpls_te_tp_tunnel_cfg:Link";
            type uint32 {
              range "1..65535";
            }
            mandatory true;
            description
              "Transport profile identifier of outgoing link";
          }
        }
        leaf in-label {
          xr:xr-xml-map "mpls_te_tp_tunnel_cfg:InLabel";
          type uint32 {
            range "16..4015";
          }
          description "Incoming MPLS label of the protect LSP";
        }
        leaf lockout {
          xr:xr-xml-map "mpls_te_tp_tunnel_cfg:Lockout";
          type empty;
          description "Enable lockout of protect LSP";
        }
        leaf lsp-id {
          xr:xr-xml-map "mpls_te_tp_tunnel_cfg:LSP_ID";
          type uint32 {
            range "0..65535";
          }
          default "1";
          description "LSP Identifier of the protect LSP";
        }
      }
      leaf source {
        xr:xr-xml-map "mpls_te_tp_tunnel_cfg:Source";
        type inet:ipv4-address-no-zone;
        description
          "Transport profile node identifier in IPv4
          address format";
      }
    }
    description
      "This augment extends the configuration data of
      'Cisco-IOS-XR-ifmgr-cfg'";
  }

  augment "/a1:interface-configurations/a1:interface-configuration" {

    container mte-tunnel-attributes {
      xr:xr-xml-map "mpls_mte_tunnel_cfg:MTETunnelAttributes";
      description "MPLS P2MP tunnel attributes";

      container destination-leafs {
        xr:xr-xml-map "mpls_mte_tunnel_cfg:DestinationTable";
        description "P2MP destination table";

        list destination-leaf {
          xr:xr-xml-map "mpls_mte_tunnel_cfg:DestinationLeaf";
          key "address";
          description "P2MP destination leaf";

          container s2l-logging {
            xr:xr-xml-map "mpls_mte_tunnel_cfg:S2lLogging";
            description "Log tunnel destination s2l messages";
            leaf s2l-reroute-messsage {
              xr:xr-xml-map "mpls_mte_tunnel_cfg:S2lRerouteMesssage";
              type empty;
              description
                "Log tunnel destination s2l rereoute messages";
            }
            leaf s2l-insufficient-bw-messsage {
              xr:xr-xml-map "mpls_mte_tunnel_cfg:S2lInsufficientBWM"+
                "esssage";
              type empty;
              description
                "Log tunnel destination s2l insufficient BW
                messages";
            }
            leaf s2l-pcalc-failure-message {
              xr:xr-xml-map "mpls_mte_tunnel_cfg:S2lPCALCFailureMes"+
                "sage";
              type empty;
              description
                "Enable logging for destination s2l
                path-calculation failures";
            }
            leaf s2l-state-message {
              xr:xr-xml-map "mpls_mte_tunnel_cfg:S2lStateMessage";
              type empty;
              description
                "Log tunnel destination s2l state messages";
            }
          }

          container path-options {
            xr:xr-xml-map "mpls_mte_tunnel_cfg:PathOptionTable";
            description
              "P2MP destination path-options attributes
              table";

            list path-option {
              xr:xr-xml-map "mpls_mte_tunnel_cfg:PathOption";
              key "preference-level";
              description "P2MP destination path option";
              leaf preference-level {
                xr:xr-xml-map "mpls_mte_tunnel_cfg:PreferenceLevel";
                type uint32 {
                  range "1..1000";
                }
                description "Preference level for this path option";
              }
              leaf path-type {
                xr:xr-xml-map "mpls_mte_tunnel_cfg:PathType";
                type Mpls-te-path-option;
                description "The type of the path option";
              }
              leaf path-id {
                xr:xr-xml-map "mpls_mte_tunnel_cfg:PathID";
                type uint32 {
                  range "1..65535";
                }
                description
                  "The ID of the IP explicit path associated
                  with this option";
              }
              leaf path-name {
                xr:xr-xml-map "mpls_mte_tunnel_cfg:PathName";
                type string;
                description
                  "The name of the IP explicit path associated
                  with this option";
              }
              leaf lockdown {
                xr:xr-xml-map "mpls_mte_tunnel_cfg:Lockdown";
                type Mpls-te-path-option-property;
                description "Path option properties";
              }
              leaf verbatim {
                xr:xr-xml-map "mpls_mte_tunnel_cfg:Verbatim";
                type Mpls-te-path-option-property;
                description "Path option properties";
              }
            }
          }
          leaf destination-disable {
            xr:xr-xml-map "mpls_mte_tunnel_cfg:DestinationDisable";
            type empty;
            description "Disables P2MP destination";
          }
          leaf destination {
            xr:xr-xml-map "mpls_mte_tunnel_cfg:Destination";
            type empty;
            description "Always set to true";
          }
          leaf address {
            xr:xr-xml-map "mpls_mte_tunnel_cfg:address";
            type inet:ipv4-address-no-zone;
            description "Address of P2MP destination";
          }
        }
      }

      container priority {
        xr:xr-xml-map "mpls_mte_tunnel_cfg:Priority";
        description "P2MP tunnel setup and hold priorities";
        leaf setup-priority {
          xr:xr-xml-map "mpls_mte_tunnel_cfg:SetupPriority";
          type uint32 {
            range "0..7";
          }
          description "Setup Priority";
        }
        leaf hold-priority {
          xr:xr-xml-map "mpls_mte_tunnel_cfg:HoldPriority";
          type uint32 {
            range "0..7";
          }
          description "Hold Priority";
        }
      }

      container new-style-affinities {
        xr:xr-xml-map "mpls_mte_tunnel_cfg:NewStyleAffinityTable";
        description
          "P2MP tunnel new style affinity attributes table";

        list new-style-affinity {
          xr:xr-xml-map "mpls_mte_tunnel_cfg:NewStyleAffinity";
          key "affinity-type affinity1 affinity2 affinity3"+
            " affinity4 affinity5 affinity6 affinity7 affinity8"+
            " affinity9 affinity10";
          description "Tunnel new style affinity attribute";
          leaf affinity-type {
            xr:xr-xml-map "mpls_mte_tunnel_cfg:AffinityType";
            type Mpls-te-tunnel-affinity;
            description "The type of the affinity entry";
          }
          leaf affinity1 {
            xr:xr-xml-map "mpls_mte_tunnel_cfg:Affinity1";
            type xr:Cisco-ios-xr-string;
            description "The name of the first affinity";
          }
          leaf affinity2 {
            xr:xr-xml-map "mpls_mte_tunnel_cfg:Affinity2";
            type xr:Cisco-ios-xr-string;
            description "The name of the second affinity";
          }
          leaf affinity3 {
            xr:xr-xml-map "mpls_mte_tunnel_cfg:Affinity3";
            type xr:Cisco-ios-xr-string;
            description "The name of the third affinity";
          }
          leaf affinity4 {
            xr:xr-xml-map "mpls_mte_tunnel_cfg:Affinity4";
            type xr:Cisco-ios-xr-string;
            description "The name of the fourth affinity";
          }
          leaf affinity5 {
            xr:xr-xml-map "mpls_mte_tunnel_cfg:Affinity5";
            type xr:Cisco-ios-xr-string;
            description "The name of the fifth affinity";
          }
          leaf affinity6 {
            xr:xr-xml-map "mpls_mte_tunnel_cfg:Affinity6";
            type xr:Cisco-ios-xr-string;
            description "The name of the sixth affinity";
          }
          leaf affinity7 {
            xr:xr-xml-map "mpls_mte_tunnel_cfg:Affinity7";
            type xr:Cisco-ios-xr-string;
            description "The name of the seventh affinity";
          }
          leaf affinity8 {
            xr:xr-xml-map "mpls_mte_tunnel_cfg:Affinity8";
            type xr:Cisco-ios-xr-string;
            description "The name of the eighth affinity";
          }
          leaf affinity9 {
            xr:xr-xml-map "mpls_mte_tunnel_cfg:Affinity9";
            type xr:Cisco-ios-xr-string;
            description "The name of the nineth affinity";
          }
          leaf affinity10 {
            xr:xr-xml-map "mpls_mte_tunnel_cfg:Affinity10";
            type xr:Cisco-ios-xr-string;
            description "The name of the tenth affinity";
          }
        }
      }

      container bandwidth {
        xr:xr-xml-map "mpls_mte_tunnel_cfg:Bandwidth";
        description "P2MP tunnel bandwidth requirement";
        leaf dste-type {
          xr:xr-xml-map "mpls_mte_tunnel_cfg:DSTEType";
          type Mpls-te-bandwidth-dste;
          description "DSTE-standard flag";
        }
        leaf class-or-pool-type {
          xr:xr-xml-map "mpls_mte_tunnel_cfg:ClassOrPoolType";
          type uint32 {
            range "0..1";
          }
          description "Class type for the bandwith allocation";
        }
        leaf bandwidth {
          xr:xr-xml-map "mpls_mte_tunnel_cfg:Bandwidth";
          type uint32 {
            range "0..4294967295";
          }
          description
            "The value of the bandwidth reserved by this
            tunnel in kbps";
        }
      }

      container affinity-mask {
        xr:xr-xml-map "mpls_mte_tunnel_cfg:AffinityMask";
        description "P2MP tunnel affinity and mask";
        leaf affinity {
          xr:xr-xml-map "mpls_mte_tunnel_cfg:Affinity";
          type xr:Hex-integer;
          description "Affinity flags";
        }
        leaf mask {
          xr:xr-xml-map "mpls_mte_tunnel_cfg:Mask";
          type xr:Hex-integer;
          description "Affinity mask";
        }
      }
      leaf record-route {
        xr:xr-xml-map "mpls_mte_tunnel_cfg:RecordRoute";
        type empty;
        description "Record route used by individual P2MP S2L(s)";
      }
      leaf signalled-name {
        xr:xr-xml-map "mpls_mte_tunnel_cfg:SignalledName";
        type xr:Cisco-ios-xr-string {
          length "0..254";
        }
        description
          "The name of the P2MP tunnel to be included in
          signalling messages";
      }
      leaf path-selection-metric {
        xr:xr-xml-map "mpls_mte_tunnel_cfg:PathSelectionMetric";
        type Mpls-te-path-selection-metric;
        description
          "Path selection configuration for this specific
          tunnel";
      }
      leaf signalled-payload {
        xr:xr-xml-map "mpls_mte_tunnel_cfg:SignalledPayload";
        type xr:Hex-integer;
        description "P2MP tunnel ipv6 signalled payload";
      }
      leaf fast-reroute {
        xr:xr-xml-map "mpls_mte_tunnel_cfg:FastReroute";
        type empty;
        description "Specify P2MP tunnel can be fast-rerouted";
      }
      leaf impose-explicit-null {
        xr:xr-xml-map "mpls_mte_tunnel_cfg:ImposeExplicitNull";
        type empty;
        description "Impose an explicit null bellow the TE label";
      }
      uses LOGGING;
    }
    description
      "This augment extends the configuration data of
      'Cisco-IOS-XR-ifmgr-cfg'";
  }

  augment "/a2:mib" {

    container mpls-te-mib {
      xr:xr-xml-map "mpls_temib_cfg:MPLS_TE_MIB";
      description "MPLS TE MIB configuration";
      leaf cache-garbage-collect-timer {
        xr:xr-xml-map "mpls_temib_cfg:CacheGarbageCollectTimer";
        type uint32 {
          range "0..3600";
        }
        units "second";
        default "1800";
        description
          "Configure the cache garbage collector time for
          the mib.";
      }
      uses CACHE-TIMER;
    }
    description
      "This augment extends the configuration data of
      'Cisco-IOS-XR-snmp-agent-cfg'";
  }

  augment "/a2:mib" {

    container mpls-p2mp-mib {
      xr:xr-xml-map "mpls_temib_cfg:MPLS_P2MP_MIB";
      description "MPLS P2MP MIB configuration";
      uses CACHE-TIMER;
    }
    description
      "This augment extends the configuration data of
      'Cisco-IOS-XR-snmp-agent-cfg'";
  }

  augment "/a2:mib" {

    container mpls-te-ext-std-mib {
      xr:xr-xml-map "mpls_temib_cfg:MPLS_TE_EXT_STD_MIB";
      description "MPLS TE EXT STD MIB configuration";
      uses CACHE-TIMER;
    }
    description
      "This augment extends the configuration data of
      'Cisco-IOS-XR-snmp-agent-cfg'";
  }

  augment "/a2:mib" {

    container mpls-te-ext-mib {
      xr:xr-xml-map "mpls_temib_cfg:MPLS_TE_EXT_MIB";
      description "MPLS TE EXT MIB configuration";
      uses CACHE-TIMER;
    }
    description
      "This augment extends the configuration data of
      'Cisco-IOS-XR-snmp-agent-cfg'";
  }

  augment "/a2:mib" {

    container mpls-frr-mib {
      xr:xr-xml-map "mpls_temib_cfg:MPLS_FRR_MIB";
      description "FRR MIB configuration";
      uses CACHE-TIMER;
    }
    description
      "This augment extends the configuration data of
      'Cisco-IOS-XR-snmp-agent-cfg'";
  }

  augment "/a2:snmp/a2:notification" {

    container mpls-te-p2mp {
      xr:xr-xml-map "mpls_temib_cfg:MPLS_TE_P2MP";
      description
        "CISCO-MPLS-TE-P2MP-STD-MIB notification
        configuration";
      leaf up {
        xr:xr-xml-map "mpls_temib_cfg:Up";
        type empty;
        description "Enable cmplsTeP2mpTunnelDestUp notification";
      }
      leaf down {
        xr:xr-xml-map "mpls_temib_cfg:Down";
        type empty;
        description "Enable cmplsTeP2mpTunnelDestDown notification";
      }
    }
    description
      "This augment extends the configuration data of
      'Cisco-IOS-XR-snmp-agent-cfg'";
  }

  augment "/a2:snmp/a2:notification" {

    container mpls-te {
      xr:xr-xml-map "mpls_temib_cfg:MPLS_TE";
      description "MPLS-TE-STD-MIB notification configuration";

      container cisco-extension {
        xr:xr-xml-map "mpls_temib_cfg:CiscoExtension";
        description
          "CISCO-MPLS-TE-STD-EXT-MIB notification
          configuration";
        leaf preempt {
          xr:xr-xml-map "mpls_temib_cfg:Preempt";
          type empty;
          description "Enable cmplsTunnelPreempt notification";
        }
        leaf insufficient-bandwidth {
          xr:xr-xml-map "mpls_temib_cfg:InsufficientBandwidth";
          type empty;
          description "Enable cmplsTunnelInsuffBW notification";
        }
        leaf re-route-pending-clear {
          xr:xr-xml-map "mpls_temib_cfg:ReRoutePendingClear";
          type empty;
          description
            "Enable cmplsTunnelReRoutePendingClear
            notification";
        }
        leaf bringup-fail {
          xr:xr-xml-map "mpls_temib_cfg:BringupFail";
          type empty;
          description "Enable cmplsTunnelBringupFail notification";
        }
        leaf re-route-pending {
          xr:xr-xml-map "mpls_temib_cfg:ReRoutePending";
          type empty;
          description
            "Enable cmplsTunnelReRoutePending notification";
        }
      }
      leaf cisco {
        xr:xr-xml-map "mpls_temib_cfg:Cisco";
        type empty;
        description
          "Enable MPLS TE tunnel Cisco format (default
          IETF) notification";
      }
      leaf up {
        xr:xr-xml-map "mpls_temib_cfg:Up";
        type empty;
        description "Enable mplsTunnelUp notification";
      }
      leaf reoptimize {
        xr:xr-xml-map "mpls_temib_cfg:Reoptimize";
        type empty;
        description "Enable mplsTunnelReoptimized notification";
      }
      leaf reroute {
        xr:xr-xml-map "mpls_temib_cfg:Reroute";
        type empty;
        description "Enable mplsTunnelRerouted notification";
      }
      leaf down {
        xr:xr-xml-map "mpls_temib_cfg:Down";
        type empty;
        description "Enable mplsTunnelDown notification";
      }
    }
    description
      "This augment extends the configuration data of
      'Cisco-IOS-XR-snmp-agent-cfg'";
  }

  augment "/a2:snmp/a2:notification" {

    container mpls-frr {
      xr:xr-xml-map "mpls_temib_cfg:MPLS_FRR";
      description "CISCO-IETF-FRR-MIB notification configuration";
      leaf unprotected {
        xr:xr-xml-map "mpls_temib_cfg:Unprotected";
        type empty;
        description "Enable cmplsFrrUnProtected notification";
      }
      leaf enable {
        xr:xr-xml-map "mpls_temib_cfg:Enable";
        type empty;
        description "Enable cmplsFrrMIB notifications";
      }
      leaf protected {
        xr:xr-xml-map "mpls_temib_cfg:Protected";
        type empty;
        description "Enable cmplsFrrProtected notification";
      }
    }
    description
      "This augment extends the configuration data of
      'Cisco-IOS-XR-snmp-agent-cfg'";
  }
}
