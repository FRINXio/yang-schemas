module Cisco-IOS-XR-ipv6-ma-cfg {

  /*** NAMESPACE / PREFIX DEFINITION ***/

  namespace "http://cisco.com/ns/yang/Cisco-IOS-XR-ipv6-ma-cfg";


  prefix "ipv6-ma-cfg";

  /*** LINKAGE (IMPORTS / INCLUDES) ***/

  import ietf-inet-types { prefix "inet"; }

  import Cisco-IOS-XR-types { prefix "xr"; }

  import Cisco-IOS-XR-ip-iarm-datatypes { prefix "dt1"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-ma package configuration.

     This YANG module augments the
       Cisco-IOS-XR-ifmgr-cfg
     module with configuration data.

     Copyright (c) 2013-2015 by Cisco Systems, Inc.
     All rights reserved.";

  revision "2015-07-30" {
    description
      "Descriptions updated.";
  }

  revision "2015-01-07" {
    description
      "IOS XR 5.3.1 revision.";
  }

  typedef Ipv6-self-ping {
    type enumeration {
      enum disabled {
        value 0;
        description "Doesn't allow router to ping itself";
      }
      enum enabled {
        value 1;
        description "Allow router to ping itself";
      }
    }
    description "Ipv6 self ping";
  }
  typedef Ipv6-reachable {
    type enumeration {
      enum any {
        value 0;
        description "Source is reachable via any interface";
      }
      enum received {
        value 1;
        description
          "Source is reachable via interface on which
          packet was received";
      }
    }
    description "Ipv6 reachable";
  }
  typedef Ipv6-default-ping {
    type enumeration {
      enum disabled {
        value 0;
        description
          "Default route is not allowed to match when
          checking source address";
      }
      enum enabled {
        value 1;
        description
          "Allow default route to match when checking
          source address";
      }
    }
    description "Ipv6 default ping";
  }
  typedef Ipv6-qppb {
    type enumeration {
      enum none {
        value 0;
        description "No QPPB configuration";
      }
      enum ip-precedence {
        value 1;
        description "Enable ip-precedence based QPPB";
      }
      enum qos-group {
        value 2;
        description "Enable qos-group based QPPB";
      }
      enum both {
        value 3;
        description
          "Enable both ip-precedence and qos-group based
          QPPB";
      }
    }
    description "Ipv6 qppb";
  }

  augment "/a1:interface-configurations/a1:interface-configuration" {

    container ipv6-network {
      xr:xr-xml-map "ipv6_ma_cfg:IPV6Network";
      description "Interface IPv6 Network configuration data";

      container bgp-qos-policy-propagation {
        xr:xr-xml-map "ipv6_ma_cfg:BGP_QOSPolicyPropagation";
        presence "Indicates a bgp-qos-policy-propagation node is"+
          " configured.";
        description "Configure BGP QoS policy propagation";
        leaf source {
          xr:xr-xml-map "ipv6_ma_cfg:Source";
          type Ipv6-qppb;
          mandatory true;
          description "QPPB configuration on source";
        }
        leaf destination {
          xr:xr-xml-map "ipv6_ma_cfg:Destination";
          type Ipv6-qppb;
          mandatory true;
          description "QPPB configuration on destination";
        }
      }

      container bgp-policy-accountings {
        xr:xr-xml-map "ipv6_ma_cfg:BGPPolicyAccountingTable";
        description "IPv6 BGP Policy Accounting";

        list bgp-policy-accounting {
          xr:xr-xml-map "ipv6_ma_cfg:BGPPolicyAccounting";
          key "direction";
          description "Accounting input or output";
          leaf direction {
            xr:xr-xml-map "ipv6_ma_cfg:Direction";
            type xr:Cisco-ios-xr-string;
            description "Accouting on input or output";
          }
          leaf destination-accounting {
            xr:xr-xml-map "ipv6_ma_cfg:DestinationAccounting";
            type boolean;
            mandatory true;
            description "Accounting on Destination IP Address";
          }
          leaf source-accounting {
            xr:xr-xml-map "ipv6_ma_cfg:SourceAccounting";
            type boolean;
            mandatory true;
            description "Accounting on Source IP Address";
          }
        }
      }

      container mac-address-filters {
        xr:xr-xml-map "ipv6_ma_cfg:MACAddressFilterTable";
        description "IPv6 Mac-Filter for a multicast address";

        list mac-address-filter {
          xr:xr-xml-map "ipv6_ma_cfg:MACAddressFilter";
          key "multicast-address";
          description
            "Allow IPv6 Mac-Filter for a multicast address";
          leaf multicast-address {
            xr:xr-xml-map "ipv6_ma_cfg:MulticastAddress";
            type inet:ipv6-address-no-zone;
            description "Multicast Address";
          }
        }
      }

      container verify {
        xr:xr-xml-map "ipv6_ma_cfg:Verify";
        presence "Indicates a verify node is configured.";
        description "IPv6 Verify Unicast Souce Reachable";
        leaf reachable {
          xr:xr-xml-map "ipv6_ma_cfg:Reachable";
          type Ipv6-reachable;
          mandatory true;
          description "Source Reachable Interface";
        }
        leaf self-ping {
          xr:xr-xml-map "ipv6_ma_cfg:SelfPing";
          type Ipv6-self-ping;
          mandatory true;
          description "Allow Self Ping";
        }
        leaf default-ping {
          xr:xr-xml-map "ipv6_ma_cfg:DefaultPing";
          type Ipv6-default-ping;
          mandatory true;
          description "Allow Default Route";
        }
      }

      container addresses {
        xr:xr-xml-map "ipv6_ma_cfg:Addresses";
        description "Set the IPv6 address of an interface";

        container link-local-address {
          xr:xr-xml-map "ipv6_ma_cfg:LinkLocalAddress";
          presence "Indicates a link-local-address node is"+
            " configured.";
          description "Link local IPv6 address";
          leaf address {
            xr:xr-xml-map "ipv6_ma_cfg:Address";
            type inet:ip-address-no-zone;
            mandatory true;
            description "IPv6 address";
          }
          leaf zone {
            xr:xr-xml-map "ipv6_ma_cfg:Zone";
            type string;
            default "0";
            description "IPv6 address zone";
          }
          leaf route-tag {
            xr:xr-xml-map "ipv6_ma_cfg:RouteTag";
            type uint32 {
              range "1..4294967295";
            }
            description "RouteTag";
          }
        }

        container eui64-addresses {
          xr:xr-xml-map "ipv6_ma_cfg:EUI64AddressTable";
          description "EUI-64 IPv6 address Table";

          list eui64-address {
            xr:xr-xml-map "ipv6_ma_cfg:EUI64Address";
            key "address";
            description "EUI-64 IPv6 address";
            leaf address {
              xr:xr-xml-map "ipv6_ma_cfg:Address";
              type inet:ip-address-no-zone;
              description "IPv6 address";
            }
            leaf prefix-length {
              xr:xr-xml-map "ipv6_ma_cfg:PrefixLength";
              type dt1:Ipv6arm-prefix-length;
              mandatory true;
              description "Prefix Length";
            }
            leaf zone {
              xr:xr-xml-map "ipv6_ma_cfg:Zone";
              type string;
              default "0";
              description "IPv6 address zone";
            }
            leaf route-tag {
              xr:xr-xml-map "ipv6_ma_cfg:RouteTag";
              type uint32 {
                range "1..4294967295";
              }
              description "RouteTag";
            }
          }
        }

        container regular-addresses {
          xr:xr-xml-map "ipv6_ma_cfg:RegularAddressTable";
          description "Regular IPv6 address Table";

          list regular-address {
            xr:xr-xml-map "ipv6_ma_cfg:RegularAddress";
            key "address";
            description "Regular IPv6 address";
            leaf address {
              xr:xr-xml-map "ipv6_ma_cfg:Address";
              type inet:ip-address-no-zone;
              description "IPv6 address";
            }
            leaf prefix-length {
              xr:xr-xml-map "ipv6_ma_cfg:PrefixLength";
              type dt1:Ipv6arm-prefix-length;
              mandatory true;
              description "Prefix Length";
            }
            leaf zone {
              xr:xr-xml-map "ipv6_ma_cfg:Zone";
              type string;
              default "0";
              description "IPv6 address zone";
            }
            leaf route-tag {
              xr:xr-xml-map "ipv6_ma_cfg:RouteTag";
              type uint32 {
                range "1..4294967295";
              }
              description "RouteTag";
            }
          }
        }

        container auto-configuration {
          xr:xr-xml-map "ipv6_ma_cfg:AutoConfiguration";
          description "Auto IPv6 Interface Configuration";
          leaf enable {
            xr:xr-xml-map "ipv6_ma_cfg:Enable";
            type empty;
            description
              "The flag to enable auto ipv6 interface
              configuration";
          }
        }
      }

      container bgp-flow-tag-policy-table {
        xr:xr-xml-map "ipv6_ma_cfg:BGP_FlowTagPolicyTable";
        description
          "Interface ipv6 bgp policy propagation flowtag
          configuration";

        container bgp-flow-tag-policy {
          xr:xr-xml-map "ipv6_ma_cfg:BGP_FlowTagPolicy";
          description "Input";
          leaf source {
            xr:xr-xml-map "ipv6_ma_cfg:Source";
            type boolean;
            description "Flow Tag configuration on source";
          }
          leaf destination {
            xr:xr-xml-map "ipv6_ma_cfg:Destination";
            type boolean;
            description "Flow Tag configuration on destination";
          }
        }
      }
      leaf mtu {
        xr:xr-xml-map "ipv6_ma_cfg:MTU";
        type uint32 {
          range "1280..65535";
        }
        description "MTU Setting of Interface";
      }
      leaf unnumbered {
        xr:xr-xml-map "ipv6_ma_cfg:Unnumbered";
        type xr:Interface-name;
        description
          "Enable IPv6 processing without an explicit
          address";
      }
      leaf ttl-propagate-disable {
        xr:xr-xml-map "ipv6_ma_cfg:TTLPropagateDisable";
        type empty;
        description "Disabled TTL propagate on an interface";
      }
      leaf tcp-mss-adjust-enable {
        xr:xr-xml-map "ipv6_ma_cfg:TCP_MSSAdjustEnable";
        type empty;
        description "Enable TCP MSS adjust on an interface";
      }
      leaf unreachables {
        xr:xr-xml-map "ipv6_ma_cfg:Unreachables";
        type empty;
        description "Override Sending of ICMP Unreachable Messages";
      }
    }
    description
      "This augment extends the configuration data of
      'Cisco-IOS-XR-ifmgr-cfg'";
  }
}
