submodule Cisco-IOS-XR-ipv6-ace-cfg {
    
  belongs-to Cisco-IOS-XR-ipv6-acl-cfg {
    prefix ipv6-acl-cfg;
  }
  
  import Cisco-IOS-XR-ipv6-acl-datatypes {
    prefix "ipv6-acl-dt";
  }

  import ietf-inet-types { 
    prefix "inet";
  }
  
  import Cisco-IOS-XR-types { 
    prefix "xr";
  } 
    
  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR IPv6 ACL entry configuration.

     Copyright (c) 2013, 2015-2016 by Cisco Systems, Inc.
     All rights reserved.";

  revision "2015-11-09" {
    description
      "Initial revision.";
  }
   
  typedef Next-hop-type {
    type enumeration {
      enum none-next-hop {
        description "None next-hop.";
      }
      enum regular-next-hop {
        description "Regular next-hop.";
      }
      enum default-next-hop {
        description "Default next-hop.";
      }
    }
    description "Next-hop type.";
  }

  grouping IPV6-ACE {
    description "IPv6 ACL entry.";
    leaf grant {
      type ipv6-acl-dt:Ipv6-acl-grant-enum;
      description "Whether to forward or drop packets matching the 
                   ACE.";
    }

    leaf protocol {
      type ipv6-acl-dt:Ipv6-acl-protocol-number;
      description "Protocol to match.";
    }

    container source-network {
      description "Source network settings.";
      leaf source-address {
        type inet:ipv6-address;
        description "Source IPv6 address, leave unspecified
                     if inputting as IPv6 address with wildcarding.";
      }
      leaf source-wild-card-bits {
        type xr:Ipv6-prefix-length;
        description "Wildcard bits to apply to source-address
                     (if specified), leave unspecified for no
                     wildcarding.";
      }
      leaf source-mask {
        type inet:ipv6-address-no-zone;
        description "Source address mask. Either
                     source-wild-card-bits or source-mask is.
                     supported, not both. Leave unspecified.
                     for any.";
      }
    }

    container destination-network {
      description "Destination network settings.";
      leaf destination-address {
        type inet:ipv6-address;
        description "Destination IPv6 address, leave unspecified
                     if inputting as IPv6 address with 
                     wildcarding.";
      }
      leaf destination-wild-card-bits {
        type xr:Ipv6-prefix-length;
        description "Wildcard bits to apply to destination 
                     destination-address (if specified), 
                     leave unspecified for no wildcarding.";
      }
      leaf destination-mask {
        type inet:ipv6-address-no-zone;
        description "Destination address mask. Either
                     destination-wild-card-bits or destination-mask.
                     is supported, not both. Leave unspecified
                     for any.";
      }
    }
        
    container source-port {
      when "../protocol = '6' or ../protocol = 'tcp' or " +
           "../protocol = '17' or ../protocol = 'udp' or " +
           "../protocol = '132' or ../protocol = 'sctp'" {
        description "Applicable only to TCP, SCTP and UDP.";
      }
      description "Source port settings.";
      leaf source-operator {
        type ipv6-acl-dt:Ipv6-acl-operator-enum;
        description "Source comparison operator. Leave unspecified if
                     no source port comparison is to be done.";
      }
      leaf first-source-port {
        type ipv6-acl-dt:Ipv6-acl-port-number;
        description "First source port for comparison, 
                     leave unspecified if source port comparison is
                     not to be performed.";
      }
      leaf second-source-port {
        type ipv6-acl-dt:Ipv6-acl-port-number;
        description "Second source port for comparion, 
                     leave unspecified if source port comparison is
                     not to be performed.";
      }
    }
    
    container destination-port {
      when "../protocol = '6' or ../protocol = 'tcp' or " +
           "../protocol = '17' or ../protocol = 'udp' or " +
           "../protocol = '132' or ../protocol = 'sctp'" {
        description "Applicable only to TCP, SCTP and UDP.";
      }
      description "Destination port settings.";
      leaf destination-operator {
        type ipv6-acl-dt:Ipv6-acl-operator-enum;
        description "Destination comparison operator. Leave 
                     unspecified if no destination port comparison 
                     is to be done.";
      }
      leaf first-destination-port {
        type ipv6-acl-dt:Ipv6-acl-port-number;
        description "First destination port for comparison, leave 
                     unspecified if destination port comparison is
                     not to be performed.";
      }
      leaf second-destination-port {
        type ipv6-acl-dt:Ipv6-acl-port-number;
        description "Second destination port for comparion, leave 
                     unspecified if destination port comparison is
                     not to be performed.";
      }
    }
    
    container icmp {
      when "../protocol = '58'" {
        description "Applicable only to ICMPv6.";
      }
      description "ICMP settings.";
      leaf icmp-type-code {
        type ipv6-acl-dt:Ipv6-acl-icmp-type-code-enum;
        description "Well known ICMP message code types to match, 
                     leave unspecified if ICMP message code type 
                     comparion is not to be performed.";
      }
    }

    container tcp {
      when "../protocol = '6' or ../protocol = 'tcp'" {
       description "Applicable only to TCP.";
      }
      description "TCP settings.";
      leaf tcp-bits-match-operator {
        type ipv6-acl-dt:Ipv6-acl-tcp-match-operator-enum;
        description "TCP Bits match operator. Leave unspecified if 
                     flexible comparison of TCP bits is not 
                     required.";
      }
      leaf tcp-bits {
        type ipv6-acl-dt:Ipv6-acl-tcp-bits-number;
        description "TCP bits to match. Leave unspecified if 
                     comparison of TCP bits is not required.";
      }
      leaf tcp-bits-mask {
        type ipv6-acl-dt:Ipv6-acl-tcp-bits-number;
        description "TCP bits mask to use for flexible TCP matching.
                     Leave unspecified if it is not required.";
      }
    }
    
    container packet-length {
      description "Packet length settings.";
      leaf packet-length-operator {
        type ipv6-acl-dt:Ipv6-acl-operator-enum;
        description "Packet length operator applicable if packet 
                     length is to be compared. Leave unspecified if
                     no Packet length comparison is to be done.";
      }
      leaf packet-length-min {
        type ipv6-acl-dt:Ipv6-acl-plen-range;
        description "Minimum packet length for comparison, leave 
                     unspecified if packet length comparison is not
                     to be performed or if only the maximum packet
                     length should be considered.";
      }
      leaf packet-length-max {
        type ipv6-acl-dt:Ipv6-acl-plen-range;
        description "Maximum packet length for comparion, leave 
                     unspecified if packet length comparison is not
                     to be performed or if only the minimum packet 
                     length should be considered.";
      }
    }
    
    container time-to-live {
      description "TTL settings.";
      leaf time-to-live-operator {
        type ipv6-acl-dt:Ipv6-acl-operator-enum;
        description "TTL operator is applicable if TTL is to be 
                     compared. Leave unspecified if TTL 
                     classification is not required.";
      }
      leaf time-to-live-min {
        type ipv6-acl-dt:Ipv6-acl-ttl-range;
        description "TTL value for comparison OR Minimum TTL value 
                     for TTL range comparision, leave unspecified if
                     TTL classification is not required.";
      }
      leaf time-to-live-max {
        type ipv6-acl-dt:Ipv6-acl-ttl-range;
        description "Maximum TTL for comparion, leave unspecified if
                     TTL comparison is not to be performed or if only
                     the minimum TTL should be considered.";
      }
    }
    
    leaf dscp {
      type ipv6-acl-dt:Ipv6-acl-dscp-number;
      description "DSCP value to match (if a protocol was specified),
                   leave unspecified if DSCP comparion is not to be
                   performed.";
    }

    leaf precedence {
      type ipv6-acl-dt:Ipv6-acl-precedence-number;
      description "Precedence value to match (if a protocol was 
                   specified), leave unspecified if precedence 
                   comparion is not to be performed.";
    }

    container next-hop {
      description "Next-hop settings.";
      leaf next-hop-type {
        type Next-hop-type;
        description "The nexthop type.";
      }
      container next-hop-1 {
        description "The first next-hop settings.";
        leaf next-hop {
          type inet:ipv6-address-no-zone;
          description "The IPv6 address of the next-hop.";
        }
        leaf vrf-name {
          type string;
          description "The VRF name of the next-hop.";
        }
        leaf track-name {
          type string;
          description "The object tracking name for the next-hop.";
        }
      }
      container next-hop-2 {
        description "The second next-hop settings.";
        leaf next-hop {
          type inet:ipv6-address-no-zone;
          description "The IPv6 address of the next-hop.";
        }
        leaf vrf-name {
          type string;
          description "The VRF name of the next-hop.";
        }
        leaf track-name {
          type string;
          description "The object tracking name for the next-hop.";
        }
      }
      container next-hop-3 {
        description "The third next-hop settings.";
        leaf next-hop {
          type inet:ipv6-address-no-zone;
          description "The IPv6 address of the next-hop.";
        }
        leaf vrf-name {
          type string;
          description "The VRF name of the next-hop.";
        }
        leaf track-name {
          type string;
          description "The object tracking name for the next-hop.";
        }
      }
    }
    
    leaf counter-name {
      type string;
      description "Counter name.";
    }

    leaf log-option {
      type ipv6-acl-dt:Ipv6-acl-logging-enum;
      description "Whether and how to log matches against this 
                   entry.";
    }

    leaf capture {
      type boolean;
      description "Enable capture.";
    }

    leaf icmp-off {
      type empty;
      description "To turn off ICMP generation for deny ACEs.";
    }

    container header-flags {
      description "Match if header-flag is present.";
      leaf routing {
        type empty;
        description "Match if routing header is present.";
      }
      leaf destopts {
        type empty;
        description "Match if destops header is present.";
      }
      leaf hop-by-hop {
        type empty;
        description "Match if hop-by-hop header is present.";
      }
      leaf fragments {
        type empty;
        description "Match if fragments header is present.";
      }
      leaf authen {
        type empty;
        description "Match if authen header is present.";
      }
    }

    leaf remark {
      type string;
      description "Comments or a description for the access list.";
    }

    leaf source-prefix-group {
      type string {
        length "1..64";
      }
      description "IPv6 source network object group name.";
    }
    
    leaf destination-prefix-group {
      type string {
        length "1..64";
      }
      description "IPv6 destination network object group name.";
    }
    
    leaf source-port-group {
      type string {
        length "1..64";
      }
      description "Source port object group name.";
    }
    
    leaf destination-port-group {
      type string {
        length "1..64";
      }
      description "Destination port object group name.";
    }
    
  } 
}
