module Cisco-IOS-XR-lib-mpp-oper {

  /*** NAMESPACE / PREFIX DEFINITION ***/

  namespace "http://cisco.com/ns/yang/Cisco-IOS-XR-lib-mpp-oper";


  prefix "lib-mpp-oper";

  /*** LINKAGE (IMPORTS / INCLUDES) ***/

  import Cisco-IOS-XR-types { prefix "xr"; }

  include Cisco-IOS-XR-lib-mpp-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-mpp package operational data.

     This module contains definitions
     for the following management objects:
       management-plane-protection: Management Plane Protection (MPP)
         operational data

     Copyright (c) 2013-2015 by Cisco Systems, Inc.
     All rights reserved.";

  revision "2015-01-07" {
    description
      "IOS XR 5.3.1 revision.";
  }


  grouping INTERFACE-TABLE {
    description "Common node of inband, outband";

    container interfaces {
      xr:xr-xml-map "mpp_oper:InterfaceTable";
      description "List of inband/outband interfaces";

      list interface {
        xr:xr-xml-map "mpp_oper:Interface";
        key "interface-name";
        description "MPP interface information";
        leaf interface-name {
          xr:xr-xml-map "mpp_oper:InterfaceName";
          type string;
          description
            "Interface name, specify 'all' for all
            interfaces";
        }
        uses MPP-PROTO;
      }
    }
  }

  container management-plane-protection {
    xr:xr-xml-map "mpp_oper:ManagementPlaneProtection";
    config false;
    description
      "Management Plane Protection (MPP) operational
      data";

    container outband {
      xr:xr-xml-map "mpp_oper:Outband";
      description
        "Management Plane Protection (MPP) outband
        interface data";

      container vrf {
        xr:xr-xml-map "mpp_oper:VRF";
        description "Outband VRF information";
        uses VRF-INFO;
      }
      uses INTERFACE-TABLE;
    }

    container inband {
      xr:xr-xml-map "mpp_oper:Inband";
      description
        "Management Plane Protection (MPP) inband
        interface data";
      uses INTERFACE-TABLE;
    }
  }
}
