module Cisco-IOS-XR-snmp-entitymib-cfg {

  /*** NAMESPACE / PREFIX DEFINITION ***/

  namespace "http://cisco.com/ns"+
    "/yang/Cisco-IOS-XR-snmp-entitymib-cfg";


  prefix "snmp-entitymib-cfg";

  /*** LINKAGE (IMPORTS / INCLUDES) ***/

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-entitymib package configuration.

     This YANG module augments the
       Cisco-IOS-XR-snmp-agent-cfg
     module with configuration data.

     Copyright (c) 2013-2015 by Cisco Systems, Inc.
     All rights reserved.";

  revision "2015-01-07" {
    description
      "IOS XR 5.3.1 revision.";
  }


  augment "/a1:mib" {

    container entity-mib {
      xr:xr-xml-map "snmp_entindex_persist_cfg:EntityMIB";
      description "Entity MIB";
      leaf entity-index-persistence {
        xr:xr-xml-map "snmp_entindex_persist_cfg:EntityIndexPersist"+
          "ence";
        type empty;
        description "Enable entPhysicalIndex persistence";
      }
    }
    description
      "This augment extends the configuration data of
      'Cisco-IOS-XR-snmp-agent-cfg'";
  }

  augment "/a1:snmp/a1:notification" {

    container entity {
      xr:xr-xml-map "entitymib_cfg:Entity";
      description "Enable ENTITY-MIB notifications";
      leaf enable {
        xr:xr-xml-map "entitymib_cfg:Enable";
        type empty;
        description "Enable entityMIB notifications";
      }
    }
    description
      "This augment extends the configuration data of
      'Cisco-IOS-XR-snmp-agent-cfg'";
  }
}
