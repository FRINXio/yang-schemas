module cisco-xr-bgp-policy-deviations {

  /*** NAMESPACE / PREFIX DEFINITION ***/

  namespace "http://cisco.com/ns/yang/cisco-xr-bgp-policy-deviations";

  prefix "cisco-xr-bgp-pol-devs";

  /*** LINKAGE (IMPORTS / INCLUDES) ***/
  import routing-policy { prefix rpol; }
  import bgp-policy { prefix bgp-pol; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains the deviations of Open Config BGP Policy YANG 
    set for Cisco IOS-XR.

     Copyright (c) 2015 by Cisco Systems, Inc.
     All rights reserved.";

  revision "2015-10-21" {
    description
      "Initial revision applicable to IOS-XR 5.3.2 and 6.0";
  }

  deviation /rpol:routing-policy/rpol:defined-sets/bgp-pol:bgp-defined-sets/bgp-pol:ext-community-sets/bgp-pol:ext-community-set {
    deviate not-supported;
  }

  deviation /rpol:routing-policy/rpol:policy-definitions/rpol:policy-definition/rpol:statements/rpol:statement/rpol:conditions/bgp-pol:bgp-conditions/bgp-pol:match-ext-community-set {
    deviate not-supported;
  }

  deviation /rpol:routing-policy/rpol:policy-definitions/rpol:policy-definition/rpol:statements/rpol:statement/rpol:conditions/bgp-pol:bgp-conditions/bgp-pol:community-count {
    deviate not-supported;
  }

  deviation /rpol:routing-policy/rpol:policy-definitions/rpol:policy-definition/rpol:statements/rpol:statement/rpol:conditions/bgp-pol:bgp-conditions/bgp-pol:route-type {
    deviate not-supported;
  }

  deviation /rpol:routing-policy/rpol:policy-definitions/rpol:policy-definition/rpol:statements/rpol:statement/rpol:actions/bgp-pol:bgp-actions/bgp-pol:set-ext-community {
    deviate not-supported;
  }
}
