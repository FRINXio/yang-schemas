submodule Cisco-IOS-XR-infra-rsi-oper-sub2 {

  belongs-to Cisco-IOS-XR-infra-rsi-oper {
    prefix Cisco-IOS-XR-infra-rsi-oper;
  }

  /*** LINKAGE (IMPORTS / INCLUDES) ***/

  import Cisco-IOS-XR-types { prefix "xr"; }

  include Cisco-IOS-XR-infra-rsi-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-rsi package operational data.

     Copyright (c) 2013-2015 by Cisco Systems, Inc.
     All rights reserved.";

  revision "2015-01-07" {
    description
      "IOS XR 5.3.1 revision.";
  }

  typedef Source {
    type enumeration {
      enum configured {
        value 1;
        description "Configured";
      }
      enum from-group {
        value 2;
        description "From group";
      }
      enum inherited {
        value 4;
        description "Inherited";
      }
      enum from-optical {
        value 8;
        description "From optical";
      }
      enum configured-and-notified {
        value 17;
        description "Configured and notified";
      }
      enum from-group-and-notified {
        value 18;
        description "From group and notified";
      }
      enum inherited-and-notified {
        value 20;
        description "Inherited and notified";
      }
      enum from-optical-and-notified {
        value 24;
        description "From optical and notified";
      }
    }
    description "Source";
  }
  typedef Priority {
    type enumeration {
      enum critical {
        value 0;
        description "Critical";
      }
      enum high {
        value 1;
        description "High";
      }
      enum medium {
        value 2;
        description "Medium";
      }
      enum low {
        value 3;
        description "Low";
      }
      enum very-low {
        value 4;
        description "Very low";
      }
    }
    description "Priority";
  }

  grouping RSI-SRLG-NAME-INTF-SHOW {
    description "RSI SRLG NAME INTF SHOW";

    container interfaces {
      description "Interfaces information";
      uses RSI-SRLG-INTF-SHOW;
    }
    leaf srlg-name-xr {
      xr:xr-xml-map "rsi_agent:srlg-name-xr";
      type string;
      description "SRLG name";
    }
    leaf srlg-value {
      xr:xr-xml-map "rsi_agent:SRLGValue";
      type uint32;
      description "SRLG value";
    }
  }

  grouping RSI-SRLG-INTF-SHOW {
    description "RSI SRLG INTF SHOW";
    leaf-list interface-name {
      xr:xr-xml-map "rsi_agent:InterfaceName";
      type String1;
      description "Interface name";
    }
  }

  grouping RSI-SRLG-ATTR-DETAIL {
    description "RSI SRLG ATTR DETAIL";
    leaf srlg-value {
      xr:xr-xml-map "rsi_agent:SRLGValue";
      type uint32;
      description "SRLG value";
    }
    leaf priority {
      xr:xr-xml-map "rsi_agent:Priority";
      type Priority;
      description "Priority";
    }
    leaf source {
      xr:xr-xml-map "rsi_agent:Source";
      type Source;
      description "Source";
    }
    leaf source-name {
      xr:xr-xml-map "rsi_agent:SourceName";
      type string;
      description "Source name";
    }
    leaf srlg-index {
      xr:xr-xml-map "rsi_agent:SRLGIndex";
      type uint16;
      description "Index";
    }
  }

  grouping RSI-SRLG-INTF-DETAIL-SHOW {
    description "RSI SRLG INTF DETAIL SHOW";
    leaf groups {
      xr:xr-xml-map "rsi_agent:Groups";
      type uint32;
      description "Groups";
    }
    leaf nodes {
      xr:xr-xml-map "rsi_agent:Nodes";
      type uint32;
      description "Nodes";
    }

    list srlg-attribute {
      description "SRLG attributes";
      uses RSI-SRLG-ATTR-DETAIL;
    }
  }

  grouping RSI-SRLG-INTF-BRIEF-SHOW {
    description "RSI SRLG INTF BRIEF SHOW";
    leaf interface-name-xr {
      xr:xr-xml-map "rsi_agent:interface-name-xr";
      type string;
      description "Interface name";
    }
    leaf value-count {
      xr:xr-xml-map "rsi_agent:ValueCount";
      type uint32;
      description "Values";
    }
    leaf registrations {
      xr:xr-xml-map "rsi_agent:Registrations";
      type uint32;
      description "Registrations";
    }
    leaf-list srlg-value {
      xr:xr-xml-map "rsi_agent:SRLGValues";
      type uint32;
      description "SRLG values";
    }
  }

  grouping RSI-SRLG-INHLOC-SHOW {
    description "RSI SRLG INHLOC SHOW";
    leaf node-name {
      xr:xr-xml-map "rsi_agent:NodeName";
      type string;
      description "Inherit node name";
    }
    leaf node-values {
      xr:xr-xml-map "rsi_agent:NodeValues";
      type uint32;
      description "Node values";
    }

    list srlg-attribute {
      description "SRLG attribute";
      uses RSI-SRLG-ATTR-BRIEF;
    }
  }

  grouping RSI-SRLG-ATTR-BRIEF {
    description "RSI SRLG ATTR BRIEF";
    leaf srlg-value {
      xr:xr-xml-map "rsi_agent:SRLGValue";
      type uint32;
      description "SRLG value";
    }
    leaf priority {
      xr:xr-xml-map "rsi_agent:Priority";
      type Priority;
      description "Priority";
    }
    leaf srlg-index {
      xr:xr-xml-map "rsi_agent:SRLGIndex";
      type uint16;
      description "Index";
    }
  }

  grouping RSI-SRLG-GROUP-SHOW {
    description "RSI SRLG GROUP SHOW";
    leaf group-name-xr {
      xr:xr-xml-map "rsi_agent:group-name-xr";
      type string;
      description "Group name";
    }
    leaf group-values {
      xr:xr-xml-map "rsi_agent:GroupValues";
      type uint32;
      description "Group values";
    }

    list srlg-attribute {
      description "SRLG attribute";
      uses RSI-SRLG-ATTR-BRIEF;
    }
  }

  grouping RSI-SRLG-NAME-VALUE-SHOW {
    description "RSI SRLG NAME VALUE SHOW";
    leaf srlg-value {
      xr:xr-xml-map "rsi_agent:SRLGValue";
      type uint32;
      description "SRLG value";
    }
    leaf srlg-name-xr {
      xr:xr-xml-map "rsi_agent:srlg-name-xr";
      type string;
      description "SRLG name";
    }
  }

  grouping RSI-VRFGROUP-ATTR-BRIEF {
    description "RSI VRFGROUP ATTR BRIEF";
    leaf vrf-name {
      xr:xr-xml-map "rsi_agent:VRFName";
      type string;
      description "VRF name";
    }
  }

  grouping RSI-VRFGROUP-GROUP-SHOW {
    description "RSI VRFGROUP GROUP SHOW";
    leaf vr-fs {
      xr:xr-xml-map "rsi_agent:VRFs";
      type uint32;
      description "Number of VRFs in this VRF group";
    }
    leaf forward-reference {
      xr:xr-xml-map "rsi_agent:ForwardReference";
      type boolean;
      description "VRF group not present but used";
    }

    list vrf {
      description "VRF group's VRF";
      uses RSI-VRFGROUP-ATTR-BRIEF;
    }
  }
}
