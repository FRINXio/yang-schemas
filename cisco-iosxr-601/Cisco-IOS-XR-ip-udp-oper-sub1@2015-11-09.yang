submodule Cisco-IOS-XR-ip-udp-oper-sub1 {

  belongs-to Cisco-IOS-XR-ip-udp-oper {
    prefix Cisco-IOS-XR-ip-udp-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-udp package operational data.

     Copyright (c) 2013-2015 by Cisco Systems, Inc.
     All rights reserved.";

  revision "2015-11-09" {
    description
      "IOS XR 6.0 revision.";
  }

  typedef Udp-in6-addr {
    type inet:ipv6-address;
    description "Udp in6 addr";
  }
  typedef Udp-address-family {
    type enumeration {
      enum ipv4 {
        value 2;
        description "IPv4";
      }
      enum ipv6 {
        value 26;
        description "IPv6";
      }
    }
    description "Address Family Type";
  }

  grouping UDP-SH-BRIEF-BAG {
    description "UDP connection brief information";

    container local-address {
      description "Local address";
      uses UDP-ADDRESS-TYPE;
    }

    container foreign-address {
      description "Foreign address";
      uses UDP-ADDRESS-TYPE;
    }
    leaf af-name {
      xr:xr-xml-map "udp_cmd:AFName";
      type Udp-address-family;
      description "Address family";
    }
    leaf local-port {
      xr:xr-xml-map "udp_cmd:LocalPort";
      type uint16;
      description "Local port";
    }
    leaf foreign-port {
      xr:xr-xml-map "udp_cmd:ForeignPort";
      type uint16;
      description "Foreign port";
    }
    leaf receive-queue {
      xr:xr-xml-map "udp_cmd:ReceiveQueue";
      type uint32;
      description "Receive queue count";
    }
    leaf send-queue {
      xr:xr-xml-map "udp_cmd:SendQueue";
      type uint32;
      description "Send queue count";
    }
    leaf vrf-id {
      xr:xr-xml-map "udp_cmd:VRF_ID";
      type uint32;
      description "VRF ID";
    }
  }

  grouping UDP-ADDRESS-TYPE {
    description "UDP ADDRESS TYPE";
    leaf af-name {
      xr:xr-xml-map "udp_cmd:AFName";
      type Udp-address-family;
      description "AFName";
    }
    leaf ipv4-address {
      xr:xr-xml-map "udp_cmd:IPv4Address";
      when "../af-name = 'ipv4'" {
        description "../AFName = 'IPv4'";
      }
      type inet:ipv4-address;
      description "IPv4 Address";
    }
    leaf ipv6-address {
      xr:xr-xml-map "udp_cmd:IPv6Address";
      when "../af-name != 'ipv4'" {
        description "../AFName != 'IPv4'";
      }
      type Udp-in6-addr;
      description "IPv6 Address";
    }
  }

  grouping UDP-SH-TABLE-BAG {
    description "UDP detail pcb information";

    container local-address {
      description "Local address";
      uses UDP-ADDRESS-TYPE;
    }

    container foreign-address {
      description "Foreign address";
      uses UDP-ADDRESS-TYPE;
    }
    leaf af-name {
      xr:xr-xml-map "udp_cmd:AFName";
      type Udp-address-family;
      description "Address family";
    }
    leaf local-process-id {
      xr:xr-xml-map "udp_cmd:LocalProcessID";
      type uint32;
      description "ID of local process";
    }
    leaf local-port {
      xr:xr-xml-map "udp_cmd:LocalPort";
      type uint16;
      description "Local port";
    }
    leaf foreign-port {
      xr:xr-xml-map "udp_cmd:ForeignPort";
      type uint16;
      description "Foreign port";
    }
    leaf receive-queue {
      xr:xr-xml-map "udp_cmd:ReceiveQueue";
      type uint32;
      description "Receive queue count";
    }
    leaf send-queue {
      xr:xr-xml-map "udp_cmd:SendQueue";
      type uint32;
      description "Send queue count";
    }
    leaf vrf-id {
      xr:xr-xml-map "udp_cmd:VRF_ID";
      type uint32;
      description "VRF ID";
    }
  }

  grouping UDP-PCB-RECEIVE-STATS-TYPE {
    description "UDP receive statistics";
    leaf received-network-packets {
      xr:xr-xml-map "udp_cmd:ReceivedNetworkPackets";
      type uint64;
      description "Packets received from network";
    }
    leaf failed-queued-application-packets {
      xr:xr-xml-map "udp_cmd:FailedQueuedApplicationPackets";
      type uint32;
      description "Packets failed queued to application";
    }
    leaf queued-application-packets {
      xr:xr-xml-map "udp_cmd:QueuedApplicationPackets";
      type uint64;
      description "Packets queued to application";
    }
    leaf failed-queued-application-socket-packets {
      xr:xr-xml-map "udp_cmd:FailedQueuedApplicationSocketPackets";
      type uint32;
      description
        "Packet that couldn't be queued to application.on
        socket";
    }
    leaf queued-application-socket-packets {
      xr:xr-xml-map "udp_cmd:QueuedApplicationSocketPackets";
      type uint64;
      description "Packets queued to application on socket";
    }
  }

  grouping UDP-PCB-SEND-STATS-TYPE {
    description "UDP send statistics";
    leaf received-application-bytes {
      xr:xr-xml-map "udp_cmd:ReceivedApplicationBytes";
      type uint64;
      units "byte";
      description "Bytes received from application";
    }
    leaf received-xipc-pulses {
      xr:xr-xml-map "udp_cmd:ReceivedXIPCPulses";
      type uint64;
      description "XIPC pulses received from application";
    }
    leaf sent-network-packets {
      xr:xr-xml-map "udp_cmd:SentNetworkPackets";
      type uint64;
      description "Packets sent to network (v4/v6 IO)";
    }
    leaf sent-net-io-packets {
      xr:xr-xml-map "udp_cmd:SentNetIOPackets";
      type uint64;
      description "Packets sent to network (NetIO)";
    }
    leaf failed-queued-network-packets {
      xr:xr-xml-map "udp_cmd:FailedQueuedNetworkPackets";
      type uint32;
      description
        "Packets failed getting queued to network (v4/v6
        IO)";
    }
    leaf failed-queued-net-io-packets {
      xr:xr-xml-map "udp_cmd:FailedQueuedNetIOPackets";
      type uint32;
      description
        "Packets failed getting queued to network (NetIO)";
    }
  }

  grouping UDP-SH-PCB-STATS-BAG {
    description "UDP statistics";

    container send {
      description "UDP send statistics";
      uses UDP-PCB-SEND-STATS-TYPE;
    }

    container receive {
      description "UDP receive statistics";
      uses UDP-PCB-RECEIVE-STATS-TYPE;
    }
    leaf vrf-id {
      xr:xr-xml-map "udp_cmd:VRF_ID";
      type uint32;
      description "VRF ID";
    }
    leaf is-paw-socket {
      xr:xr-xml-map "udp_cmd:IsPawSocket";
      type boolean;
      description "True if paw socket";
    }
  }

  grouping UDP-SH-STATS-BAG {
    description "UDP statistics summary";
    leaf received-total-packets {
      xr:xr-xml-map "udp_cmd:ReceivedTotalPackets";
      type uint32;
      description "Total packets received";
    }
    leaf received-no-port-packets {
      xr:xr-xml-map "udp_cmd:ReceivedNoPortPackets";
      type uint32;
      description "Packets received when no wild listener";
    }
    leaf received-bad-checksum-packets {
      xr:xr-xml-map "udp_cmd:ReceivedBadChecksumPackets";
      type uint32;
      description "Packets received has bad checksum";
    }
    leaf received-too-short-packets {
      xr:xr-xml-map "udp_cmd:ReceivedTooShortPackets";
      type uint32;
      description "Packets received is too short";
    }
    leaf received-drop-packets {
      xr:xr-xml-map "udp_cmd:ReceivedDropPackets";
      type uint32;
      description "Packets dropped for other reasons";
    }
    leaf sent-total-packets {
      xr:xr-xml-map "udp_cmd:SentTotalPackets";
      type uint32;
      description "Total packets sent";
    }
    leaf sent-error-packets {
      xr:xr-xml-map "udp_cmd:SentErrorPackets";
      type uint32;
      description "Total send erorr packets";
    }
    leaf forward-broadcast-packets {
      xr:xr-xml-map "udp_cmd:ForwardBroadcastPackets";
      type uint32;
      description "Total forwarding broadcast packets";
    }
    leaf cloned-packets {
      xr:xr-xml-map "udp_cmd:ClonedPackets";
      type uint32;
      description "Total cloned packets";
    }
    leaf failed-clone-packets {
      xr:xr-xml-map "udp_cmd:FailedClonePackets";
      type uint32;
      description "Total failed cloned packets";
    }
  }
}
