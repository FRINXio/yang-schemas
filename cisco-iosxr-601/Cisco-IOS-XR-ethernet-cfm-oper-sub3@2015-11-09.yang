submodule Cisco-IOS-XR-ethernet-cfm-oper-sub3 {

  belongs-to Cisco-IOS-XR-ethernet-cfm-oper {
    prefix Cisco-IOS-XR-ethernet-cfm-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ethernet-cfm package operational data.

     Copyright (c) 2013-2015 by Cisco Systems, Inc.
     All rights reserved.";

  revision "2015-11-09" {
    description
      "IOS XR 6.0 revision.";
  }

  typedef Cfm-bag-bdid-fmt {
    type enumeration {
      enum invalid {
        value 0;
        description "Invalid BDID identifier format";
      }
      enum bd-id {
        value 1;
        description "Identifier is a bridge domain ID";
      }
      enum xc-p2p-id {
        value 2;
        description "Identifier is a P2P cross-connect ID";
      }
      enum xc-mp2mp-id {
        value 3;
        description "Identifier is a MP2MP cross-connect ID";
      }
      enum down-only {
        value 4;
        description "Identifier is a maintenance association name";
      }
    }
    description "Bridge domain identifier format";
  }
  typedef Cfm-bag-ccm-offload {
    type enumeration {
      enum offload-none {
        description "CCM processing has not been offloaded";
      }
      enum offload-software {
        description "CCM processing has been offloaded to software";
      }
      enum offload-hardware {
        description "CCM processing has been offloaded to hardware";
      }
    }
    description "Offload status of CCM processing";
  }
  typedef Cfm-bag-sman-fmt {
    type enumeration {
      enum sman-vlan-id {
        value 1;
        description "Short MA Name is a 12-bit VLAN-ID";
      }
      enum sman-string {
        value 2;
        description "Short MA Name is a character string";
      }
      enum sman-uint16 {
        value 3;
        description "Short MA Name is a 16-bit unsigned integer";
      }
      enum sman-vpn-id {
        value 4;
        description "Short MA Name is a global VPN identifier";
      }
      enum sman-icc {
        value 32;
        description "Short MA Name uses the ICC-based format";
      }
      enum sman-unknown {
        value 33;
        description "Unknown Short MA Name format";
      }
    }
    description "Short MA Name format";
  }
  typedef Cfm-bag-optional-hex-data {
    type yang:hex-string;
    description "Hex binary data which may be optionally present.";
  }
  typedef Cfm-bag-optional-string {
    type string;
    description "String which may be optionally present.";
  }
  typedef Cfm-bag-mdid-fmt {
    type enumeration {
      enum mdid-null {
        value 1;
        description "MDID is explicity NULL";
      }
      enum mdid-dns-like {
        value 2;
        description "MDID is based on a DNS name";
      }
      enum mdid-mac-address {
        value 3;
        description "MDID is a (MAC address, integer) pair";
      }
      enum mdid-string {
        value 4;
        description "MDID is a character string";
      }
      enum mdid-unknown {
        value 5;
        description "Unknown MDID format";
      }
    }
    description "CFM MDID format";
  }
  typedef Cfm-bag-ccm-interval {
    type enumeration {
      enum interval-none {
        value 0;
        description "Invalid CCM interval";
      }
      enum interval3-3ms {
        value 1;
        description "Interval of 3.3ms";
      }
      enum interval10ms {
        value 2;
        description "Interval of 10ms";
      }
      enum interval100ms {
        value 3;
        description "Interval of 100ms";
      }
      enum interval1s {
        value 4;
        description "Interval of 1s";
      }
      enum interval10s {
        value 5;
        description "Interval of 10s";
      }
      enum interval1m {
        value 6;
        description "Interval of 1 min";
      }
      enum interval10m {
        value 7;
        description "Interval of 10 mins";
      }
    }
    description "CFM CCM intervals";
  }
  typedef Cfm-ma-mp-variety {
    type enumeration {
      enum mip {
        description "MIP";
      }
      enum up-mep {
        description "Up MEP";
      }
      enum downmep {
        description "Down MEP";
      }
      enum unknown-mep {
        description "Unknown MEP";
      }
    }
    description "CFM MA Maintenance Point varieties";
  }
  typedef Mac-address {
    type yang:mac-address;
    description "MAC address type";
  }
  typedef Cfm-bag-issu-role {
    type enumeration {
      enum unknown {
        value 0;
        description "Unknown";
      }
      enum primary {
        value 1;
        description "Primary";
      }
      enum secondary {
        value 2;
        description "Secondary";
      }
    }
    description "CFM ISSU role";
  }
  typedef Cfm-bag-opcode {
    type enumeration {
      enum reserved {
        value 0;
        description "Reserved";
      }
      enum ccm {
        value 1;
        description "Continuity Check";
      }
      enum lbr {
        value 2;
        description "Loopback Reply";
      }
      enum lbm {
        value 3;
        description "Loopback Message";
      }
      enum ltr {
        value 4;
        description "Linktrace Reply";
      }
      enum ltm {
        value 5;
        description "Linktrace Message";
      }
    }
    description "CFM Opcode";
  }
  typedef Cfm-bag-ais-interval {
    type enumeration {
      enum ais-interval-none {
        value 0;
        description "Invalid AIS interval";
      }
      enum ais-interval1s {
        value 4;
        description "Interval of 1s";
      }
      enum ais-interval1m {
        value 6;
        description "Interval of 1 min";
      }
    }
    description "CFM AIS intervals";
  }
  typedef Cfm-bag-md-level {
    type enumeration {
      enum level0 {
        value 0;
        description "CFM level 0";
      }
      enum level1 {
        value 1;
        description "CFM level 1";
      }
      enum level2 {
        value 2;
        description "CFM level 2";
      }
      enum level3 {
        value 3;
        description "CFM level 3";
      }
      enum level4 {
        value 4;
        description "CFM level 4";
      }
      enum level5 {
        value 5;
        description "CFM level 5";
      }
      enum level6 {
        value 6;
        description "CFM level 6";
      }
      enum level7 {
        value 7;
        description "CFM level 7";
      }
      enum level-invalid {
        value 8;
        description "Invalid CFM level";
      }
    }
    description "CFM level";
  }
  typedef Cfm-bag-direction {
    type enumeration {
      enum direction-up {
        value 0;
        description "Up";
      }
      enum direction-down {
        value 1;
        description "Down";
      }
      enum direction-invalid {
        value 2;
        description "Invalid direction";
      }
    }
    description "MEP direction";
  }
  typedef Cfm-bag-stp-state {
    type enumeration {
      enum stp-up {
        description "Interface is UP";
      }
      enum stp-blocked {
        description "Interface is STP-blocked";
      }
      enum stp-unknown {
        description "Unknown Interface STP state";
      }
    }
    description "CFM STP state";
  }
  typedef Cfm-bag-iw-state {
    type enumeration {
      enum interworking-up {
        description "Interface is UP";
      }
      enum interworking-test {
        description "Interface is in TEST mode";
      }
    }
    description "CFM Interworking state";
  }

  grouping CFM-BAG-SAT-PDU-CAPS {
    description "Satellite PDU Capabilities";
    leaf responder {
      xr:xr-xml-map "cfm_ma:Responder";
      type boolean;
      description "Responder";
    }
    leaf controller {
      xr:xr-xml-map "cfm_ma:Controller";
      type boolean;
      description "Controller";
    }
  }

  grouping CFM-BAG-SAT-ACCESS-PORT-CAPS {
    description "Satellite access port capabilities";

    container loopback {
      description "Loopback";
      uses CFM-BAG-SAT-PDU-CAPS;
    }

    container delay-measurement {
      description "Delay Measurement";
      uses CFM-BAG-SAT-PDU-CAPS;
    }

    container synthetic-loss-measurement {
      description "Synthetic Loss Measurement";
      uses CFM-BAG-SAT-PDU-CAPS;
    }
  }

  grouping CFM-MA-MEP-ERRORS {
    description "CFM MA MEP Errors";

    container mep {
      description "The MEP that has errors";
      uses CFM-MA-MP;
    }

    container service-bridge-domain {
      description
        "BD/XC ID for the MEP's Service, or Service name
        if the Service is 'down-only'";
      uses CFM-BAG-BDID;
    }

    container interface-bridge-domain {
      description
        "ID of the BD/XC that the MEP's EFP is in, if any";
      uses CFM-BAG-BDID;
    }

    container satellite-capabilities {
      description "Satellite Capabilities";
      uses CFM-BAG-SAT-ACCESS-PORT-CAPS;
    }
    leaf ccm-interval {
      xr:xr-xml-map "cfm_ma:CCMInterval";
      type Cfm-bag-ccm-interval;
      description "Interval between CCMs sent on this MEP.";
    }
    leaf no-domain {
      xr:xr-xml-map "cfm_ma:NoDomain";
      type boolean;
      description "The MEP's Domain is not configured";
    }
    leaf no-service {
      xr:xr-xml-map "cfm_ma:NoService";
      type boolean;
      description "The MEP's Service is not configured";
    }
    leaf bridge-domain-mismatch {
      xr:xr-xml-map "cfm_ma:BridgeDomainMismatch";
      type boolean;
      description
        "The MEP's EFP is not in the Service's Bridge
        Domain";
    }
    leaf level-conflict {
      xr:xr-xml-map "cfm_ma:LevelConflict";
      type boolean;
      description
        "Another MEP facing in the same direction is at
        the same Maintenance Level";
    }
    leaf ccm-interval-not-supported {
      xr:xr-xml-map "cfm_ma:CCMIntervalNotSupported";
      type boolean;
      description
        "CCM Interval is less than minimum interval
        supported by hardware";
    }
    leaf offload-out-of-resources {
      xr:xr-xml-map "cfm_ma:OffloadOutOfResources";
      type boolean;
      description "Offload resource limits have been exceeded";
    }
    leaf offload-multiple-local-mep {
      xr:xr-xml-map "cfm_ma:OffloadMultipleLocalMEP";
      type boolean;
      description
        "Multiple offloaded MEPs on the same interface
        are not supported.";
    }
    leaf offload-no-cross-check {
      xr:xr-xml-map "cfm_ma:OffloadNoCrossCheck";
      type boolean;
      description
        "The MEP should be offloaded but crosscheck has
        not been configured.";
    }
    leaf offload-multiple-peer-meps {
      xr:xr-xml-map "cfm_ma:OffloadMultiplePeerMEPs";
      type boolean;
      description
        "The MEP should be offloaded but multiple
        crosscheck MEPs have been configured, and this
        is not supported.";
    }
    leaf offload-mep-direction-not-supported {
      xr:xr-xml-map "cfm_ma:OffloadMEPDirectionNotSupported";
      type boolean;
      description "The MEP direction does not support offload.";
    }
    leaf ais-configured {
      xr:xr-xml-map "cfm_ma:AISConfigured";
      type boolean;
      description
        "AIS is configured on the same interface as the
        down MEP";
    }
    leaf bundle-level0 {
      xr:xr-xml-map "cfm_ma:BundleLevel0";
      type boolean;
      description
        "The MEP is configured in a domain at level 0, on
        a bundle interface or sub-interface.  This is
        not supported";
    }
    leaf bridge-domain-not-in-bd-infra {
      xr:xr-xml-map "cfm_ma:BridgeDomainNotInBDInfra";
      type boolean;
      description
        "A BD/XC specified in the MEG config, but it does
        not exist globally.";
    }
    leaf satellite-limitation {
      xr:xr-xml-map "cfm_ma:SatelliteLimitation";
      type boolean;
      description
        "A satellite limitation is preventing MEP being
        offloaded to satellite.";
    }
    leaf sla-loopback-operations-disabled {
      xr:xr-xml-map "cfm_ma:SLALoopbackOperationsDisabled";
      type boolean;
      description
        "In-progress Ethernet SLA loopback operations are
        disabled due to satellite having loopback
        responder-only capabilities.";
    }
    leaf sla-synthetic-loss-operations-disabled {
      xr:xr-xml-map "cfm_ma:SLASyntheticLossOperationsDisabled";
      type boolean;
      description
        "In-progress Ethernet SLA synthetic loss
        measurement operations are disabled due to
        satellite having synthetic loss measurement
        responder-only capabilities.";
    }
    leaf sla-delay-measurement-operations-disabled {
      xr:xr-xml-map "cfm_ma:SLADelayMeasurementOperationsDisabled";
      type boolean;
      description
        "In-progress Ethernet SLA delay measurement
        operations are disabled due to satellite having
        delay measurement responder-only capabilities.";
    }
    leaf no-valid-mac-address {
      xr:xr-xml-map "cfm_ma:NoValidMACAddress";
      type boolean;
      description
        "The EFP doesn't have a valid MAC address yet.
        This will also get set if the MAC address we
        have is a multicast address.";
    }
    leaf no-interface-type {
      xr:xr-xml-map "cfm_ma:NoInterfaceType";
      type boolean;
      description
        "We haven't yet been able to look up the
        interface type to find whether the interface is
        a bundle.";
    }
    leaf not-in-im {
      xr:xr-xml-map "cfm_ma:NotInIM";
      type boolean;
      description "The EFP has been deleted from IM.";
    }
    leaf no-mlacp {
      xr:xr-xml-map "cfm_ma:NoMLACP";
      type boolean;
      description
        "The EFP is a bundle and the mLACP mode is not
        yet known.";
    }
    leaf satellite-error-string {
      xr:xr-xml-map "cfm_ma:SatelliteErrorString";
      type string;
      description "Error string returned from satellite";
    }
    leaf satellite-id {
      xr:xr-xml-map "cfm_ma:SatelliteId";
      type uint16;
      description "ID of the satellite";
    }
  }

  grouping CFM-BAG-BDID {
    description "Bridge domain identifier";
    leaf bridge-domain-id-format {
      xr:xr-xml-map "cfm_ma:BridgeDomainIDFormat";
      type Cfm-bag-bdid-fmt;
      description "Bridge domain identifier format";
    }
    leaf group {
      xr:xr-xml-map "cfm_ma:Group";
      type string;
      description "Name of the Bridge/XConnect Group";
    }
    leaf name {
      xr:xr-xml-map "cfm_ma:Name";
      type string;
      description "Name of the Bridge Domain/XConnect";
    }
    leaf ce-id {
      xr:xr-xml-map "cfm_ma:CEId";
      type uint16;
      description "Local Customer Edge Identifier (CE-ID)";
    }
    leaf remote-ce-id {
      xr:xr-xml-map "cfm_ma:RemoteCEId";
      type uint16;
      description "Remote Customer Edge Identifier (CE-ID)";
    }
  }

  grouping CFM-BAG-SMAN-VPNID-NAME {
    description "Short MA Name VPN ID name";
    leaf oui {
      xr:xr-xml-map "cfm_ma:OUI";
      type uint32;
      description "VPN authority organizationally-unique ID";
    }
    leaf index {
      xr:xr-xml-map "cfm_ma:Index";
      type uint32;
      description "VPN index";
    }
  }

  grouping CFM-BAG-SMAN {
    description "Short MA Name types";

    container vpn-id-name {
      when "../short-ma-name-format-value ="+
        " 'cfm-bag-sman-fmt-vpnid'" {
          description
            "../ShortMANameFormatValue =
            'CFM_BAG_SMAN_FMT_VPNID'";
      }
      description "VPN ID name";
      uses CFM-BAG-SMAN-VPNID-NAME;
    }
    leaf short-ma-name-format-value {
      xr:xr-xml-map "cfm_ma:ShortMANameFormatValue";
      type uint32;
      description "ShortMANameFormatValue";
    }
    leaf vlan-id-name {
      xr:xr-xml-map "cfm_ma:VLAN_IDName";
      when "../short-ma-name-format-value ="+
        " 'cfm-bag-sman-fmt-vlan-id'" {
          description
            "../ShortMANameFormatValue =
            'CFM_BAG_SMAN_FMT_VLAN_ID'";
      }
      type uint16;
      description "VLAN ID name";
    }
    leaf string-name {
      xr:xr-xml-map "cfm_ma:StringName";
      when "../short-ma-name-format-value ="+
        " 'cfm-bag-sman-fmt-string'" {
          description
            "../ShortMANameFormatValue =
            'CFM_BAG_SMAN_FMT_STRING'";
      }
      type Cfm-bag-optional-string;
      description "String name";
    }
    leaf integer-name {
      xr:xr-xml-map "cfm_ma:IntegerName";
      when "../short-ma-name-format-value ="+
        " 'cfm-bag-sman-fmt-uint16'" {
          description
            "../ShortMANameFormatValue =
            'CFM_BAG_SMAN_FMT_UINT16'";
      }
      type uint16;
      description "Unsigned integer name";
    }
    leaf icc-based {
      xr:xr-xml-map "cfm_ma:ICCBased";
      when "../short-ma-name-format-value ="+
        " 'cfm-bag-sman-fmt-icc'" {
          description
            "../ShortMANameFormatValue =
            'CFM_BAG_SMAN_FMT_ICC'";
      }
      type Cfm-bag-optional-string;
      description "ICC-based format";
    }
    leaf short-ma-name-data {
      xr:xr-xml-map "cfm_ma:ShortMANameData";
      when "../short-ma-name-format-value !="+
        " 'cfm-bag-sman-fmt-vlan-id' and"+
        " ../short-ma-name-format-value !="+
        " 'cfm-bag-sman-fmt-string' and"+
        " ../short-ma-name-format-value !="+
        " 'cfm-bag-sman-fmt-uint16' and"+
        " ../short-ma-name-format-value !="+
        " 'cfm-bag-sman-fmt-vpnid' and"+
        " ../short-ma-name-format-value != 'cfm-bag-sman-fmt-icc'" {
          description
            "../ShortMANameFormatValue !=
            'CFM_BAG_SMAN_FMT_VLAN_ID' and .
            ./ShortMANameFormatValue !=
            'CFM_BAG_SMAN_FMT_STRING' and .
            ./ShortMANameFormatValue !=
            'CFM_BAG_SMAN_FMT_UINT16' and .
            ./ShortMANameFormatValue !=
            'CFM_BAG_SMAN_FMT_VPNID' and .
            ./ShortMANameFormatValue !=
            'CFM_BAG_SMAN_FMT_ICC'";
      }
      type Cfm-bag-optional-hex-data;
      description "Hex data";
    }
  }

  grouping CFM-BAG-MDID-MAC-NAME {
    description "MDID MAC name";
    leaf mac-address {
      xr:xr-xml-map "cfm_ma:MACAddress";
      type Mac-address;
      description "MAC address";
    }
    leaf integer {
      xr:xr-xml-map "cfm_ma:Integer";
      type uint16;
      description "Integer";
    }
  }

  grouping CFM-BAG-MDID {
    description "MDID types";

    container mac-name {
      when "../mdid-format-value ="+
        " 'cfm-bag-mdid-fmt-mac-addr-uint'" {
          description
            "../MDIDFormatValue =
            'CFM_BAG_MDID_FMT_MACADDR_UINT'";
      }
      description "MAC address name";
      uses CFM-BAG-MDID-MAC-NAME;
    }
    leaf mdid-format-value {
      xr:xr-xml-map "cfm_ma:MDIDFormatValue";
      type uint32;
      description "MDIDFormatValue";
    }
    leaf dns-like-name {
      xr:xr-xml-map "cfm_ma:DNSLikeName";
      when "../mdid-format-value = 'cfm-bag-mdid-fmt-dns-like'" {
        description
          "../MDIDFormatValue = 'CFM_BAG_MDID_FMT_DNSLIKE'";
      }
      type Cfm-bag-optional-string;
      description "DNS-like name";
    }
    leaf string-name {
      xr:xr-xml-map "cfm_ma:StringName";
      when "../mdid-format-value = 'cfm-bag-mdid-fmt-string'" {
        description
          "../MDIDFormatValue = 'CFM_BAG_MDID_FMT_STRING'";
      }
      type Cfm-bag-optional-string;
      description "String name";
    }
    leaf mdid-data {
      xr:xr-xml-map "cfm_ma:MDIDData";
      when "../mdid-format-value != 'cfm-bag-mdid-fmt-dns-like'"+
        " and ../mdid-format-value !="+
        " 'cfm-bag-mdid-fmt-mac-addr-uint' and"+
        " ../mdid-format-value != 'cfm-bag-mdid-fmt-string'" {
          description
            "../MDIDFormatValue !=
            'CFM_BAG_MDID_FMT_DNSLIKE' and .
            ./MDIDFormatValue !=
            'CFM_BAG_MDID_FMT_MACADDR_UINT' and .
            ./MDIDFormatValue != 'CFM_BAG_MDID_FMT_STRING'";
      }
      type Cfm-bag-optional-hex-data;
      description "Hex data";
    }
  }

  grouping CFM-MA-MP {
    description "CFM MA Maintenance Point";
    leaf domain-name {
      xr:xr-xml-map "cfm_ma:DomainName";
      type string;
      description "Domain name";
    }
    leaf level {
      xr:xr-xml-map "cfm_ma:Level";
      type Cfm-bag-md-level;
      description "Domain level";
    }
    leaf service-name {
      xr:xr-xml-map "cfm_ma:ServiceName";
      type string;
      description "Service name";
    }
    leaf interface {
      xr:xr-xml-map "cfm_ma:Interface";
      type xr:Interface-name;
      description "Interface";
    }
    leaf maintenance-point-type {
      xr:xr-xml-map "cfm_ma:MaintenancePointType";
      type Cfm-ma-mp-variety;
      description "Type of Maintenance Point";
    }
    leaf mep-id {
      xr:xr-xml-map "cfm_ma:MEP_ID";
      type uint16;
      description "MEP ID";
    }
  }

  grouping CFM-MA-MP-BRIEF {
    description "CFM MA Maintenance Point Information";

    container maintenance-point {
      description "Maintenance Point";
      uses CFM-MA-MP;
    }
    leaf mep-has-error {
      xr:xr-xml-map "cfm_ma:MEPHasError";
      type boolean;
      description "MEP error flag";
    }
    leaf mac-address {
      xr:xr-xml-map "cfm_ma:MACAddress";
      type Mac-address;
      description "MAC Address";
    }
  }

  grouping CFM-MA-SUMMARY {
    description "CFM MA Summary Information";
    leaf domains {
      xr:xr-xml-map "cfm_ma:Domains";
      type uint32;
      description "The number of domains in the CFM database.";
    }
    leaf services {
      xr:xr-xml-map "cfm_ma:Services";
      type uint32;
      description "The number of services in the CFM database.";
    }
    leaf ccm-rate {
      xr:xr-xml-map "cfm_ma:CCMRate";
      type uint32;
      description "The combined rate of CCMs on this card.";
    }
    leaf local-meps {
      xr:xr-xml-map "cfm_ma:LocalMEPs";
      type uint32;
      description "The number of local MEPs in the CFM database.";
    }
    leaf operational-local-meps {
      xr:xr-xml-map "cfm_ma:OperationalLocalMEPs";
      type uint32;
      description "The number of operational local MEPs.";
    }
    leaf down-meps {
      xr:xr-xml-map "cfm_ma:DownMEPs";
      type uint32;
      description "The number of down-MEPs.";
    }
    leaf up-meps {
      xr:xr-xml-map "cfm_ma:UpMEPs";
      type uint32;
      description "The number of up-MEPs.";
    }
    leaf offloaded {
      xr:xr-xml-map "cfm_ma:Offloaded";
      type uint32;
      description
        "The number of MEPs for which CCM processing has
        been offloaded.";
    }
    leaf offloaded-at3-3ms {
      xr:xr-xml-map "cfm_ma:OffloadedAt3_3ms";
      type uint32;
      description
        "The number of MEPs offloaded with CCMs at 3.3ms
        intervals.";
    }
    leaf offloaded-at10ms {
      xr:xr-xml-map "cfm_ma:OffloadedAt10ms";
      type uint32;
      description
        "The number of MEPs offloaded with CCMs at 10ms
        intervals.";
    }
    leaf disabled-misconfigured {
      xr:xr-xml-map "cfm_ma:DisabledMisconfigured";
      type uint32;
      description
        "The number of local MEPs disabled due to
        configuration errors.";
    }
    leaf disabled-out-of-resources {
      xr:xr-xml-map "cfm_ma:DisabledOutOfResources";
      type uint32;
      description
        "The number of local MEPs disabled due to lack of
        resources.";
    }
    leaf disabled-operational-error {
      xr:xr-xml-map "cfm_ma:DisabledOperationalError";
      type uint32;
      description
        "The number of local MEPs disabled due to
        operational errors.";
    }
    leaf peer-meps {
      xr:xr-xml-map "cfm_ma:PeerMEPs";
      type uint32;
      description "The number of peer MEPs.";
    }
    leaf operational-peer-meps {
      xr:xr-xml-map "cfm_ma:OperationalPeerMEPs";
      type uint32;
      description
        "The number of operational peer MEPs recorded in
        the CFM database.";
    }
    leaf peer-meps-with-defects {
      xr:xr-xml-map "cfm_ma:PeerMEPsWithDefects";
      type uint32;
      description "The number of peer MEPs with defects.";
    }
    leaf peer-meps-without-defects {
      xr:xr-xml-map "cfm_ma:PeerMEPsWithoutDefects";
      type uint32;
      description "The number of peer MEPs without defects.";
    }
    leaf peer-meps-timed-out {
      xr:xr-xml-map "cfm_ma:PeerMEPsTimedOut";
      type uint32;
      description "The number of peer MEPs that have timed out.";
    }
    leaf mips {
      xr:xr-xml-map "cfm_ma:MIPs";
      type uint32;
      description "The number of MIPs";
    }
    leaf interfaces {
      xr:xr-xml-map "cfm_ma:Interfaces";
      type uint32;
      description "The number of interfaces running CFM.";
    }
    leaf bridge-domains-and-xconnects {
      xr:xr-xml-map "cfm_ma:BridgeDomainsAndXconnects";
      type uint32;
      description "Number or bridge domains and crossconnects.";
    }
    leaf traceroute-cache-entries {
      xr:xr-xml-map "cfm_ma:TracerouteCacheEntries";
      type uint32;
      description "Number of traceroute cache entries.";
    }
    leaf traceroute-cache-replies {
      xr:xr-xml-map "cfm_ma:TracerouteCacheReplies";
      type uint32;
      description "Number of traceroute cache replies.";
    }
    leaf ccm-learning-db-entries {
      xr:xr-xml-map "cfm_ma:CCMLearningDBEntries";
      type uint32;
      description "Number of entries in the CCM learning database.";
    }
    leaf issu-role {
      xr:xr-xml-map "cfm_ma:ISSURole";
      type Cfm-bag-issu-role;
      description "ISSU Role of CFM-D, if any.";
    }
    leaf bnm-enabled-links {
      xr:xr-xml-map "cfm_ma:BNMEnabledLinks";
      type uint32;
      description "Number of BNM Enabled Links";
    }
  }
}
