module Cisco-IOS-XR-ip-mobileip-cfg {

  /*** NAMESPACE / PREFIX DEFINITION ***/

  namespace "http://cisco.com/ns/yang/Cisco-IOS-XR-ip-mobileip-cfg";


  prefix "ip-mobileip-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-mobileip package configuration.

     This module contains definitions
     for the following management objects:
       mobile-ip: MobileIP configuration

     Copyright (c) 2013-2015 by Cisco Systems, Inc.
     All rights reserved.";

  revision "2015-11-09" {
    description
      "IOS XR 6.0 revision.";
  }

  revision "2015-09-02" {
    description
      "Revision description string.";
  }

  typedef Service-type {
    type enumeration {
      enum ipv4 {
        value 1;
        description "ipv4 service type";
      }
      enum ipv6 {
        value 2;
        description "ipv6 service type";
      }
      enum dual {
        value 3;
        description "dual service type";
      }
    }
    description "Service type";
  }
  typedef Lma-service {
    type enumeration {
      enum service-mll {
        value 1;
        description "Wireless Private Routing service";
      }
    }
    description "Lma service";
  }
  typedef Lma-role {
    type enumeration {
      enum 3gma {
        value 0;
        description "3GMA mode";
      }
    }
    description "Lma role";
  }
  typedef Lma-rat {
    type enumeration {
      enum virtual {
        value 0;
        description "VIRTUAL rat";
      }
      enum ppp {
        value 1;
        description "PPP rat";
      }
      enum ethernet {
        value 2;
        description "ETHERNET rat";
      }
      enum wlan {
        value 3;
        description "WLAN rat";
      }
      enum wi-max {
        value 4;
        description "WIMAX rat";
      }
      enum 3gppgeran {
        value 5;
        description "3GPP_GERAN rat";
      }
      enum 3gpputran {
        value 6;
        description "3GPP_UTRAN rat";
      }
      enum 3gppeutran {
        value 7;
        description "3GPP_E_UTRAN rat";
      }
      enum 3gpp2ehrpd {
        value 8;
        description "3GPP2_EHRPD rat";
      }
      enum 3gpp2hrpd {
        value 9;
        description "3GPP2_HRPD rat";
      }
      enum 3gpp21rtt {
        value 10;
        description "3GPP2_1RTT rat";
      }
      enum 3gpp2umb {
        value 11;
        description "3GPP2_UMB rat";
      }
    }
    description "Lma rat";
  }
  typedef Encap-opt {
    type enumeration {
      enum greipv4 {
        value 4;
        description "GRE IPv4 tunnel encap";
      }
      enum greipv6 {
        value 5;
        description "GRE IPv6 tunnel encap";
      }
      enum mgreipv4 {
        value 7;
        description "mGRE IPv4 tunnel encap";
      }
      enum mgreipv6 {
        value 8;
        description "mGRE IPv6 tunnel encap";
      }
    }
    description "Encap opt";
  }

  container mobile-ip {
    xr:xr-xml-map "ipv6_pmipv6_domain_mode_cfg:MobileIP";
    description "MobileIP configuration";

    container domains {
      xr:xr-xml-map "ipv6_pmipv6_domain_mode_cfg:DomainTable";
      description "Table of Domain";

      list domain {
        xr:xr-xml-map "ipv6_pmipv6_domain_mode_cfg:Domain";
        key "domain-name";
        description "PMIPv6 domain configuration";

        container mags {
          xr:xr-xml-map "ipv6_pmipv6_domain_submodes_cfg:MAGTable";
          description "Table of MAG";

          list mag {
            xr:xr-xml-map "ipv6_pmipv6_domain_submodes_cfg:MAG";
            key "mag-name";
            description "MAG within domain";
            leaf mag-name {
              xr:xr-xml-map "ipv6_pmipv6_domain_submodes_cfg:MAGNam"+
                "e";
              type xr:Cisco-ios-xr-string {
                length "0..125";
              }
              description "MAG Identifier";
            }
          }
        }

        container nais {
          xr:xr-xml-map "ipv6_pmipv6_domain_submodes_cfg:NAITable";
          description "Table of NAI";

          list nai {
            xr:xr-xml-map "ipv6_pmipv6_domain_submodes_cfg:NAI";
            key "nai-name";
            description "Network access identifier or Realm";
            leaf lma {
              xr:xr-xml-map "ipv6_pmipv6_domain_cfg:LMA";
              type string {
                length "0..125";
              }
              description "LMA for this MN";
            }
            leaf apn {
              xr:xr-xml-map "ipv6_pmipv6_domain_cfg:APN";
              type string {
                length "0..125";
              }
              description "Access point network for this MN";
            }
            leaf customer {
              xr:xr-xml-map "ipv6_pmipv6_domain_cfg:Customer";
              type xr:Cisco-ios-xr-string {
                length "0..125";
              }
              description "Customer name for this MN";
            }
            leaf service {
              xr:xr-xml-map "ipv6_pmipv6_domain_cfg:Service";
              type Service-type;
              description "Service type for this MN";
            }
            leaf network {
              xr:xr-xml-map "ipv6_pmipv6_domain_cfg:Network";
              type string {
                length "0..125";
              }
              description "Network name (Address pool) for this MN";
            }
            leaf nai-name {
              xr:xr-xml-map "ipv6_pmipv6_domain_submodes_cfg:NAINam"+
                "e";
              type string {
                length "0..125";
              }
              description "MN Identifier";
            }
          }
        }

        container authenticate-option {
          xr:xr-xml-map "ipv6_pmipv6_domain_cfg:AuthenticateOption";
          description
            "Authentication option between PMIPV6 entities";
          leaf spi {
            xr:xr-xml-map "ipv6_pmipv6_domain_cfg:SPI";
            type xr:Hex-integer;
            description "SPI in hex value";
          }
          leaf key {
            xr:xr-xml-map "ipv6_pmipv6_domain_cfg:Key";
            type string {
              length "0..125";
            }
            description "ASCII string";
          }
        }

        container lmas {
          xr:xr-xml-map "ipv6_pmipv6_domain_submodes_cfg:LMATable";
          description "Table of LMA";

          list lma {
            xr:xr-xml-map "ipv6_pmipv6_domain_submodes_cfg:LMA";
            key "lma-name";
            description "LMA within domain";
            leaf lma-name {
              xr:xr-xml-map "ipv6_pmipv6_domain_submodes_cfg:LMANam"+
                "e";
              type xr:Cisco-ios-xr-string {
                length "0..125";
              }
              description "LMA Identifier";
            }
          }
        }
        leaf enable {
          xr:xr-xml-map "ipv6_pmipv6_domain_mode_cfg:Enable";
          type empty;
          description
            "Enable PMIPv6 domain configuration. Deletion
            of this object also causes deletion of all
            associated objects under Domain.";
        }
        leaf domain-name {
          xr:xr-xml-map "ipv6_pmipv6_domain_mode_cfg:DomainName";
          type xr:Cisco-ios-xr-string {
            length "0..125";
          }
          description "Domain Name";
        }
      }
    }

    container lmas {
      xr:xr-xml-map "ipv6_pmipv6_lma_mode_cfg:LMATable";
      description "Table of LMA";

      list lma {
        xr:xr-xml-map "ipv6_pmipv6_lma_mode_cfg:LMA";
        key "lma-name domain-name";
        description "PMIPv6 LMA configuration";

        container binding-revocation-attributes {
          xr:xr-xml-map "ipv6_pmipv6_lma_cfg:BindingRevocationAttri"+
            "butes";
          description "LMA Binding Revocation Attributes";

          container delay {
            xr:xr-xml-map "ipv6_pmipv6_lma_cfg:Delay";
            description
              "Time to wait before Retransmitting BRI
              Message";
            leaf minimum {
              xr:xr-xml-map "ipv6_pmipv6_lma_cfg:Minimum";
              type uint32 {
                range "500..65535";
              }
              description "Minimum time delay to send BRI";
            }
            leaf maximum {
              xr:xr-xml-map "ipv6_pmipv6_lma_cfg:Maximum";
              type uint32 {
                range "500..65535";
              }
              description "Maximum time delay to send BRI";
            }
          }
          leaf retry {
            xr:xr-xml-map "ipv6_pmipv6_lma_cfg:Retry";
            type uint32 {
              range "1..10";
            }
            description
              "Number of Retransmissons Allowed for BRI
              Message";
          }
        }

        container rat-attributes {
          xr:xr-xml-map "ipv6_pmipv6_lma_cfg:RatAttributes";
          description
            "Radio access technology type config  this LMA";
          leaf lma-rat {
            xr:xr-xml-map "ipv6_pmipv6_lma_cfg:LMARat";
            type Lma-rat;
            description "LMA rat type";
          }
          leaf priority-value {
            xr:xr-xml-map "ipv6_pmipv6_lma_cfg:PriorityValue";
            type uint32 {
              range "1..255";
            }
            description "Specify the priority value";
          }
        }

        container heart-beat-attributes {
          xr:xr-xml-map "ipv6_pmipv6_lma_cfg:HeartBeatAttributes";
          description "heartbeat config for this LMA";
          leaf interval {
            xr:xr-xml-map "ipv6_pmipv6_lma_cfg:Interval";
            type uint32 {
              range "10..3600";
            }
            description "Specify the interval value in second";
          }
          leaf retries {
            xr:xr-xml-map "ipv6_pmipv6_lma_cfg:Retries";
            type uint32 {
              range "1..10";
            }
            description "Specify the retry value";
          }
          leaf timeout {
            xr:xr-xml-map "ipv6_pmipv6_lma_cfg:Timeout";
            type uint32 {
              range "1..3600";
            }
            description "Specify the timeout value";
          }
        }

        container lmaipv6-addresses {
          xr:xr-xml-map "ipv6_pmipv6_lma_cfg:LMAIPv6AddressTable";
          description "Table of LMAIPv6Address";

          list lmaipv6-address {
            xr:xr-xml-map "ipv6_pmipv6_lma_cfg:LMAIPv6Address";
            key "address";
            description "Configure IPv6 address for this LMA";
            leaf address {
              xr:xr-xml-map "ipv6_pmipv6_lma_cfg:Address";
              type inet:ipv6-address-no-zone;
              description "LMA IPv6 address";
            }
          }
        }

        container hnp {
          xr:xr-xml-map "ipv6_pmipv6_lma_cfg:Hnp";
          description "LMA HNP options";
          leaf maximum {
            xr:xr-xml-map "ipv6_pmipv6_lma_cfg:Maximum";
            type uint32 {
              range "1..3";
            }
            description "maximum HNPs allowed per MN interface";
          }
        }

        container redistribute {
          xr:xr-xml-map "ipv6_pmipv6_lma_cfg:Redistribute";
          description "Redistribute routes";
          leaf redist-type {
            xr:xr-xml-map "ipv6_pmipv6_lma_cfg:RedistType";
            type int32;
            description "Set constant integer";
          }
          leaf redist-sub-type {
            xr:xr-xml-map "ipv6_pmipv6_lma_cfg:RedistSubType";
            type int32;
            description "Set constant integer";
          }
        }

        container dscp {
          xr:xr-xml-map "ipv6_pmipv6_lma_cfg:DSCP";
          description "DSCP for packets originating from this LMA";
          leaf value {
            xr:xr-xml-map "ipv6_pmipv6_lma_cfg:Value";
            type uint32 {
              range "1..63";
            }
            description "Specify the DSCP value";
          }
          leaf force {
            xr:xr-xml-map "ipv6_pmipv6_lma_cfg:Force";
            type int32;
            description "Set constant integer";
          }
        }

        container lmaipv4-addresses {
          xr:xr-xml-map "ipv6_pmipv6_lma_cfg:LMAIPv4AddressTable";
          description "Table of LMAIPv4Address";

          list lmaipv4-address {
            xr:xr-xml-map "ipv6_pmipv6_lma_cfg:LMAIPv4Address";
            key "address";
            description "Configure IPv4 address for this LMA";
            leaf address {
              xr:xr-xml-map "ipv6_pmipv6_lma_cfg:Address";
              type inet:ipv4-address-no-zone;
              description "LMA IPv4 address";
            }
          }
        }

        container roles {
          xr:xr-xml-map "ipv6_pmipv6_lma_submodes_cfg:RoleTable";
          description "Table of Role";

          list role {
            xr:xr-xml-map "ipv6_pmipv6_lma_submodes_cfg:Role";
            key "lma-role";
            description "Role of this LMA";
            leaf lma-role {
              xr:xr-xml-map "ipv6_pmipv6_lma_submodes_cfg:LMARole";
              type Lma-role;
              description "LMA role mode";
            }
          }
        }

        container binding-attributes {
          xr:xr-xml-map "ipv6_pmipv6_lma_cfg:BindingAttributes";
          description "LMA binding attributes";
          leaf refresh-time {
            xr:xr-xml-map "ipv6_pmipv6_lma_cfg:RefreshTime";
            type uint32 {
              range "4..65000";
            }
            units "second";
            description "Specify in seconds, (multiples of 4)";
          }
          leaf delete-wait-interval {
            xr:xr-xml-map "ipv6_pmipv6_lma_cfg:DeleteWaitInterval";
            type uint32 {
              range "100..65535";
            }
            description "bce delete wait time interval";
          }
          leaf create-wait-interval {
            xr:xr-xml-map "ipv6_pmipv6_lma_cfg:CreateWaitInterval";
            type uint32 {
              range "100..65535";
            }
            description "bce create wait time interval";
          }
          leaf max-life-time {
            xr:xr-xml-map "ipv6_pmipv6_lma_cfg:MaxLifeTime";
            type uint32 {
              range "10..65535";
            }
            units "second";
            description "Maximum bce lifetime permitted";
          }
          leaf maximum {
            xr:xr-xml-map "ipv6_pmipv6_lma_cfg:Maximum";
            type uint32 {
              range "1..128000";
            }
            description "Specify max. number of bindings";
          }
        }

        container aaa {
          xr:xr-xml-map "ipv6_pmipv6_lma_cfg:AAA";
          description "aaa config attributes for this LMA";
          leaf enable {
            xr:xr-xml-map "ipv6_pmipv6_lma_cfg:Enable";
            type int32;
            description "Set constant integer";
          }
          leaf interim-interval {
            xr:xr-xml-map "ipv6_pmipv6_lma_cfg:InterimInterval";
            type int32;
            description "Set constant integer";
          }
        }

        container mags {
          xr:xr-xml-map "ipv6_pmipv6_lma_submodes_cfg:MAGTable";
          description "Table of MAG";

          list mag {
            xr:xr-xml-map "ipv6_pmipv6_lma_submodes_cfg:MAG";
            key "mag-name domain-name";
            description "MAG within LMA";

            container authenticate-option {
              xr:xr-xml-map "ipv6_pmipv6_lma_cfg:AuthenticateOption";
              description
                "Authentication option between PMIPV6
                entities";
              leaf spi {
                xr:xr-xml-map "ipv6_pmipv6_lma_cfg:SPI";
                type xr:Hex-integer;
                description "SPI in hex value";
              }
              leaf key {
                xr:xr-xml-map "ipv6_pmipv6_lma_cfg:Key";
                type string {
                  length "0..125";
                }
                description "ASCII string";
              }
            }

            container dscp {
              xr:xr-xml-map "ipv6_pmipv6_lma_cfg:DSCP";
              description
                "DSCP for packets originating from this MAG";
              leaf value {
                xr:xr-xml-map "ipv6_pmipv6_lma_cfg:Value";
                type uint32 {
                  range "1..63";
                }
                description "Specify the DSCP value";
              }
              leaf force {
                xr:xr-xml-map "ipv6_pmipv6_lma_cfg:Force";
                type int32;
                description "Set constant integer";
              }
            }
            leaf encap-option {
              xr:xr-xml-map "ipv6_pmipv6_lma_cfg:EncapOption";
              type Encap-opt;
              description
                "Encapsulation option between PMIPV6 entities";
            }
            leaf ipv4-address {
              xr:xr-xml-map "ipv6_pmipv6_lma_cfg:IPv4Address";
              type inet:ipv4-address-no-zone;
              description "Configure IPv4 address for this MAG";
            }
            leaf ipv6-address {
              xr:xr-xml-map "ipv6_pmipv6_lma_cfg:IPv6Address";
              type inet:ipv6-address-no-zone;
              description "Configure IPv6 address for this MAG";
            }
            leaf tunnel {
              xr:xr-xml-map "ipv6_pmipv6_lma_cfg:Tunnel";
              type xr:Interface-name;
              description "static tunnel for this peer MAG";
            }
            leaf mag-name {
              xr:xr-xml-map "ipv6_pmipv6_lma_submodes_cfg:MAGName";
              type string {
                length "0..125";
              }
              description "MAG identifier";
            }
            leaf domain-name {
              xr:xr-xml-map "ipv6_pmipv6_lma_submodes_cfg:DomainNam"+
                "e";
              type string {
                length "0..125";
              }
              description "Domain name";
            }
          }
        }

        container tunnel-attributes {
          xr:xr-xml-map "ipv6_pmipv6_lma_cfg:TunnelAttributes";
          description "tunnel attributes";
          leaf mtu {
            xr:xr-xml-map "ipv6_pmipv6_lma_cfg:Mtu";
            type uint32 {
              range "68..17916";
            }
            description "maximum transmission unit for tunnel";
          }
          leaf acl {
            xr:xr-xml-map "ipv6_pmipv6_lma_cfg:Acl";
            type string {
              length "0..125";
            }
            description "access list to apply for tunnel";
          }
        }

        container services {
          xr:xr-xml-map "ipv6_pmipv6_lma_submodes_cfg:ServiceTable";
          description "Table of Service";

          list service {
            xr:xr-xml-map "ipv6_pmipv6_lma_submodes_cfg:Service";
            key "lma-service";
            description "Service of this LMA";

            container customers {
              xr:xr-xml-map "ipv6_pmipv6_lma_service_mode_cfg:Custo"+
                "merTable";
              description "Table of Customer";

              list customer {
                xr:xr-xml-map "ipv6_pmipv6_lma_service_mode_cfg:Cus"+
                  "tomer";
                key "customer-name vrf-name";
                description
                  "customer configuration on this mobile local
                  loop service";

                container authenticate-option {
                  xr:xr-xml-map "ipv6_pmipv6_lma_service_cust_cfg:A"+
                    "uthenticateOption";
                  description
                    "Authentication option between PMIPV6
                    entities";
                  leaf spi {
                    xr:xr-xml-map "ipv6_pmipv6_lma_service_cust_cfg"+
                      ":SPI";
                    type xr:Hex-integer;
                    description "SPI in hex value";
                  }
                  leaf key {
                    xr:xr-xml-map "ipv6_pmipv6_lma_service_cust_cfg"+
                      ":Key";
                    type string {
                      length "0..125";
                    }
                    description "ASCII string";
                  }
                }

                container heart-beat-attributes {
                  xr:xr-xml-map "ipv6_pmipv6_lma_service_cust_cfg:H"+
                    "eartBeatAttributes";
                  description "heartbeat config for this Customer";
                  leaf interval {
                    xr:xr-xml-map "ipv6_pmipv6_lma_service_cust_cfg"+
                      ":Interval";
                    type uint32 {
                      range "10..3600";
                    }
                    description
                      "Specify the interval value in second";
                  }
                  leaf retries {
                    xr:xr-xml-map "ipv6_pmipv6_lma_service_cust_cfg"+
                      ":Retries";
                    type uint32 {
                      range "1..10";
                    }
                    description "Specify the retry value";
                  }
                  leaf timeout {
                    xr:xr-xml-map "ipv6_pmipv6_lma_service_cust_cfg"+
                      ":Timeout";
                    type uint32 {
                      range "1..3600";
                    }
                    description "Specify the timeout value";
                  }
                }

                container transports {
                  xr:xr-xml-map "ipv6_pmipv6_lma_service_cust_cfg:T"+
                    "ransportTable";
                  description "Table of Transport";

                  list transport {
                    xr:xr-xml-map "ipv6_pmipv6_lma_service_cust_cfg"+
                      ":Transport";
                    key "vrf-name";
                    description "Customer transport attributes";
                    leaf ipv4-address {
                      xr:xr-xml-map "ipv6_pmipv6_lma_service_cust_s"+
                        "ubmode_cfg:IPv4Address";
                      type inet:ipv4-address-no-zone;
                      description
                        "Configure IPv4 address for this LMA";
                    }
                    leaf ipv6-address {
                      xr:xr-xml-map "ipv6_pmipv6_lma_service_cust_s"+
                        "ubmode_cfg:IPv6Address";
                      type inet:ipv6-address-no-zone;
                      description
                        "Configure IPv6 address for this LMA";
                    }
                    leaf vrf-name {
                      xr:xr-xml-map "ipv6_pmipv6_lma_service_cust_c"+
                        "fg:VrfName";
                      type string {
                        length "0..125";
                      }
                      description "VRF Name";
                    }
                  }
                }

                container network-attributes {
                  xr:xr-xml-map "ipv6_pmipv6_lma_service_cust_cfg:N"+
                    "etworkAttributes";
                  description "network parameters for the customer";

                  container authorizes {
                    xr:xr-xml-map "ipv6_pmipv6_lma_service_cust_cfg"+
                      ":AuthorizeTable";
                    description "Table of Authorize";

                    list authorize {
                      xr:xr-xml-map "ipv6_pmipv6_lma_service_cust_c"+
                        "fg:Authorize";
                      key "name";
                      description
                        "not authorize the network prefixes";

                      container pool-attributes {
                        xr:xr-xml-map "ipv6_pmipv6_lma_cust_nw_subm"+
                          "ode:PoolAttributes";
                        description "Pool configs for this network";

                        container mobile-node {
                          xr:xr-xml-map "ipv6_pmipv6_lma_cust_nw_su"+
                            "bmode:MobileNode";
                          description
                            "pool configs for the mobile nodes";

                          container ipv4-pool {
                            xr:xr-xml-map "ipv6_pmipv6_lma_cust_nw_"+
                              "submode:IPV4Pool";
                            description "None";
                            leaf start-address {
                              xr:xr-xml-map "ipv6_pmipv6_lma_cust_n"+
                                "w_submode:StartAddress";
                              type inet:ipv4-address-no-zone;
                              description "Pool IPv4 start address";
                            }
                            leaf pool-prefix {
                              xr:xr-xml-map "ipv6_pmipv6_lma_cust_n"+
                                "w_submode:PoolPrefix";
                              type uint32 {
                                range "8..30";
                              }
                              description "IPv4 Pool Prefix value";
                            }
                          }

                          container ipv6-pool {
                            xr:xr-xml-map "ipv6_pmipv6_lma_cust_nw_"+
                              "submode:IPV6Pool";
                            description "None";
                            leaf start-address {
                              xr:xr-xml-map "ipv6_pmipv6_lma_cust_n"+
                                "w_submode:StartAddress";
                              type inet:ipv6-address-no-zone;
                              description "Pool IPv6 start address";
                            }
                            leaf pool-prefix {
                              xr:xr-xml-map "ipv6_pmipv6_lma_cust_n"+
                                "w_submode:PoolPrefix";
                              type uint32 {
                                range "8..62";
                              }
                              description "IPv6 Pool Prefix value";
                            }
                          }
                        }

                        container mobile-network {
                          xr:xr-xml-map "ipv6_pmipv6_lma_cust_nw_su"+
                            "bmode:MobileNetwork";
                          description
                            "pool configs for the mobile network";

                          container mripv4-pools {
                            xr:xr-xml-map "ipv6_pmipv6_lma_cust_nw_"+
                              "submode:MRIPV4PoolTable";
                            description "Table of MRIPV4Pool";

                            list mripv4-pool {
                              xr:xr-xml-map "ipv6_pmipv6_lma_cust_n"+
                                "w_submode:MRIPV4Pool";
                              key "start-address";
                              description "ipv4 pool";
                              leaf start-address {
                                xr:xr-xml-map "ipv6_pmipv6_lma_cust"+
                                  "_nw_submode:StartAddress";
                                type inet:ipv4-address-no-zone;
                                description
                                  "Pool IPv4 start address";
                              }
                              leaf pool-prefix {
                                xr:xr-xml-map "ipv6_pmipv6_lma_cust"+
                                  "_nw_submode:PoolPrefix";
                                type uint32 {
                                  range "8..30";
                                }
                                description
                                  "IPv4 Pool Prefix value";
                              }
                              leaf network-prefix {
                                xr:xr-xml-map "ipv6_pmipv6_lma_cust"+
                                  "_nw_submode:NetworkPrefix";
                                type uint32 {
                                  range "8..32";
                                }
                                description
                                  "IPv4 Network Prefix value";
                              }
                            }
                          }

                          container mripv6-pools {
                            xr:xr-xml-map "ipv6_pmipv6_lma_cust_nw_"+
                              "submode:MRIPV6PoolTable";
                            description "Table of MRIPV6Pool";

                            list mripv6-pool {
                              xr:xr-xml-map "ipv6_pmipv6_lma_cust_n"+
                                "w_submode:MRIPV6Pool";
                              key "start-address";
                              description "ipv6 pool";
                              leaf start-address {
                                xr:xr-xml-map "ipv6_pmipv6_lma_cust"+
                                  "_nw_submode:StartAddress";
                                type inet:ipv6-address-no-zone;
                                description
                                  "Pool IPv6 start address";
                              }
                              leaf pool-prefix {
                                xr:xr-xml-map "ipv6_pmipv6_lma_cust"+
                                  "_nw_submode:PoolPrefix";
                                type uint32 {
                                  range "8..64";
                                }
                                description
                                  "IPv6 Pool Prefix value";
                              }
                              leaf network-prefix {
                                xr:xr-xml-map "ipv6_pmipv6_lma_cust"+
                                  "_nw_submode:NetworkPrefix";
                                type uint32 {
                                  range "8..64";
                                }
                                description
                                  "IPv4 Network Prefix value";
                              }
                            }
                          }
                        }
                      }
                      leaf name {
                        xr:xr-xml-map "ipv6_pmipv6_lma_service_cust"+
                          "_cfg:Name";
                        type string {
                          length "0..125";
                        }
                        description "ASCII string";
                      }
                    }
                  }
                  leaf unauthorize {
                    xr:xr-xml-map "ipv6_pmipv6_lma_service_cust_cfg"+
                      ":Unauthorize";
                    type empty;
                    description
                      "not authorize the network prefixes";
                  }
                }

                container gre-key {
                  xr:xr-xml-map "ipv6_pmipv6_lma_service_cust_cfg:G"+
                    "reKey";
                  description "Customer specific GRE key";
                  leaf gre-key-type {
                    xr:xr-xml-map "ipv6_pmipv6_lma_service_cust_cfg"+
                      ":GreKeyType";
                    type int32;
                    description "Set constant integer";
                  }
                  leaf gre-key-value {
                    xr:xr-xml-map "ipv6_pmipv6_lma_service_cust_cfg"+
                      ":GreKeyValue";
                    type int32;
                    description "GRE key value";
                  }
                }

                container binding-attributes {
                  xr:xr-xml-map "ipv6_pmipv6_lma_service_cust_cfg:B"+
                    "indingAttributes";
                  description
                    "Customer specific binding attributes";
                  leaf max-life-time {
                    xr:xr-xml-map "ipv6_pmipv6_lma_service_cust_cfg"+
                      ":MaxLifeTime";
                    type uint32 {
                      range "10..65535";
                    }
                    units "second";
                    description "Maximum bce lifetime permitted";
                  }
                }
                leaf mnp-customer {
                  xr:xr-xml-map "ipv6_pmipv6_lma_service_cust_cfg:M"+
                    "npCustomer";
                  type uint32 {
                    range "1..4000000";
                  }
                  description "mnp limit config for customer";
                }
                leaf mnp-ipv4-lmn {
                  xr:xr-xml-map "ipv6_pmipv6_lma_service_cust_cfg:M"+
                    "npIPv4Lmn";
                  type uint32 {
                    range "1..32";
                  }
                  description
                    "mnp limit config for customer specific
                    logical mn";
                }
                leaf mnp-ipv6-lmn {
                  xr:xr-xml-map "ipv6_pmipv6_lma_service_cust_cfg:M"+
                    "npIPv6Lmn";
                  type uint32 {
                    range "1..32";
                  }
                  description
                    "mnp limit config for customer specific
                    logical mn";
                }
                leaf mnp-lmn {
                  xr:xr-xml-map "ipv6_pmipv6_lma_service_cust_cfg:M"+
                    "npLmn";
                  type uint32 {
                    range "1..32";
                  }
                  description
                    "mnp limit config for customer specific
                    logical mn";
                }
                leaf mnp-ipv4-customer {
                  xr:xr-xml-map "ipv6_pmipv6_lma_service_cust_cfg:M"+
                    "npIPv4Customer";
                  type uint32 {
                    range "1..4000000";
                  }
                  description "mnp limit config for customer";
                }
                leaf mnp-ipv6-customer {
                  xr:xr-xml-map "ipv6_pmipv6_lma_service_cust_cfg:M"+
                    "npIPv6Customer";
                  type uint32 {
                    range "1..4000000";
                  }
                  description "mnp limit config for customer";
                }
                leaf mobile-route-ad {
                  xr:xr-xml-map "ipv6_pmipv6_lma_service_cust_cfg:M"+
                    "obileRouteAD";
                  type uint32 {
                    range "1..254";
                  }
                  description "Specify the Admin Distance value";
                }
                leaf bandwidth-aggregate {
                  xr:xr-xml-map "ipv6_pmipv6_lma_service_cust_cfg:B"+
                    "andwidthAggregate";
                  type int32;
                  units "kbit/s";
                  description
                    "Aggregate bandwidth across all logical MNs";
                }
                leaf customer-name {
                  xr:xr-xml-map "ipv6_pmipv6_lma_service_mode_cfg:C"+
                    "ustomerName";
                  type string {
                    length "0..125";
                  }
                  description "Customer name";
                }
                leaf vrf-name {
                  xr:xr-xml-map "ipv6_pmipv6_lma_service_mode_cfg:V"+
                    "RFName";
                  type string {
                    length "0..125";
                  }
                  description "VRF name";
                }
              }
            }
            leaf ignore {
              xr:xr-xml-map "ipv6_pmipv6_lma_service_mode_cfg:Ignor"+
                "e";
              type empty;
              description
                "ignore options for mobile local loop service";
            }
            leaf mnp-customer {
              xr:xr-xml-map "ipv6_pmipv6_lma_service_mode_cfg:MnpCu"+
                "stomer";
              type uint32 {
                range "1..4000000";
              }
              description "mnp limit config for all customer's";
            }
            leaf mnp-ipv4-lmn {
              xr:xr-xml-map "ipv6_pmipv6_lma_service_mode_cfg:MnpIP"+
                "v4Lmn";
              type uint32 {
                range "1..32";
              }
              description "mnp limit config for all logical mn's";
            }
            leaf mnp-ipv6-lmn {
              xr:xr-xml-map "ipv6_pmipv6_lma_service_mode_cfg:MnpIP"+
                "v6Lmn";
              type uint32 {
                range "1..32";
              }
              description "mnp limit config for all logical mn's";
            }
            leaf mnp-lmn {
              xr:xr-xml-map "ipv6_pmipv6_lma_service_mode_cfg:MnpLm"+
                "n";
              type uint32 {
                range "1..32";
              }
              description "mnp limit config for all logical mn's";
            }
            leaf mnp-ipv4-customer {
              xr:xr-xml-map "ipv6_pmipv6_lma_service_mode_cfg:MnpIP"+
                "v4Customer";
              type uint32 {
                range "1..4000000";
              }
              description "mnp limit config for all customer's";
            }
            leaf mnp-ipv6-customer {
              xr:xr-xml-map "ipv6_pmipv6_lma_service_mode_cfg:MnpIP"+
                "v6Customer";
              type uint32 {
                range "1..4000000";
              }
              description "mnp limit config for all customer's";
            }
            leaf lma-service {
              xr:xr-xml-map "ipv6_pmipv6_lma_submodes_cfg:LMAServic"+
                "e";
              type Lma-service;
              description "LMA service mode";
            }
          }
        }

        container replay-protection {
          xr:xr-xml-map "ipv6_pmipv6_lma_cfg:ReplayProtection";
          description "Replay Protection Method";
          leaf validity-window {
            xr:xr-xml-map "ipv6_pmipv6_lma_cfg:ValidityWindow";
            type uint32 {
              range "1..255";
            }
            units "second";
            description "Specify window value in seconds";
          }
          leaf ignore {
            xr:xr-xml-map "ipv6_pmipv6_lma_cfg:Ignore";
            type int32;
            description "Set constant integer";
          }
        }

        container networks {
          xr:xr-xml-map "ipv6_pmipv6_lma_submodes_cfg:NetworkTable";
          description "Table of Network";

          list network {
            xr:xr-xml-map "ipv6_pmipv6_lma_submodes_cfg:Network";
            key "lma-network";
            description "network for this LMA";

            container pool-attributes {
              xr:xr-xml-map "ipv6_pmipv6_lma_cfg:PoolAttributes";
              description "Pool configs for this network";

              container mobile-node {
                xr:xr-xml-map "ipv6_pmipv6_lma_cfg:MobileNode";
                description "pool configs for the mobile nodes";

                container ipv4-pool {
                  xr:xr-xml-map "ipv6_pmipv6_lma_cfg:IPV4Pool";
                  description "None";
                  leaf start-address {
                    xr:xr-xml-map "ipv6_pmipv6_lma_cfg:StartAddress";
                    type inet:ipv4-address-no-zone;
                    description "Pool IPv4 start address";
                  }
                  leaf pool-prefix {
                    xr:xr-xml-map "ipv6_pmipv6_lma_cfg:PoolPrefix";
                    type uint32 {
                      range "8..30";
                    }
                    description "IPv4 Pool Prefix value";
                  }
                }

                container ipv6-pool {
                  xr:xr-xml-map "ipv6_pmipv6_lma_cfg:IPV6Pool";
                  description "None";
                  leaf start-address {
                    xr:xr-xml-map "ipv6_pmipv6_lma_cfg:StartAddress";
                    type inet:ipv6-address-no-zone;
                    description "Pool IPv6 start address";
                  }
                  leaf pool-prefix {
                    xr:xr-xml-map "ipv6_pmipv6_lma_cfg:PoolPrefix";
                    type uint32 {
                      range "8..62";
                    }
                    description "IPv6 Pool Prefix value";
                  }
                }
              }

              container mobile-network {
                xr:xr-xml-map "ipv6_pmipv6_lma_cfg:MobileNetwork";
                description "pool configs for the mobile network";

                container mripv6-pools {
                  xr:xr-xml-map "ipv6_pmipv6_lma_cfg:MRIPV6PoolTabl"+
                    "e";
                  description "Table of MRIPV6Pool";

                  list mripv6-pool {
                    xr:xr-xml-map "ipv6_pmipv6_lma_cfg:MRIPV6Pool";
                    key "start-address";
                    description "ipv6 pool";
                    leaf start-address {
                      xr:xr-xml-map "ipv6_pmipv6_lma_cfg:StartAddre"+
                        "ss";
                      type inet:ipv6-address-no-zone;
                      description "Pool IPv6 start address";
                    }
                    leaf pool-prefix {
                      xr:xr-xml-map "ipv6_pmipv6_lma_cfg:PoolPrefix";
                      type uint32 {
                        range "8..64";
                      }
                      description "IPv6 Pool Prefix value";
                    }
                    leaf network-prefix {
                      xr:xr-xml-map "ipv6_pmipv6_lma_cfg:NetworkPre"+
                        "fix";
                      type uint32 {
                        range "8..64";
                      }
                      description "IPv4 Network Prefix value";
                    }
                  }
                }

                container mripv4-pools {
                  xr:xr-xml-map "ipv6_pmipv6_lma_cfg:MRIPV4PoolTabl"+
                    "e";
                  description "Table of MRIPV4Pool";

                  list mripv4-pool {
                    xr:xr-xml-map "ipv6_pmipv6_lma_cfg:MRIPV4Pool";
                    key "start-address";
                    description "ipv4 pool";
                    leaf start-address {
                      xr:xr-xml-map "ipv6_pmipv6_lma_cfg:StartAddre"+
                        "ss";
                      type inet:ipv4-address-no-zone;
                      description "Pool IPv4 start address";
                    }
                    leaf pool-prefix {
                      xr:xr-xml-map "ipv6_pmipv6_lma_cfg:PoolPrefix";
                      type uint32 {
                        range "8..30";
                      }
                      description "IPv4 Pool Prefix value";
                    }
                    leaf network-prefix {
                      xr:xr-xml-map "ipv6_pmipv6_lma_cfg:NetworkPre"+
                        "fix";
                      type uint32 {
                        range "8..32";
                      }
                      description "IPv4 Network Prefix value";
                    }
                  }
                }
              }
            }
            leaf lma-network {
              xr:xr-xml-map "ipv6_pmipv6_lma_submodes_cfg:LMANetwor"+
                "k";
              type string {
                length "0..125";
              }
              description "Network name";
            }
          }
        }
        leaf generate {
          xr:xr-xml-map "ipv6_pmipv6_lma_cfg:Generate";
          type empty;
          description "generate gre key for LMA bindings";
        }
        leaf mobile-route-ad {
          xr:xr-xml-map "ipv6_pmipv6_lma_cfg:MobileRouteAD";
          type uint32 {
            range "1..254";
          }
          description "Specify the Admin Distance value";
        }
        leaf ani {
          xr:xr-xml-map "ipv6_pmipv6_lma_cfg:ANI";
          type empty;
          description "enable ani option processing in LMA";
        }
        leaf multipath {
          xr:xr-xml-map "ipv6_pmipv6_lma_cfg:Multipath";
          type empty;
          description "enable multipath support for LMA";
        }
        leaf dynamic {
          xr:xr-xml-map "ipv6_pmipv6_lma_cfg:Dynamic";
          type empty;
          description "enable dynamic mag learning for LMA";
        }
        leaf enforce {
          xr:xr-xml-map "ipv6_pmipv6_lma_cfg:Enforce";
          type empty;
          description "enforce heartbeat values to MAG";
        }
        leaf default-profile {
          xr:xr-xml-map "ipv6_pmipv6_lma_cfg:DefaultProfile";
          type string {
            length "0..125";
          }
          description "Default MN profile for LMA";
        }
        leaf interface {
          xr:xr-xml-map "ipv6_pmipv6_lma_cfg:Interface";
          type xr:Interface-name;
          description "CN facing interface name";
        }
        leaf mobile-map {
          xr:xr-xml-map "ipv6_pmipv6_lma_cfg:MobileMap";
          type string {
            length "0..125";
          }
          description "Mobile Map for this LMA";
        }
        leaf pgw-subs-cont {
          xr:xr-xml-map "ipv6_pmipv6_lma_cfg:PGWSubsCont";
          type empty;
          description "Feature related to interface with PGW";
        }
        leaf lma-name {
          xr:xr-xml-map "ipv6_pmipv6_lma_mode_cfg:LMAName";
          type string {
            length "0..125";
          }
          description "LMA name";
        }
        leaf domain-name {
          xr:xr-xml-map "ipv6_pmipv6_lma_mode_cfg:DomainName";
          type string {
            length "0..125";
          }
          description "Domain name";
        }
      }
    }
  }
}
