submodule Cisco-IOS-XR-mpls-te-oper-sub3 {

  belongs-to Cisco-IOS-XR-mpls-te-oper {
    prefix Cisco-IOS-XR-mpls-te-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2015 by Cisco Systems, Inc.
     All rights reserved.";

  revision "2015-11-09" {
    description
      "IOS XR 6.0 revision.";
  }

  typedef Tp-link-state {
    type enumeration {
      enum down {
        description "TP link state is down";
      }
      enum admin-down {
        description "TP link state is administratively down";
      }
      enum up {
        description "TP link state is up";
      }
      enum unknown {
        description "TP link state is unknown";
      }
    }
    description "Transport profile link state";
  }

  grouping MPLS-TE-TP-LINK-INFO {
    description "Transport profile link information";
    leaf link-id {
      xr:xr-xml-map "mpls_te_tp_link:LinkID";
      type uint32;
      description "Transport profile link identifier";
    }
    leaf interface {
      xr:xr-xml-map "mpls_te_tp_link:Interface";
      type string;
      description "Transport profile link interface name";
    }
    leaf next-hop-address {
      xr:xr-xml-map "mpls_te_tp_link:NextHopAddress";
      type inet:ipv4-address;
      description
        "Transport profile next-hop in IPv4 address
        format";
    }
    leaf link-state {
      xr:xr-xml-map "mpls_te_tp_link:LinkState";
      type Tp-link-state;
      description "Link state";
    }
    leaf available-bandwidth {
      xr:xr-xml-map "mpls_te_tp_link:AvailableBandwidth";
      type uint64;
      units "kbit/s";
      description "Available bandwidth in Kbps";
    }
  }

  grouping MPLS-TE-TP-LINK-SUMMARY-INFO {
    description "Transport profile link summary";
    leaf links {
      xr:xr-xml-map "mpls_te_tp_link:Links";
      type uint32;
      description "Number of transport profile links";
    }
  }

  grouping MPLS-TE-TP-DETAIL-LINK-INFO {
    description "Transport profile link detail information";
    leaf link-id {
      xr:xr-xml-map "mpls_te_tp_link:LinkID";
      type uint32;
      description "Transport profile link identifier";
    }
    leaf interface {
      xr:xr-xml-map "mpls_te_tp_link:Interface";
      type string;
      description "Transport profile link interface name";
    }
    leaf next-hop-address {
      xr:xr-xml-map "mpls_te_tp_link:NextHopAddress";
      type inet:ipv4-address;
      description
        "Transport profile next-hop in IPv4 address
        format";
    }
    leaf link-state {
      xr:xr-xml-map "mpls_te_tp_link:LinkState";
      type Tp-link-state;
      description "Link State";
    }
    leaf ls-ps {
      xr:xr-xml-map "mpls_te_tp_link:LSPs";
      type uint32;
      description "Number of TP LSPs on this TP link";
    }
    leaf reserved-bandwidth {
      xr:xr-xml-map "mpls_te_tp_link:ReservedBandwidth";
      type uint64;
      units "kbit/s";
      description "Reserved bandwidth in Kbps";
    }
    leaf available-bandwidth {
      xr:xr-xml-map "mpls_te_tp_link:AvailableBandwidth";
      type uint64;
      units "kbit/s";
      description "Available bandwidth in Kbps";
    }
    leaf unsupported-linecard {
      xr:xr-xml-map "mpls_te_tp_link:UnsupportedLinecard";
      type boolean;
      description
        "Link is hosted on a linecard that does not
        support MPLS-TP";
    }
  }
}
