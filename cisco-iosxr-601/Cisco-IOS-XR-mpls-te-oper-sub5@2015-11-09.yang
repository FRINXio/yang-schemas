submodule Cisco-IOS-XR-mpls-te-oper-sub5 {

  belongs-to Cisco-IOS-XR-mpls-te-oper {
    prefix Cisco-IOS-XR-mpls-te-oper;
  }

  /*** LINKAGE (IMPORTS / INCLUDES) ***/

  import ietf-inet-types { prefix "inet"; }

  import Cisco-IOS-XR-types { prefix "xr"; }

  include Cisco-IOS-XR-mpls-te-oper-sub6 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2015 by Cisco Systems, Inc.
     All rights reserved.";

  revision "2015-11-09" {
    description
      "IOS XR 6.0 revision.";
  }

  typedef Tunnel-state-enum {
    type enumeration {
      enum tunnel-state-unknown {
        description "No known state";
      }
      enum new {
        description "Tunnel is new";
      }
      enum preempting {
        description "Tunnel is being preempted";
      }
      enum admitting {
        description "Path being admitted";
      }
      enum half-admitted {
        description
          "Path was admitted partially and was then
          rejected";
      }
      enum admitted {
        description "Path is already admitted successfully";
      }
      enum reservation-admitting {
        description "Reservation being admitted";
      }
      enum reservation-half-admitted {
        description
          "Reservation was admitted partially and was then
          rejected";
      }
      enum reservation-admitted {
        description "Reservation is already admitted successfully";
      }
    }
    description "Types of tunnel admission states";
  }
  typedef Bandwidth-state-enum {
    type enumeration {
      enum bandwidth-held {
        description
          "Bandwidth is held, is not guaranteed when it is
          time to reserve";
      }
      enum bandwidth-reserved {
        description
          "Bandwidth is reserved and can be used for
          forwarding";
      }
      enum bandwidth-unknown {
        description "Bandwidth is unknown";
      }
    }
    description "Types of bandwidth states";
  }
  typedef Bandwidth-type-enum {
    type enumeration {
      enum pool0 {
        description "Bandwidth from the pool0";
      }
      enum pool1 {
        description "Pool1 bandwidth";
      }
      enum unknown {
        description "Unknown Bandwidth";
      }
    }
    description "Types of bandwidth pools";
  }
  typedef Admission-policy {
    type enumeration {
      enum reject-all {
        description "Deprecated";
      }
      enum allow-all {
        description "Deprecated";
      }
      enum reject-huge {
        description "Deprecated";
      }
      enum allow-if-room {
        description "Deprecated";
      }
    }
    description "Deprecated";
  }
  typedef Signaling-agent-enum {
    type enumeration {
      enum no-signaling {
        description "Deprecated - No signaling protocol configured";
      }
      enum rsvp-signaling {
        description "Deprecated - RSVP is the signaling protocol";
      }
    }
    description "Deprecated - Signaling Agent";
  }
  typedef Resource-provider {
    type enumeration {
      enum resource-provider-none {
        description "Unknown";
      }
      enum packet-switch-capable {
        description "Packet Switch Capable";
      }
      enum time-division-multiplex {
        description "TDM - SONET/SDH";
      }
      enum lambda-switch-capable {
        description "Lambda Switch Capable";
      }
      enum fiber-switch-capable {
        description "Fiber Switch Capable";
      }
      enum g709odu-capable {
        description "Resource provider of type G709-ODU";
      }
    }
    description "The resource provider type";
  }
  typedef Link-direction-enum {
    type enumeration {
      enum link-direction-up-stream {
        description "Upstream direction, Tail to Head";
      }
      enum link-direction-down-stream {
        description "Upstream direction, Head to Tail";
      }
      enum link-direction-unknown {
        description "Unknown direction";
      }
    }
    description "Link direction types";
  }
  typedef Bandwidth-unit-enum {
    type enumeration {
      enum kilo-bits-per-second {
        description "kilobits per second";
      }
      enum kilo-bytes-per-second {
        description "kilobytes per second";
      }
    }
    description "Types of bandwidth units";
  }
  typedef Flooding-trigger {
    type enumeration {
      enum flooding-reason-unknown {
        description "Not known what caused flooding";
      }
      enum link-up {
        description "TE link came Up";
      }
      enum link-down {
        description "TE link went Down";
      }
      enum threshold-up {
        description "Up threshold crossed in pool0";
      }
      enum threshold-down {
        description "Down threshold crossed in pool0";
      }
      enum threshold-up-pool1 {
        description "Up threshold crossed in pool1";
      }
      enum threshold-down-pool1 {
        description "Down threshold crossed in pool1";
      }
      enum timer-expired {
        description "Periodic timer expired";
      }
      enum bandwidth-change {
        description "Link BW changed";
      }
      enum user {
        description "User triggered flooding";
      }
      enum rsvp-timeout {
        description "RSVP timed out";
      }
      enum rsvp-reconnect {
        description "RSVP reconnected";
      }
      enum te-exited {
        description "TE-control process exited";
      }
      enum srlg-change {
        description "Link SRLG changed";
      }
    }
    description "Types of flooding triggers";
  }
  typedef Te-s2l-output-rw-explicit-null {
    type enumeration {
      enum tes2l-output-rw-exp-null {
        value 0;
        description "No explicit null imposed";
      }
      enum tes2l-output-rw-exp-null-v4 {
        value 1;
        description "IPv4 explicit null imposed";
      }
      enum tes2l-output-rw-exp-null-v6 {
        value 2;
        description "IPv6 explicit null imposed";
      }
    }
    description "Explicit-null type";
  }
  typedef Mpls-te-tunnels-process-status {
    type enumeration {
      enum not-running {
        description "MPLS TE process is not running";
      }
      enum running {
        description "MPLS TE process is running";
      }
      enum not-registered-with-rsvp {
        description "MPLS TE process has not registered with RSVP";
      }
    }
    description "Mpls te tunnels process status";
  }
  typedef Mpls-te-frr-sharing {
    type enumeration {
      enum sharing-none {
        description "No Fate Sharing";
      }
      enum sharing-pri-oi-backup-oi-parent {
        description
          "Primary Sharing outgoing interface with the
          Parent of the backup outgoing interface";
      }
      enum sharing-pri-oi-parent-backup-oi {
        description
          "Primary Sharing Parent of the outgoing
          interface with the backup outgoing interface";
      }
      enum sharing-pri-oi-parent-backup-oi-parent {
        description
          "Primary Sharing Parent of the outgoing
          interface with the Parent of the backup
          outgoing interface";
      }
    }
    description "FRR sharing type";
  }
  typedef Mpls-te-bw-limit {
    type enumeration {
      enum bandwidth-limited {
        description "Bandwidth is limited";
      }
      enum bandwidth-unlimited {
        description "Bandwidth is unlimited";
      }
      enum bandwidth-none {
        description "Bandwidth is None";
      }
    }
    description "Bandwidth limit type";
  }
  typedef Mpls-te-backup-usage {
    type enumeration {
      enum backup-not-protecting {
        description "Backup is not protecting any LSP";
      }
      enum backup-protecting {
        description "Backup is protecting at least one LSP";
      }
    }
    description "FRR backup tunnel usage status";
  }
  typedef Mpls-te-backup {
    type enumeration {
      enum backup-static {
        description "Backup type is static";
      }
      enum backup-auto {
        description "Backup type is auto-tunnel";
      }
    }
    description "FRR backup tunnel type";
  }
  typedef Mpls-te-backup-status {
    type enumeration {
      enum backup-none {
        description "Backup not found";
      }
      enum backup-unused {
        description "Backup status undefined";
      }
      enum backup-next-next-hop {
        description
          "Backup is next next hop safe (node protection)";
      }
      enum backup-next-hop {
        description "Backup is next hop safe (link protection)";
      }
      enum backup-next-next-hop-srlg {
        description
          "Backup is next next hop and SRLG safe (node
          protection)";
      }
      enum backup-next-hop-srlg {
        description
          "Backup is next hop and SRLG safe (link
          protection)";
      }
    }
    description "FRR backup status";
  }
  typedef Te-sync-pending-reason {
    type enumeration {
      enum current-lspoos {
        description "Current LSP OOS";
      }
      enum reopt-lspoos {
        description "Reopt LSP OOS";
      }
      enum standby-lspoos {
        description "Standby LSP OOS";
      }
      enum standby-reopt-lspoos {
        description "Standby Reopt LSP OOS";
      }
      enum restore-lspoos {
        description "Restore LSP OOS";
      }
      enum invalid-sync-id {
        description "Invalid internal ID";
      }
      enum null-pointer {
        description "Null pointer";
      }
      enum pending-flag {
        description "Pending flag set";
      }
      enum del-from-act-flag {
        description "Deleted by Active set";
      }
      enum oos-from-act-flag {
        description "OOS with Active set";
      }
      enum unknown {
        description "Unknown";
      }
    }
    description "Te sync pending reason";
  }
  typedef Te-sync-not-ready-reason {
    type enumeration {
      enum idt-in-progress {
        description "IDT in progress";
      }
      enum standby-not-connected {
        description "Standby not connected";
      }
      enum collaborator-disconnected {
        description "Collaborator disconnected";
      }
      enum collaborator-timeout {
        description "Collaborator timeout";
      }
      enum unknown {
        description "Unknown";
      }
    }
    description "Te sync not ready reason";
  }
  typedef Te-sync-status-show {
    type enumeration {
      enum master-sync-status-show {
        description "Master sync status information";
      }
      enum slave-sync-status-show {
        description "Slave sync status information";
      }
    }
    description "Te sync status show";
  }
  typedef Mpls-te-dste-class-status {
    type enumeration {
      enum configured {
        description "The TE class is explicitely configured";
      }
      enum default {
        description "The TE class is a default";
      }
      enum unused {
        description
          "The TE class is unused due to a configuration
          conflict";
      }
    }
    description "DSTE class status";
  }
  typedef Te-proc-role {
    type enumeration {
      enum unknown {
        description "Unknown";
      }
      enum v1-active {
        description "V1 Active";
      }
      enum v2-active {
        description "V2 Active";
      }
      enum v1-standby {
        description "V1 Standby";
      }
      enum v2-standby {
        description "V2 Standby";
      }
      enum v1-active-post-big-bang {
        description "V1 Active post big bang";
      }
      enum v1-standby-post-big-bang {
        description "V1 Standby post big bang";
      }
      enum number-of-role {
        description "Number of role";
      }
    }
    description "TE Process Role";
  }
  typedef Te-acl {
    type enumeration {
      enum acl-type-unknown {
        value 0;
        description "Unknown type of ACL";
      }
      enum acl-type-access-list {
        value 1;
        description "Access-list type of ACL";
      }
      enum acl-type-prefix-list {
        value 2;
        description "Prefix-list type of ACL";
      }
      enum acl-type-unregistered {
        value 3;
        description "ACL failed to register to ACL infra";
      }
    }
    description "Te acl";
  }
  typedef Mpls-te-p2mp-timer {
    type enumeration {
      enum lmrib-restart {
        value 0;
        description "P2MP Local Multicast RIB restart";
      }
      enum lmrib-recovery {
        value 1;
        description "P2MP LMRIB recovery";
      }
      enum rsvp-restart {
        value 2;
        description "P2MP RSVP restart";
      }
      enum lsd-restart {
        value 3;
        description "LSD restart";
      }
      enum lsd-recovery {
        value 4;
        description "LSD recovery";
      }
      enum clear-in-progress-bandwidth {
        value 5;
        description
          "Timer to clear the inprogress bandwidth for all
          the nodes in the topology";
      }
      enum rsi-restart {
        value 6;
        description "RSI restart";
      }
      enum rsi-recovery {
        value 7;
        description "RSI recovery";
      }
      enum ipv4-caps-replay {
        value 8;
        description
          "Timer to timeout the replay of IPv4 Caps after
          a TE or IM restart";
      }
      enum retry-acl-registration-timer {
        value 9;
        description "Timer to retry ACL registration";
      }
      enum mpls-te-exit {
        value 10;
        description "MPLS TE Exit";
      }
      enum mpls-te-nsr-peer-restart {
        value 11;
        description "MPLS TE NSR Peer Restart";
      }
      enum mpls-te-issu-peer-restart {
        value 12;
        description "MPLS TE ISSU Peer Restart";
      }
      enum bfd-restart {
        value 13;
        description "BFD restart";
      }
      enum bfd-recovery {
        value 14;
        description "BFD recovery";
      }
      enum im-oc-restart {
        value 15;
        description "IM Optical Connection restart";
      }
      enum im-oc-recovery {
        value 16;
        description "IM Optical Connection recovery";
      }
      enum rib-restart {
        value 17;
        description "RIB restart";
      }
      enum rib-recovery {
        value 18;
        description "RIB recovery";
      }
      enum rib-next-hop-route-cleanup {
        value 19;
        description "RIB next-hop route cleanup";
      }
      enum rsi-srlg-producer-retry {
        value 20;
        description "RSI SRLG-producer connection retry";
      }
      enum eoc-reg-retry {
        value 21;
        description "End-of-Config registration retry";
      }
      enum timer-not-used {
        value 22;
        description "Do not use";
      }
    }
    description "P2MP timer types";
  }
  typedef Mpls-te-afi {
    type enumeration {
      enum ipv4-unicast {
        description "MPLS TE IPv4 unicast";
      }
      enum ipv4-multicast {
        description "MPLS TE IPv4 multicast";
      }
      enum ipv6-unicast {
        description "MPLS TE IPv6 unicast";
      }
      enum ipv6-multicast {
        description "MPLS TE IPv6 multicast";
      }
    }
    description "Mpls te afi";
  }
  typedef Mpls-te-tunnel-announce {
    type enumeration {
      enum announce-type-not-set {
        description "Tunnel announcement type not set";
      }
      enum autoroute {
        description "Autoroute-announced tunnel";
      }
      enum forward-adjacency {
        description "Forwarding-adjacency tunnel";
      }
    }
    description "Type of TE tunnel announcement to IGP";
  }
  typedef Te-rev-ero-reject-reasons {
    type enumeration {
      enum none {
        description "None";
      }
      enum bad-reverse-ero {
        description "Bad Reverse ERO";
      }
      enum tie-rejected {
        description "Tie Rejected";
      }
      enum standby-not-required {
        description "Standby Not Required";
      }
      enum admin-state {
        description "Admin State";
      }
      enum priority {
        description "Priority";
      }
      enum class-type {
        description "Class Type";
      }
      enum bad-association {
        description "Bad Associated Tunnel";
      }
    }
    description "TE Reverse ERO Reject Reasons";
  }
  typedef Mte-path-option {
    type enumeration {
      enum none {
        description "No Path Option type";
      }
      enum dynamic {
        description "Dynamic Path Option type";
      }
      enum explicit {
        description "Explicit Path Option type";
      }
      enum no-ero {
        description "No ERO Path Option type";
      }
      enum segment-routing {
        description "One SID SegmentRouting Path Option type";
      }
      enum po-count {
        description "Number of Path option types";
      }
    }
    description "Path Option Type";
  }
  typedef Mpls-te-mgmt-gmpls-label-origin {
    type enumeration {
      enum not-set {
        description "Not set";
      }
      enum uni-c {
        description "UNI C";
      }
      enum uni-n {
        description "UNI N";
      }
    }
    description "GMPLS label source";
  }
  typedef Mpls-te-tunnel-state {
    type enumeration {
      enum state-down {
        description "Tunnel state is down";
      }
      enum state-up {
        description "Tunnel state is up";
      }
      enum state-down-policy {
        description
          "Tunnel state is down as it has been deactivated
          administratively";
      }
      enum state-lockout {
        description "Tunnel state is lockout";
      }
    }
    description "Tunnel state";
  }
  typedef Mpls-te-soft-preemption-resolution {
    type enumeration {
      enum soft-preemption-resolution-none {
        value 0;
        description "No Soft Preemption Resolution";
      }
      enum soft-preemption-resolution-pending {
        value 1;
        description
          "Soft Preemption has no resolution since it is
          still pending";
      }
      enum soft-preemption-resolution-reopt-completed {
        value 2;
        description "The soft preempted LSP has been reoptimized";
      }
      enum soft-preemption-resolution-teardown {
        value 3;
        description "The soft preempted LSP has been torn";
      }
      enum soft-preemption-resolution-frr-triggered {
        value 4;
        description "The soft preempted LSP has been fast rerouted";
      }
      enum soft-preemption-resolution-path-protetion-switchover {
        value 5;
        description
          "The soft preempted LSP was switched with the
          protection LSP";
      }
    }
    description "The possible ways for soft preemption to end";
  }
  typedef Mpls-te-iep-hop {
    type enumeration {
      enum iep-hop-type-unknown {
        description "Unknown IEP hop type";
      }
      enum iep-hop-type-strict-next {
        description "Strict next IEP hop type";
      }
      enum iep-hop-type-exclude {
        description "Exclude IEP hop type";
      }
      enum iep-hop-type-exclude-node {
        description "Exclude Node IEP hop type";
      }
      enum iep-hop-type-exclude-srlg {
        description "Exclude SRLG IEP hop type";
      }
      enum iep-hop-type-loose-next {
        description "Loose next IEP hop type";
      }
      enum iep-hop-type-next {
        description "Next IEP hop type";
      }
      enum iep-hop-type-share-srlg {
        description "Weighted SRLG IEP hop type";
      }
    }
    description "Explicit path hop type";
  }
  typedef Mpls-te-pce-fail-reasons {
    type enumeration {
      enum te-pce-fail-no-reason {
        description "No reason";
      }
      enum te-pce-fail-no-pce {
        description "No PCE to send request";
      }
      enum te-pce-fail-sub-pool {
        description "Sub pool bandwidth tunnel";
      }
      enum te-pce-fail-intra-area {
        description "Intra Area Tunnel";
      }
      enum te-pce-fail-gmpls {
        description "GMPLS Tunnel";
      }
      enum te-pce-fail-pending {
        description "Pending request";
      }
      enum te-pce-fail-oor {
        description "OOR condition";
      }
      enum te-pce-fail-bidirectional {
        description "Bi directional";
      }
      enum te-pce-fail-no-path {
        description "No Path received from PCE";
      }
      enum te-pce-fail-request-timeout {
        description "Request Timeout";
      }
    }
    description "PCE failure reasons";
  }
  typedef Te-autobw-app-rej {
    type enumeration {
      enum application-allowed {
        description "Application allowed";
      }
      enum auto-bw-disabled {
        description "Auto-bw disabled";
      }
      enum tunnel-is-down {
        description "TunnelIsDown";
      }
      enum tunnel-is-frr {
        description "TunnelIsFRRActive";
      }
      enum tunnel-is-backup {
        description "TunnelIsBackup";
      }
      enum tunnel-is-lock-down {
        description "TunnelIsLockdown";
      }
    }
    description "Reason for auto-bandwidth application rejection";
  }
  typedef Te-autobw-app-trigger {
    type enumeration {
      enum application-none {
        description "No BW Application";
      }
      enum application-periodic {
        description "BW Application Periodic";
      }
      enum application-manual {
        description "BW Application Manual";
      }
      enum application-overflow {
        description "BW Application Overflow";
      }
      enum application-underflow {
        description "BW Application Underflow";
      }
    }
    description "Auto-bandwidth application trigger";
  }
  typedef Te-hop-limit-ignore {
    type enumeration {
      enum ignore-unknown {
        description "Ignore for an unknown reason";
      }
      enum ignore-explicit {
        description "Ignore due to explicit path option";
      }
      enum ignore-pce {
        description "Ignore due to PCE path option";
      }
    }
    description "Te hop limit ignore";
  }
  typedef Mpls-te-metric-qualifier {
    type enumeration {
      enum metric-default {
        description "Default metric";
      }
      enum metric-global {
        description "This metric was specified globally";
      }
      enum metric-interface {
        description
          "This metric was specified on this particular
          tunnel";
      }
    }
    description "Metric qualifier";
  }
  typedef Mpls-te-loadshare {
    type enumeration {
      enum loadshare-equal {
        description "Equal load-sharing on this tunnel";
      }
      enum loadshare-bandwidth-based {
        description
          "Loadshare inferred from bandwidth configuration";
      }
      enum loadshare-configured {
        description
          "Loadshare determined from explicit
          configuration";
      }
    }
    description "load-share type";
  }
  typedef Te-destination-state {
    type enumeration {
      enum destination-disabled {
        description "The destination is disabled in configuration";
      }
      enum destination-down {
        description "The destination is down";
      }
      enum destination-up {
        description "The destination is up";
      }
    }
    description "P2MP destination state";
  }
  typedef Mpls-mte-tunnel-fail-reason {
    type enumeration {
      enum mtunnel-fail-reason-unapplicable {
        description "None of the reasons below is valid";
      }
      enum mtunnel-fail-reason-shutdown {
        description "Tunnel interface is shutdown";
      }
      enum mtunnel-fail-reason-no-destination {
        description "No destination is configured";
      }
      enum mtunnel-fail-reason-no-path-option {
        description "No path option is configured";
      }
      enum mtunnel-fail-reason-no-source {
        description "No ip source address is configured";
      }
      enum mtunnel-fail-reason-collaborator-disc {
        description "Collaborator not connected";
      }
      enum mtunnel-fail-reason-unmatched-class-type-priority {
        description
          "The class type and priority do not match any of
          the TE-classes";
      }
      enum mtunnel-fail-reason-invalid-bidir-cfg {
        description
          "Configured bidirectional, incomplete switching
          capability config";
      }
      enum mtunnel-fail-reason-po-switchover {
        description
          "Manual path-option switchover failed due to
          destination(s) down";
      }
      enum mtunnel-fail-reason-no-tunnel-id {
        description "No tunnel-id is configured";
      }
      enum mtunnel-fail-reason-no-link {
        description "Tunnel's egress link doesn't exist";
      }
      enum mtunnel-fail-reason-link-shutdown {
        description "Tunnel's egress link is shut down";
      }
      enum mtunnel-fail-reason-link-lmp-down {
        description "LMP is down on the tunnel's egress link";
      }
      enum mtunnel-fail-reason-source-destination-same {
        description
          "Tunnel source and destination addresses are the
          same";
      }
      enum mtunnel-fail-reason-otn-no-odu-level {
        description "OTN tunnel does not have odu-level set";
      }
      enum mtunnel-fail-reason-bidir-assoc-id-missing {
        description
          "Bidirectional is configured without Association
          ID";
      }
      enum mtunnel-fail-reason-bfdgal-on-unidirectional {
        description
          "BFD GAL mode is supported on bidirectional
          tunnels only";
      }
    }
    description "Reason for tunnel being down";
  }
  typedef Mte-tunnel-oper-state {
    type enumeration {
      enum tunnel-state-oper-unknown {
        description "Tunnel is in unknown state";
      }
      enum operational-down {
        description "Tunnel is in operational down state";
      }
      enum operational-up {
        description "Tunnel is in operational up state";
      }
    }
    description "Tunnel operational state";
  }
  typedef Mte-tunnel-admin-state {
    type enumeration {
      enum tunnel-state-admin-unknown {
        description "Tunnel is in unknown state";
      }
      enum admin-shutdown {
        description "Tunnel is in admin shutdown state";
      }
      enum admin-up {
        description "Tunnel is in admin up state";
      }
    }
    description "Tunnel admin state";
  }
  typedef Te-vif-bfd-encap-mode {
    type enumeration {
      enum ip {
        description "BFD Encap Mode IP";
      }
      enum gal {
        description "BFD Encap Mode GAL";
      }
    }
    description "BFD Encap Mode";
  }
  typedef Mpls-te-bfd-session-down-action1 {
    type enumeration {
      enum reopt {
        value 0;
        description "BFD session down action reoptimization";
      }
      enum re-setup {
        value 1;
        description "BFD session down action tear down and resetup";
      }
    }
    description "BFD session down action";
  }
  typedef Mte-reopt-trigger {
    type enumeration {
      enum no-trigger {
        description "No trigger";
      }
      enum timer-trigger {
        description "Timer Trigger";
      }
      enum bandwidth-change-trigger {
        description "Bandwidth Change Trigger";
      }
      enum auto-bandwidth-overflow-trigger {
        description "Auto Bandwidth Overflow Trigger";
      }
      enum auto-bandwidth-underflow-trigger {
        description "Auto Bandwidth Underflow Trigger";
      }
      enum auto-bandwidth-adjustment-trigger {
        description "Auto Bandwidth Adjustment Trigger";
      }
      enum metric-type-change-trigger {
        description "Metric Type Change Trigger";
      }
      enum user-trigger {
        description "User Trigger";
      }
      enum frr-trigger {
        description "FRR Trigger";
      }
      enum remerge-error-trigger {
        description "Remerge Error Trigger";
      }
      enum preferred-path-trigger {
        description
          "Reception of the preferred path exists path
          error";
      }
      enum preferred-tree-trigger {
        description
          "Reception of the preferred tree exists path
          error";
      }
      enum due-to-maximum-metric {
        description
          "Reoptimization triggered due to receiving an
          LSA with MAX metric";
      }
      enum path-option-switchover-trigger {
        description "Path option switchover";
      }
      enum path-protection-switchover-trigger {
        description "Path Protection Switchover Trigger";
      }
      enum iep-enable-reoptimization-trigger {
        description "IEP Enable Reoptimization Trigger";
      }
      enum affinity-path-verification-fail-trigger {
        description "Affinity path verification failure trigger";
      }
      enum cost-limit-path-verification-fail-trigger {
        description "Cost limit path verification failure trigger";
      }
      enum soft-preemption-trigger {
        description "Soft preemption trigger";
      }
      enum iep-changed {
        description "Explicit path has changed";
      }
      enum po-changed {
        description "Path-option has changed";
      }
      enum dest-changed {
        description "Destination has changed";
      }
      enum reopt-try-to-force-it {
        description "Reoptimization with try-to-force-it option";
      }
      enum topology-change-trigger {
        description "Topology change trigger";
      }
      enum reopt-link-up-event {
        description "Topology link-up event trigger";
      }
      enum bfd-session-down-trigger {
        description "FRR enabled and BFD session down trigger";
      }
      enum reverse-assoc-s2l-received-trigger {
        description "Reverse associated S2L received trigger";
      }
      enum gmpls-uni-multilayer-trigger {
        description "Multilayer recovery for GMPLS-UNI";
      }
      enum gmpls-uni-user-trigger {
        description "User-triggered GMPLS-UNI reopt request";
      }
      enum path-selection-tiebreaker-change-trigger {
        description "Path Selection Tiebreaker Change Trigger";
      }
      enum sr-egress-path-change-trigger {
        description "Segment-Routing Egress Path Change Trigger";
      }
      enum overload-bit-trigger {
        description "Overload-bit set on current path";
      }
      enum pce-trigger {
        description "PCE Trigger";
      }
      enum lockout-metric-trigger {
        description
          "Reoptimization triggered due to receiving an
          LSA with Lockout metric";
      }
      enum higher-priority-po-change-trigger {
        description "Higher priority path option changed";
      }
      enum trigger-not-used {
        description "Not used";
      }
    }
    description "Reoptimization trigger";
  }
  typedef Mpls-te-reopt-decision-reason {
    type enumeration {
      enum decision-reason-none {
        value 0;
        description "No reason";
      }
      enum not-superset {
        value 1;
        description
          "Reopt LSP not signalled because it is not a
          superset of the current LSP";
      }
      enum superset {
        value 2;
        description
          "Reopt LSP is signalled because it is a superset
          of the current LSP";
      }
      enum lsp-frr-active {
        value 3;
        description
          "Reopt LSP is signalled because the current LSP
          is in FRR";
      }
      enum bandwidth-change {
        value 4;
        description
          "Reopt LSP is signalled  because there is a
          bandwidth change";
      }
      enum metric-type-change {
        value 5;
        description
          "Reopt LSP is signalled because there is a
          metric type change";
      }
      enum better-path-option-indexes {
        value 6;
        description
          "Reopt LSP is signalled because it has better
          path option indexes than the current LSP";
      }
      enum inter-area-preferred-path-exists {
        value 7;
        description
          "Reopt LSP is signalled because an inter-area
          preferred path exists";
      }
      enum inter-area-preferred-tree-exists {
        value 8;
        description
          "Reopt LSP is signalled because an inter-area
          preferred tree exists";
      }
      enum worse-path-option-indexes {
        value 9;
        description
          "Reopt LSP is not signalled because it has worse
          path option indexes than the current LSP";
      }
      enum better-cumulative-metric {
        value 10;
        description
          "Reopt LSP is signalled because it has better
          path option indexes than the current LSP";
      }
      enum worse-cumulative-metric {
        value 11;
        description
          "Reopt LSP is not signalled because it has worse
          cumulative metric than the current LSP";
      }
      enum identical {
        value 12;
        description
          "Reopt LSP is not signalled because it is
          identical to the current LSP";
      }
      enum no-s2-ls {
        value 13;
        description
          "Reopt LSP is not signalled because it has no
          S2Ls";
      }
      enum no-current-lsp {
        value 14;
        description "Reopt LSP not signalled, no current LSP";
      }
      enum user-path-option-switchover {
        value 15;
        description
          "Reopt LSP signalled due to user requested
          path-option switchover";
      }
      enum better-hops {
        value 16;
        description
          "Reopt LSP is signalled because it has more S2Ls
          with less hops than the current LSP";
      }
      enum worse-hops {
        value 17;
        description
          "Reopt LSP is not signalled because it has less
          S2Ls with less hops than the current LSP";
      }
      enum pce-force {
        value 18;
        description
          "PCE based reoptimization triggered by CLI with
          force option than the current LSP";
      }
      enum affinity-changed {
        value 19;
        description
          "Reopt LSP is signalled  because there is an
          affinity change";
      }
      enum cost-limit {
        value 20;
        description
          "Reopt LSP is signalled  because the path cost
          limit is crossed";
      }
      enum sig-timeout {
        value 21;
        description
          "Re-opt LSP could not be signalled within
          signalling timeout";
      }
      enum not-superset-inst-timer-expired {
        value 22;
        description
          "Re-opt LSP is not a superset when the install
          timer expired";
      }
      enum path-verifiction-failed {
        value 23;
        description "Re-opt LSP path verification failed";
      }
      enum soft-preemption-recovery {
        value 24;
        description
          "Re-opt LSP is signalled because of soft
          preemption recovery";
      }
      enum iep-changed {
        value 25;
        description
          "Re-opt LSP is signalled because the inuse
          explicit-path has changed";
      }
      enum po-changed {
        value 26;
        description
          "Re-opt LSP is signalled because the inuse
          path-option has changed";
      }
      enum dest-changed {
        value 27;
        description
          "Re-opt LSP is signalled because the destination
          has changed";
      }
      enum better-igp-area {
        value 28;
        description
          "Reopt LSP is signalled because its path was
          calculated in a preferred IGP-area to the
          current LSP";
      }
      enum worse-igp-area {
        value 29;
        description
          "Reopt LSP is not signalled because its path was
          calculated in a worse IGP-area than the current
          LSP";
      }
      enum better-bandwidth-load-balancing {
        value 30;
        description
          "Reopt LSP is signalled because it gives better
          bandwidth load balancing than the current LSP";
      }
      enum worse-bandwidth-load-balancing {
        value 31;
        description
          "Reopt LSP is not signalled because it gives
          worse bandwidth load balancing than the current
          LSP";
      }
      enum bfd-session-down {
        value 32;
        description
          "Reopt LSP is signaled because BFD sesssion went
          down";
      }
      enum auto-pcc-reopt {
        value 33;
        description
          "Re-opt LSP is signalled because it was
          triggered by a PCE";
      }
      enum sr-egress-path-changed {
        value 34;
        description
          "Reopt LSP is signaled because the egress
          path(s) changed";
      }
      enum overload-bit-set {
        value 35;
        description
          "Reopt LSP is signalled because the current LSP
          uses an OL node";
      }
      enum better-diversity {
        value 36;
        description
          "Reopt LSP is signalled because it has better
          diversity than the current LSP";
      }
      enum worse-diversity {
        value 37;
        description
          "Reopt LSP is not signalled because it has worse
          diversity than the current lsp";
      }
      enum lsp-drop-mode {
        value 38;
        description
          "Reopt LSP is signalled because current LSP is
          in drop mode";
      }
      enum not-used {
        value 39;
        description "Not used, must be last entry";
      }
    }
    description "Reoptimization decision";
  }
  typedef Mpls-te-lsp-wrap-state {
    type enumeration {
      enum lsp-wrap-not-ready {
        description "LSP Wrap state is not ready";
      }
      enum lsp-wrap-active {
        description "LSP Wrap state is active";
      }
      enum lsp-wrap-ready {
        description "LSP Wrap state is ready";
      }
    }
    description "LSP Wrap state";
  }
  typedef Te-sr-sid {
    type enumeration {
      enum srsid-not-set {
        description "Type not set";
      }
      enum srsid-node {
        description "Segment-Routing Node";
      }
      enum srsid-adj {
        description "Segment-Routing Link";
      }
      enum srsid-unknown {
        description "Segment-Routing Unknown";
      }
    }
    description "Segment-Routing SID types";
  }
  typedef Flex-lsp-lockout-origination {
    type enumeration {
      enum lockout-origination-none {
        description "Flex LSP Lockout Origination None";
      }
      enum lockout-origination-local {
        description "Flex LSP Lockout Originated From Local";
      }
      enum lockout-origination-remote {
        description "Flex LSP Lockout Originated From Remote";
      }
    }
    description "TE Flex LSP Lockout Origination";
  }
  typedef Te-association-tie-role {
    type enumeration {
      enum none {
        description "Association Role None";
      }
      enum master {
        description "Association Role Master";
      }
      enum slave {
        description "Association Role Slave";
      }
    }
    description "TE Association Tie Breaker Role";
  }
  typedef Te-bfd-lsp-session-state {
    type enumeration {
      enum bfd-over-lsp-session-state-none {
        value 0;
        description "BFDOverLSP session state none";
      }
      enum bfd-over-lsp-session-state-created {
        value 1;
        description "BFDOverLSP session state created";
      }
      enum bfd-over-lsp-session-state-up {
        value 2;
        description "BFDOverLSP session state up";
      }
      enum bfd-over-lsp-session-state-down {
        value 3;
        description "BFDOverLSP session state down";
      }
      enum bfd-over-lsp-session-state-admin-down {
        value 4;
        description "BFDOverLSP session state admin down";
      }
      enum bfd-over-lsp-session-state-deleted {
        value 5;
        description "BFDOverLSP sesssion state deleted";
      }
    }
    description "TE BFDOverLSP Session State";
  }
  typedef Gmpls-uni-mgmt-dwdm-cs {
    type enumeration {
      enum not-set {
        description "Not Set";
      }
      enum dwdm100g-hz {
        description "100GHz";
      }
      enum dwdm50g-hz {
        description "50GHz";
      }
      enum dwdm25g-hz {
        description "25GHz";
      }
      enum dwdm12g-hz {
        description "12.5GHz";
      }
    }
    description "GMPLS-UNI DWDM channel spacings";
  }
  typedef Gmpls-uni-mgmt-wdm-grid {
    type enumeration {
      enum not-set {
        description "Not Set";
      }
      enum dwdm {
        description "DWDM";
      }
      enum cwdm {
        description "CWDM";
      }
    }
    description "GMPLS-UNI WDM grid";
  }
  typedef Mpls-te-mgmt-gmpls-label {
    type enumeration {
      enum not-set {
        description "Not Set";
      }
      enum fixed-wdm {
        description "Fixed-grid WDM";
      }
      enum fixed-g709otn {
        description "Fixed-size G709 OTN";
      }
    }
    description "GMPLS label type";
  }
  typedef Mpls-te-soft-preemption-state {
    type enumeration {
      enum soft-preemption-not-pending {
        description
          "Soft Preemption has not been triggered and is
          not pending";
      }
      enum soft-preemption-pending {
        description
          "Soft Preemption has been triggered and is
          pending";
      }
    }
    description "The possible states for soft preemption";
  }
  typedef Mpls-te-tunnels-signaling-status {
    type enumeration {
      enum down {
        description "The tunnel is down";
      }
      enum recovering {
        description "The tunnel is recovering";
      }
      enum recovered {
        description "The tunnel is recovered";
      }
      enum connected {
        description "The tunnel is connected";
      }
      enum disabled {
        description "The tunnel signalling is disabled";
      }
      enum proceeding {
        description "The tunnel signalling is proceeding";
      }
      enum wait-bfd-session-up {
        description "The tunnel is waiting for BFD session up";
      }
      enum wait-sr-segment-path-up {
        description "The tunnel is waiting for SR segment path";
      }
      enum wait-local-label {
        description "The tunnel is waiting for a local label";
      }
      enum wait-local-label-rewrite {
        description
          "The tunnel is waiting for a local label rewrite";
      }
    }
    description "Tunnel signalling status";
  }
  typedef Mpls-te-frr-state {
    type enumeration {
      enum frr-inactive {
        description "FRR state is inactive";
      }
      enum frr-active {
        description "FRR state is active";
      }
      enum frr-ready {
        description "FRR state is ready";
      }
    }
    description "FRR state";
  }
  typedef Te-controller-state {
    type enumeration {
      enum notready {
        description "Controller not ready";
      }
      enum admin-down {
        description "Controller is admin down";
      }
      enum down {
        description "Controller is operationally down";
      }
      enum shutdown {
        description "Controller is shutdown";
      }
      enum error-disabled {
        description "Controller is disabled due to error";
      }
      enum up {
        description "Controller is operationally up";
      }
      enum unknown {
        description "Controller state unknown";
      }
    }
    description "Controller States";
  }
  typedef Te-mgmt-generic-fspec {
    type enumeration {
      enum te-generic-fspec-type-g709otn {
        description "TE G709 OTN FSpec type";
      }
    }
    description "TE generic FSpec types";
  }
  typedef Te-mgmt-generic-tspec {
    type enumeration {
      enum te-generic-tspec-type-g709otn {
        description "TE G709 OTN TSpec type";
      }
    }
    description "TE generic TSpec types";
  }
  typedef Rsvp-mgmt-rro-subobj {
    type enumeration {
      enum ipv4rro-type {
        value 1;
        description "IPv4 RRO Type";
      }
      enum label-rro-type {
        value 3;
        description "Label RRO Type";
      }
      enum unnumbered-rro-type {
        value 4;
        description "Unnumbered RRO Type";
      }
      enum srlg-rro-type {
        value 34;
        description "SRLG RRO Type";
      }
    }
    description "RSVP RRO Types";
  }
  typedef Rsvp-mgmt-ero-subobj-status {
    type enumeration {
      enum rsvp-mgmt-ero-status-not-available {
        value 0;
        description "ERO is not available in topology";
      }
      enum rsvp-mgmt-ero-status-available {
        value 1;
        description "ERO is available in topology";
      }
      enum rsvp-mgmt-ero-status-bw-not-available {
        value 2;
        description "ERO doesn't have bw available in topology";
      }
    }
    description "RSVP ERO Status";
  }
  typedef Rsvp-mgmt-ero-subobj {
    type enumeration {
      enum rsvp-mgmt-ero-type-ipv4 {
        value 1;
        description "IPv4 ERO Type";
      }
      enum rsvp-mgmt-ero-type-un-num {
        value 4;
        description "Unnumbered ERO Type";
      }
    }
    description "RSVP ERO Types";
  }
  typedef Mpls-te-metric {
    type enumeration {
      enum metric-not-set {
        description "Metric type not set";
      }
      enum metric-igp {
        description "Metric for IGP routes";
      }
      enum metric-te {
        description "Metric for MPLS traffic engineering tunnels";
      }
      enum metric-delay {
        description "Delay Metric";
      }
    }
    description "Metric type";
  }
  typedef Te-path-inval-action {
    type enumeration {
      enum none {
        value 0;
        description "TE path selection invalidation action none";
      }
      enum tear {
        value 1;
        description "TE path selection invalidation action tear";
      }
      enum drop {
        value 2;
        description "TE path selection invalidation action drop";
      }
    }
    description "Path selection invalidation action type";
  }
  typedef Te-s2l-sr-path-selection {
    type enumeration {
      enum te-s2l-sr-path-selection-any {
        value 0;
        description
          "TE S2L Segment-Routing Path Selection type Any";
      }
      enum te-s2l-sr-path-selection-adj-unprotected {
        value 1;
        description
          "TE S2L Segment-Routing Path Selection type
          Adjacency Unprotected";
      }
      enum te-s2l-sr-path-selection-adj-protected {
        value 2;
        description
          "TE S2L Segment-Routing Path Selection type
          Adjacency Protected";
      }
    }
    description "Segment-routing path selection type";
  }
  typedef Tunnel-attribute-set {
    type enumeration {
      enum tunnel-attribute-set-none {
        value 0;
        description "No Tunnel AttributeSet configured";
      }
      enum tunnel-attribute-set-static {
        value 1;
        description "Tunnel AttributeSet Type is Static";
      }
      enum tunnel-attribute-set-path-option {
        value 2;
        description "Tunnel AttributeSet Type is Path Option";
      }
      enum tunnel-attribute-set-not-used {
        value 3;
        description "None";
      }
      enum tunnel-attribute-set-auto-backup {
        value 4;
        description "Tunnel AttributeSet Type is AutoBackup";
      }
      enum tunnel-attribute-set-auto-mesh {
        value 5;
        description "Tunnel AttributeSet Type is AutoMesh";
      }
      enum tunnel-attribute-set-xro {
        value 6;
        description "Tunnel AttributeSet Type is XRO";
      }
      enum tunnel-attribute-set-p2mpte {
        value 7;
        description "Tunnel AttributeSet Type is P2MP TE";
      }
      enum tunnel-attribute-aps-pp {
        value 8;
        description
          "Tunnel AttributeSet Type is APS Path Protection";
      }
      enum tunnel-attribute-set-p2p-te {
        value 9;
        description "Tunnel AttributeSet Type is P2P TE";
      }
    }
    description "Tunnel attribute set";
  }
  typedef Mpls-te-pathoption {
    type enumeration {
      enum path-option-unknown {
        description "Unknown Path Option";
      }
      enum path-option-dynamic {
        description "Dynamic Path Option";
      }
      enum path-option-explicit-name {
        description "Explicit name Path Option";
      }
      enum path-option-explicit-id {
        description "Explicit Identifier Path Option";
      }
      enum path-option-pce {
        description "PCE Path Option";
      }
      enum path-option-no-ero {
        description "No-ERO Path Option";
      }
      enum path-option-segment-routing {
        description "Segment-Routing Path Option";
      }
    }
    description "Path-option type";
  }
  typedef Mpls-te-bw-pool {
    type enumeration {
      enum te-bandwidth-pool0 {
        description "Bandwidth pool type is pool0";
      }
      enum te-bandwidth-pool1 {
        description "Bandwidth pool type is pool1";
      }
      enum te-bandwidth-any-pool {
        description "Bandwidth pool type is any pool";
      }
    }
    description "Bandwidth pool type";
  }

  grouping MPLS-LM-SOFT-PREEMPTION-LINK-INFO {
    description "Soft Preemption Info per Link";
    leaf link-address {
      xr:xr-xml-map "mpls_lcac:LinkAddress";
      type inet:ipv4-address;
      description "The link's IPv4 address";
    }
    leaf total-soft-preempted-bandwidth-bc0 {
      xr:xr-xml-map "mpls_lcac:TotalSoftPreemptedBandwidthBC0";
      type uint64;
      description
        "The total BC0 BW that is softly preempted: this
        is the sum of bandwidth for all the LSPs that
        were soft preempted";
    }
    leaf total-soft-preempted-bandwidth-bc1 {
      xr:xr-xml-map "mpls_lcac:TotalSoftPreemptedBandwidthBC1";
      type uint64;
      description
        "The total BC1 BW that is softly preempted: this
        is the sum of bandwidth for all the LSPs that
        were soft preempted";
    }
    leaf current-soft-preempted-bandwidth-bc0 {
      xr:xr-xml-map "mpls_lcac:CurrentSoftPreemptedBandwidthBC0";
      type uint64;
      description
        "The current BC0 BW that is softly preempted:
        this is the sum of bandwidth for the LSPs that
        are soft preempted and have not been torn down
        yet";
    }
    leaf current-soft-preempted-bandwidth-bc1 {
      xr:xr-xml-map "mpls_lcac:CurrentSoftPreemptedBandwidthBC1";
      type uint64;
      description
        "The current BC1 BW that is softly preempted:
        this is the sum of bandwidth for the LSPs that
        are soft preempted and have not been torn down
        yet";
    }
    leaf release-soft-preempted-bandwidth-bc0 {
      xr:xr-xml-map "mpls_lcac:ReleaseSoftPreemptedBandwidthBC0";
      type uint64;
      description
        "The total released BC0 BW that is softly
        preempted: this is the sum of bandwidth for the
        LSPs that are soft preempted and are torn down";
    }
    leaf release-soft-preempted-bandwidth-bc1 {
      xr:xr-xml-map "mpls_lcac:ReleaseSoftPreemptedBandwidthBC1";
      type uint64;
      description
        "The total released BC1 BW that is softly
        preempted: this is the sum of bandwidth for the
        LSPs that are soft preempted and are torn down";
    }
    leaf current-over-subscribed-bandwidth-bc0 {
      xr:xr-xml-map "mpls_lcac:CurrentOverSubscribedBandwidthBC0";
      type uint64;
      description
        "The BC0 bandwidth that is over subscribed on
        this link: this is the difference between the
        maximum available BC0 BW on the link and the sum
        of the currently reserved BC0 bandwidth and the
        currently soft preempted BC0 BW";
    }
    leaf current-over-subscribed-bandwidth-bc1 {
      xr:xr-xml-map "mpls_lcac:CurrentOverSubscribedBandwidthBC1";
      type uint64;
      description
        "The BC1 bandwidth that is over subscribed on
        this link: this is the difference between the
        maximum available BC1 BW on the link and the sum
        of the currently reserved BC1 bandwidth and the
        currently soft preempted BC1 BW";
    }

    list current-soft-preemption-lsp {
      description
        "List of the soft preempted LSPs that are not yet
        cleaned up";
      uses MPLS-LM-PREEMPTED-LSP;
    }
  }

  grouping MPLS-TE-SOFT-PREEMPTION-GLOBAL-INFO {
    description "Global Soft Preemption Info";
    leaf is-configured {
      xr:xr-xml-map "mpls_lcac:IsConfigured";
      type boolean;
      description "Is global soft-preemption configured";
    }
    leaf is-timeout-interval-configured {
      xr:xr-xml-map "mpls_lcac:IsTimeoutIntervalConfigured";
      type boolean;
      description
        "Is global soft-preemption timeout interval
        configured";
    }
    leaf timeout-interval {
      xr:xr-xml-map "mpls_lcac:TimeoutInterval";
      type uint32;
      description "Global soft-preemption timeout interval";
    }
  }

  grouping MPLS-LM-ADMISSION-CONTROL-TUNNEL-INFO {
    description "Information about a given admitted tunnel";
    leaf tunnel-name {
      xr:xr-xml-map "mpls_lcac:TunnelName";
      type string;
      description "The admitted tunnel's name";
    }
    leaf bandwidth-state {
      xr:xr-xml-map "mpls_lcac:BandwidthState";
      type Bandwidth-state-enum;
      description "The bandwidth state";
    }
    leaf bandwidth-pool {
      xr:xr-xml-map "mpls_lcac:BandwidthPool";
      type Bandwidth-type-enum;
      description "The bandwidth pool";
    }
    leaf setup-priority {
      xr:xr-xml-map "mpls_lcac:SetupPriority";
      type uint8;
      description "The tunnel's setup priority";
    }
    leaf hold-priority {
      xr:xr-xml-map "mpls_lcac:HoldPriority";
      type uint8;
      description "The tunnel's hold priority";
    }
    leaf up-link-name {
      xr:xr-xml-map "mpls_lcac:UpLinkName";
      type string;
      description "The uplink's name for this tunnel";
    }
    leaf down-link-name {
      xr:xr-xml-map "mpls_lcac:DownLinkName";
      type string;
      description "The downlink's name for this tunnel";
    }
    leaf tunnel-state {
      xr:xr-xml-map "mpls_lcac:TunnelState";
      type Tunnel-state-enum;
      description "The tunnel's state";
    }
    leaf bandwidth {
      xr:xr-xml-map "mpls_lcac:Bandwidth";
      type uint64;
      description "The bandwidth used by this tunnel";
    }
    leaf local-label {
      xr:xr-xml-map "mpls_lcac:LocalLabel";
      type uint32;
      description "The local label";
    }
    leaf outgoing-label {
      xr:xr-xml-map "mpls_lcac:OutgoingLabel";
      type uint32;
      description "The outgoing label";
    }
    leaf backup-interface {
      xr:xr-xml-map "mpls_lcac:BackupInterface";
      type string;
      description "The backup Interface";
    }
    leaf is-rerouted {
      xr:xr-xml-map "mpls_lcac:IsRerouted";
      type boolean;
      description "TRUE if the tunnel is currently rerouted";
    }
  }

  grouping MPLS-LM-ADMISSION-CONTROL-COMMON-INFO {
    description "Global information about admitted tunnels";
    leaf is-role-standby {
      xr:xr-xml-map "mpls_lcac:IsRoleStandby";
      type boolean;
      description "TRUE if Role is Standby, Active otherwise";
    }
    leaf total-tunnels {
      xr:xr-xml-map "mpls_lcac:TotalTunnels";
      type uint32;
      description "Total p2p tunnels admitted";
    }
    leaf total-p2mp-tunnels {
      xr:xr-xml-map "mpls_lcac:TotalP2MPTunnels";
      type uint32;
      description "Total p2mp tunnels admitted";
    }
    leaf selected-tunnels {
      xr:xr-xml-map "mpls_lcac:SelectedTunnels";
      type uint32;
      description "Number of tunnels selected";
    }
    leaf bandwidth-units {
      xr:xr-xml-map "mpls_lcac:BandwidthUnits";
      type Bandwidth-unit-enum;
      description "Bandwidth units";
    }
  }

  grouping MPLS-LM-INTERFACE-LOCKOUT-INFO {
    description
      "Information about flex LSP lockout info for the
      link";
    leaf is-lockout {
      xr:xr-xml-map "mpls_lcac:IsLockout";
      type boolean;
      description "True if link is locked out";
    }
    leaf lockout-on-timestamp {
      xr:xr-xml-map "mpls_lcac:LockoutOnTimestamp";
      type uint32;
      description "Timestamp when the lockout is set";
    }
    leaf lockout-off-timestamp {
      xr:xr-xml-map "mpls_lcac:LockoutOffTimestamp";
      type uint32;
      description "Timestamp when the lockout is cleared";
    }
  }

  grouping MPLS-LM-INTERFACE-LINK-AREA-INFO {
    description
      "Information about an area to which the link
      belongs";
    leaf area-id {
      xr:xr-xml-map "mpls_lcac:AreaID";
      type string;
      description "Area id";
    }
    leaf neighbor-id {
      xr:xr-xml-map "mpls_lcac:NeighborID";
      type string;
      description "The interface neighbor id";
    }
    leaf neighbor-address {
      xr:xr-xml-map "mpls_lcac:NeighborAddress";
      type inet:ipv4-address;
      description "The interface's neighbor's ip address";
    }
    leaf is-neighbor-up {
      xr:xr-xml-map "mpls_lcac:IsNeighborUp";
      type boolean;
      description "TRUE if the neighbor is up";
    }
    leaf igp-metric {
      xr:xr-xml-map "mpls_lcac:IGPMetric";
      type uint32;
      description "The link's IGP metric";
    }
  }

  grouping MPLS-LM-INTERFACE-LINK-INFO {
    description "IGP and area information of a link";

    container link-common {
      description "The link's common info";
      uses MPLS-LM-COMMON-LINK-INFO;
    }
    leaf reason-not-flooded {
      xr:xr-xml-map "mpls_lcac:ReasonNotFlooded";
      type string;
      description
        "Reason why link is not flooded
        (area-independent)";
    }
    leaf maximum-reservation-bandwidth-rdm {
      xr:xr-xml-map "mpls_lcac:MaximumReservationBandwidthRDM";
      type uint64;
      description "The link's maximum reservable BW in RDM";
    }
    leaf reservable-pool0-bandwidth-rdm {
      xr:xr-xml-map "mpls_lcac:ReservablePool0BandwidthRDM";
      type uint64;
      description "The link's reservable pool0 BW in RDM";
    }
    leaf reservable-pool1-bandwidth-rdm {
      xr:xr-xml-map "mpls_lcac:ReservablePool1BandwidthRDM";
      type uint64;
      description "The link's reservable pool1 BW in RDM";
    }
    leaf maximum-reservation-bandwidth-mam {
      xr:xr-xml-map "mpls_lcac:MaximumReservationBandwidthMAM";
      type uint64;
      description "The link's maximum reservable BW in MAM";
    }
    leaf reservable-pool0-bandwidth-mam {
      xr:xr-xml-map "mpls_lcac:ReservablePool0BandwidthMAM";
      type uint64;
      description "The link's reservable pool0 BW in MAM";
    }
    leaf reservable-pool1-bandwidth-mam {
      xr:xr-xml-map "mpls_lcac:ReservablePool1BandwidthMAM";
      type uint64;
      description "The link's reservable pool1 BW in MAM";
    }
    leaf link-attributes {
      xr:xr-xml-map "mpls_lcac:LinkAttributes";
      type uint32;
      description "Deprecated";
    }
    leaf is-attribute-incomplete {
      xr:xr-xml-map "mpls_lcac:IsAttributeIncomplete";
      type boolean;
      description
        "TRUE if one or more affinity definition(s)
        is/are unknown";
    }
    leaf is-name-based-attribute {
      xr:xr-xml-map "mpls_lcac:IsNameBasedAttribute";
      type boolean;
      description
        "TRUE, if name based attribute style is in effect";
    }
    leaf te-metric {
      xr:xr-xml-map "mpls_lcac:TEMetric";
      type uint32;
      description "The link's TE metric";
    }
    leaf is-te-metric-valid {
      xr:xr-xml-map "mpls_lcac:IsTEMetricValid";
      type boolean;
      description
        "Flag to indicate whether the link's TE metric is
        a valid value";
    }
    leaf-list link-extended-attribute {
      xr:xr-xml-map "mpls_lcac:LinkExtendedAttributes";
      type uint32;
      description "The link's extended attribute bit map";
    }
    leaf-list link-forwad-ref-value {
      xr:xr-xml-map "mpls_lcac:LinkForwadRefValue";
      type uint32;
      description "Reference bits for undefined affinity names";
    }

    list affinity-map {
      description "Affinity map array";
      uses MPLS-TE-AFFINITY-MAP-INFO;
    }

    list areas {
      description "Per-area data";
      uses MPLS-LM-INTERFACE-LINK-AREA-INFO;
    }

    list lockout {
      description "Flex LSP Lockout info";
      uses MPLS-LM-INTERFACE-LOCKOUT-INFO;
    }
  }

  grouping MPLS-LM-INTERFACE-COMMON-INFO {
    description "Global info about links";
    leaf is-role-standby {
      xr:xr-xml-map "mpls_lcac:IsRoleStandby";
      type boolean;
      description "TRUE if Role is Standby, Active otherwise";
    }
    leaf links {
      xr:xr-xml-map "mpls_lcac:Links";
      type uint16;
      description "The number of links";
    }
    leaf maximum-links {
      xr:xr-xml-map "mpls_lcac:MaximumLinks";
      type uint16;
      description "Maximum number of links supported";
    }
  }

  grouping MPLS-LM-SUMMARY-AREA-INFO {
    description "Summary information of an area";
    leaf area-id {
      xr:xr-xml-map "mpls_lcac:AreaID";
      type string;
      description "Area id";
    }
    leaf protocol {
      xr:xr-xml-map "mpls_lcac:Protocol";
      type Igp-protocol;
      description "Protocol running over the area";
    }
    leaf is-flooded {
      xr:xr-xml-map "mpls_lcac:IsFlooded";
      type boolean;
      description "TRUE if flooding occurred in this area";
    }
    leaf is-periodic-flooding-on {
      xr:xr-xml-map "mpls_lcac:IsPeriodicFloodingOn";
      type boolean;
      description "TRUE if periodic flooding is on";
    }
    leaf periodic-flooding-interval {
      xr:xr-xml-map "mpls_lcac:PeriodicFloodingInterval";
      type uint16;
      units "second";
      description "Flooding period in seconds";
    }
    leaf links-flooded {
      xr:xr-xml-map "mpls_lcac:LinksFlooded";
      type uint16;
      description "Number of flooded links";
    }
    leaf system-id {
      xr:xr-xml-map "mpls_lcac:SystemID";
      type string;
      description "IGP id of local node";
    }
    leaf local-node-router-id {
      xr:xr-xml-map "mpls_lcac:LocalNodeRouterID";
      type inet:ipv4-address;
      description "Local router id";
    }
    leaf igp-neighbors {
      xr:xr-xml-map "mpls_lcac:IGPNeighbors";
      type uint16;
      description "Number of IGP neighbors";
    }
  }

  grouping MPLS-LM-SUMMARY-COMMON-INFO {
    description "Summary information for all the areas";
    leaf is-role-standby {
      xr:xr-xml-map "mpls_lcac:IsRoleStandby";
      type boolean;
      description "TRUE if Role is Standby, Active otherwise";
    }
    leaf links {
      xr:xr-xml-map "mpls_lcac:Links";
      type uint16;
      description "Total number of links";
    }
    leaf maximum-links {
      xr:xr-xml-map "mpls_lcac:MaximumLinks";
      type uint16;
      description "Maximum number of links supported";
    }
    leaf is-flooding-enabled {
      xr:xr-xml-map "mpls_lcac:IsFloodingEnabled";
      type boolean;
      description "TRUE if flooding is enabled";
    }

    list areas-summary {
      description "Summary info for the areas";
      uses MPLS-LM-SUMMARY-AREA-INFO;
    }
  }

  grouping MPLS-LM-BW-LINK-BW-POOL-INFO {
    description
      "Information about the bandwidth of a given pool
      and priority";
    leaf hold-priority {
      xr:xr-xml-map "mpls_lcac:HoldPriority";
      type uint8;
      description "The BW priority";
    }
    leaf held-amount {
      xr:xr-xml-map "mpls_lcac:HeldAmount";
      type uint32;
      description "The held bandwidth";
    }
    leaf total-held-amount {
      xr:xr-xml-map "mpls_lcac:TotalHeldAmount";
      type uint32;
      description "The total held bandwidth";
    }
    leaf locked-amount {
      xr:xr-xml-map "mpls_lcac:LockedAmount";
      type uint32;
      description "The locked bandwidth";
    }
    leaf total-locked-amount {
      xr:xr-xml-map "mpls_lcac:TotalLockedAmount";
      type uint32;
      description "The total locked bandwidth";
    }
  }

  grouping MPLS-LM-BW-LINK-DIR-BW-INFO {
    description "Information about the bandwidth of a given  link.";
    leaf bandwidth-direction {
      xr:xr-xml-map "mpls_lcac:BandwidthDirection";
      type Link-direction-enum;
      description "BW Direction";
    }
    leaf is-admission-method-allocated-bandwidth {
      xr:xr-xml-map "mpls_lcac:IsAdmissionMethodAllocatedBandwidth";
      type boolean;
      description
        "True if the link's admit method is based on
        Allocated BW";
    }
    leaf bandwidth-units {
      xr:xr-xml-map "mpls_lcac:BandwidthUnits";
      type Bandwidth-unit-enum;
      description "Bandwidth units";
    }

    list bandwidth-pool0 {
      max-elements "8";
      description "Pool0 BW info for the different priority levels";
      uses MPLS-LM-BW-LINK-BW-POOL-INFO;
    }

    list bandwidth-pool1 {
      max-elements "8";
      description "Pool1 BW info for the different priority levels";
      uses MPLS-LM-BW-LINK-BW-POOL-INFO;
    }
  }

  grouping MPLS-LM-FLOODED-AREA {
    description "Information for the flooded area";
    leaf flooded-area {
      xr:xr-xml-map "mpls_lcac:FloodedArea";
      type string;
      description "The flooded area information";
    }
  }

  grouping MPLS-LM-LINK-FLAGS {
    description "Link properties";
    leaf is-mpls-te-on {
      xr:xr-xml-map "mpls_lcac:IsMPLS_TEOn";
      type boolean;
      description "Deprecated - TRUE if the link is a TE-Link";
    }
    leaf signaling-agent {
      xr:xr-xml-map "mpls_lcac:SignalingAgent";
      type Signaling-agent-enum;
      description "Deprecated - Signaling agent";
    }
    leaf is-admin-up {
      xr:xr-xml-map "mpls_lcac:IsAdminUp";
      type boolean;
      description "TRUE if the link is admin up";
    }
  }

  grouping MPLS-LM-INTF-SWITCHING-CAP-INFO {
    description
      "Information about the Interface Switching
      Capability Descriptor (IXCD)";
    leaf key {
      xr:xr-xml-map "mpls_lcac:Key";
      type uint8;
      description "The switching capability descriptor key";
    }
    leaf switching-capability {
      xr:xr-xml-map "mpls_lcac:SwitchingCapability";
      type uint8;
      description "The switching capability";
    }
    leaf encoding {
      xr:xr-xml-map "mpls_lcac:Encoding";
      type uint8;
      description "The link encoding type";
    }
  }

  grouping MPLS-LM-COMMON-LINK-INFO {
    description "Link information";

    container link-flags {
      description "The link's flags";
      uses MPLS-LM-LINK-FLAGS;
    }
    leaf link-id {
      xr:xr-xml-map "mpls_lcac:LinkID";
      type string;
      description "The link's id";
    }
    leaf link-address {
      xr:xr-xml-map "mpls_lcac:LinkAddress";
      type inet:ipv4-address;
      description "The link's ip address";
    }
    leaf is-unnumbered {
      xr:xr-xml-map "mpls_lcac:IsUnnumbered";
      type boolean;
      description "TRUE if the link is unnumbered";
    }
    leaf has-protection {
      xr:xr-xml-map "mpls_lcac:HasProtection";
      type boolean;
      description "TRUE if the link is protected";
    }
    leaf capability {
      xr:xr-xml-map "mpls_lcac:Capability";
      type uint32;
      description "The link's protection capability";
    }
    leaf working-priority {
      xr:xr-xml-map "mpls_lcac:WorkingPriority";
      type uint32;
      description "The link's working priority";
    }
    leaf resource-provider {
      xr:xr-xml-map "mpls_lcac:ResourceProvider";
      type Resource-provider;
      description "The link's resource provider";
    }
    leaf is-resource-provider-installed {
      xr:xr-xml-map "mpls_lcac:IsResourceProviderInstalled";
      type boolean;
      description "TRUE if the resource provider is installed";
    }
    leaf bandwidth-units {
      xr:xr-xml-map "mpls_lcac:BandwidthUnits";
      type Bandwidth-unit-enum;
      description "The bandwidth units";
    }
    leaf physical-bandwidth {
      xr:xr-xml-map "mpls_lcac:PhysicalBandwidth";
      type uint64;
      description "The link's physical bandwidth";
    }
    leaf bcm-id {
      xr:xr-xml-map "mpls_lcac:BCM_ID";
      type uint16;
      description "Bandwidth Constraints Model ID";
    }
    leaf maximum-reservable-bandwidth {
      xr:xr-xml-map "mpls_lcac:MaximumReservableBandwidth";
      type uint64;
      description "The link's maximum reservable BW";
    }
    leaf incoming-reservable-bandwidth-percentage {
      xr:xr-xml-map "mpls_lcac:IncomingReservableBandwidthPercentag"+
        "e";
      type uint8;
      description "Incoming reserved BW in %";
    }
    leaf outgoing-reservable-bandwidth-percentage {
      xr:xr-xml-map "mpls_lcac:OutgoingReservableBandwidthPercentag"+
        "e";
      type uint8;
      description "Outgoing reserved BW in %";
    }
    leaf maximum-reservable-pool0-bandwidth {
      xr:xr-xml-map "mpls_lcac:MaximumReservablePool0Bandwidth";
      type uint64;
      description "The link's maximum reservable pool0 BW";
    }
    leaf incoming-reservable-pool0-bandwidth-percentage {
      xr:xr-xml-map "mpls_lcac:IncomingReservablePool0BandwidthPerc"+
        "entage";
      type uint8;
      description "Incoming reserved pool0 BW in %";
    }
    leaf outgoing-reservable-pool0-bandwidth-percentage {
      xr:xr-xml-map "mpls_lcac:OutgoingReservablePool0BandwidthPerc"+
        "entage";
      type uint8;
      description "Outgoing reserved pool0 BW in %";
    }
    leaf maximum-reservable-pool1-bandwidth {
      xr:xr-xml-map "mpls_lcac:MaximumReservablePool1Bandwidth";
      type uint64;
      description "The link's maximum reservable pool1 BW";
    }
    leaf incoming-reservable-pool1-bandwidth-percentage {
      xr:xr-xml-map "mpls_lcac:IncomingReservablePool1BandwidthPerc"+
        "entage";
      type uint8;
      description "Incoming reserved pool1 BW in %";
    }
    leaf outgoing-reservable-pool1-bandwidth-percentage {
      xr:xr-xml-map "mpls_lcac:OutgoingReservablePool1BandwidthPerc"+
        "entage";
      type uint8;
      description "Outgoing reserved pool1 BW in %";
    }
    leaf inbound-admission-method {
      xr:xr-xml-map "mpls_lcac:InboundAdmissionMethod";
      type Admission-policy;
      description "Deprecated";
    }
    leaf outbound-admission-method {
      xr:xr-xml-map "mpls_lcac:OutboundAdmissionMethod";
      type Admission-policy;
      description "Deprecated";
    }
    leaf igp-neighbors {
      xr:xr-xml-map "mpls_lcac:IGPNeighbors";
      type uint16;
      description "The link's neighbor count";
    }

    list shared-risk-link-group {
      description "The link's shared risk link groups";
      uses MPLS-SRLG-INFO;
    }

    list interface-switching-capability-descriptor {
      description "The link's switching capability descriptor";
      uses MPLS-LM-INTF-SWITCHING-CAP-INFO;
    }

    list flooded-areas {
      description "List of areas into which the link is flooded";
      uses MPLS-LM-FLOODED-AREA;
    }
  }

  grouping MPLS-LM-BW-ALLOC-LINK-INFO {
    description "Bandwidth allocation information for a given link";

    container link-common {
      description "The link's common info";
      uses MPLS-LM-COMMON-LINK-INFO;
    }

    container upstream-bandwidth {
      description "BW info in the upstream direction";
      uses MPLS-LM-BW-LINK-DIR-BW-INFO;
    }

    container downstream-bandwidth {
      description "BW info in the dnstream direction";
      uses MPLS-LM-BW-LINK-DIR-BW-INFO;
    }
    leaf total-bandwidth-descriptors {
      xr:xr-xml-map "mpls_lcac:TotalBandwidthDescriptors";
      type uint16;
      description "Number of total BW descriptors";
    }
    leaf bandwidth-descriptors {
      xr:xr-xml-map "mpls_lcac:BandwidthDescriptors";
      type uint16;
      description "Number of BW descriptor for the given pool";
    }
    leaf bandwidth-pool {
      xr:xr-xml-map "mpls_lcac:BandwidthPool";
      type Bandwidth-type-enum;
      description "type of the BW pool";
    }
    leaf flooding-up-thresholds-are-default {
      xr:xr-xml-map "mpls_lcac:FloodingUpThresholdsAreDefault";
      type boolean;
      description "TRUE if the up-threshold are default";
    }
    leaf flooding-down-thresholds-are-default {
      xr:xr-xml-map "mpls_lcac:FloodingDownThresholdsAreDefault";
      type boolean;
      description "TRUE if the down-threshold are default";
    }
    leaf flooding-up-thresholds-are-global {
      xr:xr-xml-map "mpls_lcac:FloodingUpThresholdsAreGlobal";
      type boolean;
      description "TRUE if the up-threshold are global";
    }
    leaf flooding-down-thresholds-are-global {
      xr:xr-xml-map "mpls_lcac:FloodingDownThresholdsAreGlobal";
      type boolean;
      description "TRUE if the down-threshold are global";
    }
    leaf-list flooding-up-threshold {
      xr:xr-xml-map "mpls_lcac:FloodingUpThresholds";
      type uint8;
      description "Flooding up-thresholds";
    }
    leaf-list flooding-down-threshold {
      xr:xr-xml-map "mpls_lcac:FloodingDownThresholds";
      type uint8;
      description "Flooding down-thresholds";
    }
  }

  grouping MPLS-LM-BW-ALLOC-COMMON-INFO {
    description "Common information about bandwidth allocation";
    leaf is-role-standby {
      xr:xr-xml-map "mpls_lcac:IsRoleStandby";
      type boolean;
      description "TRUE if Role is Standby, Active otherwise";
    }
    leaf links {
      xr:xr-xml-map "mpls_lcac:Links";
      type uint16;
      description "Number of links";
    }
    leaf bandwidth-hold-time {
      xr:xr-xml-map "mpls_lcac:BandwidthHoldTime";
      type uint16;
      units "second";
      description "How long to hold the bandwith (seconds)";
    }
  }

  grouping MPLS-LM-STATS-LINK-INFO {
    description "Statistics for a link";

    container incoming-path-statistics {
      description "Deprecated";
      uses MPLS-LM-STATS-COUNTERS;
    }

    container incoming-reservation-statistics {
      description "Deprecated";
      uses MPLS-LM-STATS-COUNTERS;
    }

    container outgoing-path-statistics {
      description "Deprecated";
      uses MPLS-LM-STATS-COUNTERS;
    }

    container outgoing-reservation-statistics {
      description "Deprecated";
      uses MPLS-LM-STATS-COUNTERS;
    }

    container incoming-path-statistics32-bit {
      description "Incoming PATH counters";
      uses MPLS-LM-STATS-COUNTERS-32-BIT;
    }

    container incoming-reservation-statistics32-bit {
      description "Incoming RESV counters";
      uses MPLS-LM-STATS-COUNTERS-32-BIT;
    }

    container outgoing-path-statistics32-bit {
      description "Outgoing PATH counters";
      uses MPLS-LM-STATS-COUNTERS-32-BIT;
    }

    container outgoing-reservation-statistics32-bit {
      description "Outgoing RESV counters";
      uses MPLS-LM-STATS-COUNTERS-32-BIT;
    }
    leaf interface-name-xr {
      xr:xr-xml-map "mpls_lcac:interface-name-xr";
      type string;
      description "Link name";
    }
    leaf link-address {
      xr:xr-xml-map "mpls_lcac:LinkAddress";
      type inet:ipv4-address;
      description "Link's ip address";
    }
  }

  grouping MPLS-LM-STATS-COUNTERS-32-BIT {
    description "Statistics for Setup and Tear processing (32 bit)";
    leaf setup-requests {
      xr:xr-xml-map "mpls_lcac:SetupRequests";
      type uint32;
      description "Setup requests";
    }
    leaf setup-errors {
      xr:xr-xml-map "mpls_lcac:SetupErrors";
      type uint32;
      description "Setup errors";
    }
    leaf setup-admits {
      xr:xr-xml-map "mpls_lcac:SetupAdmits";
      type uint32;
      description "Setup admits";
    }
    leaf setup-rejects {
      xr:xr-xml-map "mpls_lcac:SetupRejects";
      type uint32;
      description "Setup rejects";
    }
    leaf tear-requests {
      xr:xr-xml-map "mpls_lcac:TearRequests";
      type uint32;
      description "Tear requests";
    }
    leaf tear-errors {
      xr:xr-xml-map "mpls_lcac:TearErrors";
      type uint32;
      description "Tear errors";
    }
    leaf tear-preempts {
      xr:xr-xml-map "mpls_lcac:TearPreempts";
      type uint32;
      description "Tear preempts";
    }
  }

  grouping MPLS-LM-STATS-COUNTERS {
    description
      "DEPRECATED, use of mpls_lm_stats_counters_32_bit
      recommended";
    leaf setup-requests {
      xr:xr-xml-map "mpls_lcac:SetupRequests";
      type uint16;
      description "Deprecated";
    }
    leaf setup-errors {
      xr:xr-xml-map "mpls_lcac:SetupErrors";
      type uint16;
      description "Deprecated";
    }
    leaf setup-admits {
      xr:xr-xml-map "mpls_lcac:SetupAdmits";
      type uint16;
      description "Deprecated";
    }
    leaf setup-rejects {
      xr:xr-xml-map "mpls_lcac:SetupRejects";
      type uint16;
      description "Deprecated";
    }
    leaf tear-requests {
      xr:xr-xml-map "mpls_lcac:TearRequests";
      type uint16;
      description "Deprecated";
    }
    leaf tear-errors {
      xr:xr-xml-map "mpls_lcac:TearErrors";
      type uint16;
      description "Deprecated";
    }
    leaf tear-preempts {
      xr:xr-xml-map "mpls_lcac:TearPreempts";
      type uint16;
      description "Deprecated";
    }
  }

  grouping MPLS-LM-STATS-SUMMARY-INFO {
    description "Statistics for Path and Reservation processing";

    container path-statistics {
      description "Deprecated";
      uses MPLS-LM-STATS-COUNTERS;
    }

    container reservation-statistics {
      description "Deprecated";
      uses MPLS-LM-STATS-COUNTERS;
    }

    container path-statistics32-bit {
      description "Path counters (32-bit)";
      uses MPLS-LM-STATS-COUNTERS-32-BIT;
    }

    container reservation-statistics32-bit {
      description "Reservation counters (32-bit)";
      uses MPLS-LM-STATS-COUNTERS-32-BIT;
    }
    leaf is-role-standby {
      xr:xr-xml-map "mpls_lcac:IsRoleStandby";
      type boolean;
      description "TRUE if Role is Standby, Active otherwise";
    }
  }

  grouping MPLS-LM-ADV-LINK-RESV-BW {
    description "Information about a link bandwidth";
    leaf priority {
      xr:xr-xml-map "mpls_lcac:Priority";
      type uint8;
      description "The priority level of this bandwidth";
    }
    leaf pool0-bandwidth {
      xr:xr-xml-map "mpls_lcac:Pool0Bandwidth";
      type uint32;
      description "The reservable pool0 BW at this priority";
    }
    leaf pool1-bandwidth {
      xr:xr-xml-map "mpls_lcac:Pool1Bandwidth";
      type uint32;
      description "The reservable pool1 BW at this priority";
    }
  }

  grouping MPLS-LM-ADV-FLOODED-LINK {
    description "Information about a flooded link";

    container odu-link-capabilities {
      description "ODU Link Capabilities";
      uses ODU-LINK-CAPABILITIES;
    }
    leaf link-id {
      xr:xr-xml-map "mpls_lcac:LinkID";
      type uint16;
      description "The link's id";
    }
    leaf interface-name {
      xr:xr-xml-map "mpls_lcac:InterfaceName";
      type string;
      description "The link's interface name";
    }
    leaf link-address {
      xr:xr-xml-map "mpls_lcac:LinkAddress";
      type inet:ipv4-address;
      description "The link's IPv4 address";
    }
    leaf subnet-type {
      xr:xr-xml-map "mpls_lcac:SubnetType";
      type Igp-subnet;
      description "The link's subnet type";
    }
    leaf outgoing-interface-id {
      xr:xr-xml-map "mpls_lcac:OutgoingInterfaceID";
      type uint32;
      description "The link's outgoing interface's id";
    }
    leaf is-designated-router {
      xr:xr-xml-map "mpls_lcac:IsDesignatedRouter";
      type boolean;
      description "TRUE if the link belongs to a desig. router";
    }
    leaf designated-router-igp-id {
      xr:xr-xml-map "mpls_lcac:DesignatedRouterIGP_ID";
      type string;
      description "IGP id of the designated router";
    }
    leaf neighbor-igp-id {
      xr:xr-xml-map "mpls_lcac:NeighborIGP_ID";
      type string;
      description "The neighbor's IGP id";
    }
    leaf igp-neighbor-address {
      xr:xr-xml-map "mpls_lcac:IGPNeighborAddress";
      type inet:ipv4-address;
      description "The neighbor's ip address";
    }
    leaf incoming-interface-id {
      xr:xr-xml-map "mpls_lcac:IncomingInterfaceID";
      type uint32;
      description "The link's incoming interface's id";
    }
    leaf te-metric {
      xr:xr-xml-map "mpls_lcac:TEMetric";
      type uint32;
      description "The link's TE metric";
    }
    leaf igp-metric {
      xr:xr-xml-map "mpls_lcac:IGPMetric";
      type uint32;
      description "The link's IGP metric";
    }
    leaf uni-link-delay {
      xr:xr-xml-map "mpls_lcac:UniLinkDelay";
      type uint32;
      description "Unidirectional Link Delay in micro-sec";
    }
    leaf bandwidth-units {
      xr:xr-xml-map "mpls_lcac:BandwidthUnits";
      type Bandwidth-unit-enum;
      description "The link's bandwidth units";
    }
    leaf physical-bandwidth {
      xr:xr-xml-map "mpls_lcac:PhysicalBandwidth";
      type uint32;
      description "The link's physical BW";
    }
    leaf bcm-id {
      xr:xr-xml-map "mpls_lcac:BCM_ID";
      type uint16;
      description "Bandwidth Constraints Model ID";
    }
    leaf link-maximum-reservable-bandwidth {
      xr:xr-xml-map "mpls_lcac:LinkMaximumReservableBandwidth";
      type uint32;
      description "The link's maximum reservable BW";
    }
    leaf reservable-pool0-bandwidth {
      xr:xr-xml-map "mpls_lcac:ReservablePool0Bandwidth";
      type uint32;
      description "The link's reservable pool0 BW";
    }
    leaf reservable-pool1-bandwidth {
      xr:xr-xml-map "mpls_lcac:ReservablePool1Bandwidth";
      type uint32;
      description "The link's reservable pool1 BW";
    }
    leaf is-receiving-reservable-bandwidth-enabled {
      xr:xr-xml-map "mpls_lcac:IsReceivingReservableBandwidthEnable"+
        "d";
      type boolean;
      description "TRUE if receiving reservable BW is enabled";
    }
    leaf receiving-direction {
      xr:xr-xml-map "mpls_lcac:ReceivingDirection";
      type Link-direction-enum;
      description "Upstream or Downstream";
    }
    leaf is-transmitting-reservable-bandwidth-enabled {
      xr:xr-xml-map "mpls_lcac:IsTransmittingReservableBandwidthEna"+
        "bled";
      type boolean;
      description "TRUE if transmitting reservable BW is enabled";
    }
    leaf transmitting-direction {
      xr:xr-xml-map "mpls_lcac:TransmittingDirection";
      type Link-direction-enum;
      description "Upstream or Downstream";
    }
    leaf affinity-attribute-flags {
      xr:xr-xml-map "mpls_lcac:AffinityAttributeFlags";
      type uint32;
      description "Deprecated";
    }
    leaf-list extended-affinity-attribute-flag {
      xr:xr-xml-map "mpls_lcac:ExtendedAffinityAttributeFlags";
      type uint32;
      description "The link's extended affinity bits";
    }

    list shared-risk-link-group {
      description "The link's shared risk link groups";
      uses MPLS-SRLG-INFO;
    }

    list receiving-reservable-bandwidth {
      max-elements "8";
      description
        "Receiving reservable BW at each priority
        level(priority 0 to priority 7)";
      uses MPLS-LM-ADV-LINK-RESV-BW;
    }

    list transmitting-reservable-bandwidth {
      max-elements "8";
      description
        "Transmitting reservable BW at each priority
        level (priority 0 to priority 7)";
      uses MPLS-LM-ADV-LINK-RESV-BW;
    }
  }

  grouping MPLS-LM-ADV-CONFIGURED-AREA {
    description "The information about an advertized area";
    leaf igp-area-id {
      xr:xr-xml-map "mpls_lcac:IGPAreaID";
      type string;
      description "The area id";
    }
    leaf protocol {
      xr:xr-xml-map "mpls_lcac:Protocol";
      type Igp-protocol;
      description "The IGP protocol running over this area";
    }
    leaf system-id {
      xr:xr-xml-map "mpls_lcac:SystemID";
      type string;
      description "The node's system id";
    }
    leaf router-id {
      xr:xr-xml-map "mpls_lcac:RouterID";
      type inet:ipv4-address;
      description "The node's router ID";
    }

    list flooded-link {
      description "The array of flooded links in this area";
      uses MPLS-LM-ADV-FLOODED-LINK;
    }
  }

  grouping MPLS-LM-ADVERTISEMENT-INFO {
    description "Information about all the advertized areas";
    leaf flooding-status-message {
      xr:xr-xml-map "mpls_lcac:FloodingStatusMessage";
      type string;
      description "Flooding status: ready or reason";
    }
    leaf last-flooding-time {
      xr:xr-xml-map "mpls_lcac:LastFloodingTime";
      type uint32;
      units "second";
      description "Time elapsed since last flooding in seconds";
    }
    leaf last-flooding-trigger {
      xr:xr-xml-map "mpls_lcac:LastFloodingTrigger";
      type Flooding-trigger;
      description "Trigger for last flooding";
    }
    leaf next-flooding-time {
      xr:xr-xml-map "mpls_lcac:NextFloodingTime";
      type uint32;
      units "second";
      description "Time remained for next flooding in seconds";
    }
    leaf ds-te-mode {
      xr:xr-xml-map "mpls_lcac:DS_TEMode";
      type Rrr-dste-migration-mode;
      description "DS-TE Mode";
    }

    list advertized-areas {
      description "Advertising info for all the IGP areas";
      uses MPLS-LM-ADV-CONFIGURED-AREA;
    }
  }

  grouping MPLS-LM-PREEMPTED-LSP {
    description "Preempted LSP info";
    leaf tunnel-id {
      xr:xr-xml-map "mpls_lcac:TunnelID";
      type uint16;
      description "Tunnel ID";
    }
    leaf lsp-id {
      xr:xr-xml-map "mpls_lcac:LSP_ID";
      type uint16;
      description "LSP ID";
    }
    leaf source-address {
      xr:xr-xml-map "mpls_lcac:SourceAddress";
      type inet:ipv4-address;
      description "Source";
    }
    leaf destination-address {
      xr:xr-xml-map "mpls_lcac:DestinationAddress";
      type inet:ipv4-address;
      description "Destination";
    }
    leaf requested-bandwidth {
      xr:xr-xml-map "mpls_lcac:RequestedBandwidth";
      type uint64;
      description "The path's requested bandwidth";
    }
    leaf setup-priority {
      xr:xr-xml-map "mpls_lcac:SetupPriority";
      type uint8;
      description "The path's setup priority";
    }
    leaf hold-priority {
      xr:xr-xml-map "mpls_lcac:HoldPriority";
      type uint8;
      description "The path's hold priority";
    }
    leaf bandwidth-type {
      xr:xr-xml-map "mpls_lcac:BandwidthType";
      type uint8;
      description "The path's bandwidth type; 0:BC0, 1:BC1, so on";
    }
    leaf soft-preempted {
      xr:xr-xml-map "mpls_lcac:SoftPreempted";
      type boolean;
      description "TRUE is the preemption is a soft preemption";
    }
    leaf soft-preemption-timeout {
      xr:xr-xml-map "mpls_lcac:SoftPreemptionTimeout";
      type uint16;
      units "second";
      description
        "If the soft preemption is underway, this value
        indicates the number of seconds before hard
        preemption is triggered";
    }
    leaf bandwidth-preempted {
      xr:xr-xml-map "mpls_lcac:BandwidthPreempted";
      type boolean;
      description "LSPs bandwidth is already preempted";
    }
    leaf soft-preempted-fr-rrewrite {
      xr:xr-xml-map "mpls_lcac:SoftPreemptedFRRrewrite";
      type boolean;
      description "FRR-rewrite is done during soft preemption";
    }
  }

  grouping MPLS-LM-PREEMPTION-EVENT {
    description "Preemption event info";
    leaf tunnel-id {
      xr:xr-xml-map "mpls_lcac:TunnelID";
      type uint16;
      description "Tunnel ID";
    }
    leaf lsp-id {
      xr:xr-xml-map "mpls_lcac:LSP_ID";
      type uint16;
      description "LSP ID";
    }
    leaf source-address {
      xr:xr-xml-map "mpls_lcac:SourceAddress";
      type inet:ipv4-address;
      description "Source";
    }
    leaf destination-address {
      xr:xr-xml-map "mpls_lcac:DestinationAddress";
      type inet:ipv4-address;
      description "Destination";
    }
    leaf requested-bandwidth {
      xr:xr-xml-map "mpls_lcac:RequestedBandwidth";
      type uint64;
      description "The path's requested bandwidth";
    }
    leaf setup-priority {
      xr:xr-xml-map "mpls_lcac:SetupPriority";
      type uint8;
      description "The path's setup priority";
    }
    leaf hold-priority {
      xr:xr-xml-map "mpls_lcac:HoldPriority";
      type uint8;
      description "The path's hold priority";
    }
    leaf bandwidth-type {
      xr:xr-xml-map "mpls_lcac:BandwidthType";
      type uint8;
      description "The path's bandwidth type; 0:CT0, 1:CT1, so on";
    }
    leaf old-bandwidth-bc0 {
      xr:xr-xml-map "mpls_lcac:OldBandwidthBC0";
      type uint64;
      description "Old BW for BC0";
    }
    leaf old-bandwidth-bc1 {
      xr:xr-xml-map "mpls_lcac:OldBandwidthBC1";
      type uint64;
      description "Old BW for BC1";
    }
    leaf new-bandwidth-bc0 {
      xr:xr-xml-map "mpls_lcac:NewBandwidthBC0";
      type uint64;
      description "New BW for BC0";
    }
    leaf new-bandwidth-bc1 {
      xr:xr-xml-map "mpls_lcac:NewBandwidthBC1";
      type uint64;
      description "New BW for BC1";
    }
    leaf bandwidth-overshoot0 {
      xr:xr-xml-map "mpls_lcac:BandwidthOvershoot0";
      type uint64;
      description "BW Overshoot for BC0";
    }
    leaf bandwidth-overshoot1 {
      xr:xr-xml-map "mpls_lcac:BandwidthOvershoot1";
      type uint64;
      description "BW Overshoot for BC1";
    }
    leaf interface-name {
      xr:xr-xml-map "mpls_lcac:InterfaceName";
      type string;
      description "Interface name";
    }
    leaf event-time {
      xr:xr-xml-map "mpls_lcac:EventTime";
      type uint32;
      units "second";
      description
        "Event time; seconds elapsed since January 1,
        1970";
    }
    leaf ls-ps {
      xr:xr-xml-map "mpls_lcac:LSPs";
      type uint16;
      description
        "Number of LSPs (not all may be present in the
        list)";
    }
    leaf soft-preempted-ls-ps {
      xr:xr-xml-map "mpls_lcac:SoftPreemptedLSPs";
      type uint16;
      description "Number of LSPs softly preempted";
    }
    leaf soft-preempted-ls-ps-fr-rrewrite {
      xr:xr-xml-map "mpls_lcac:SoftPreemptedLSPsFRRrewrite";
      type uint16;
      description
        "Number of LSPs softly preempted with traffic
        switched to backup";
    }
    leaf hard-preempted-ls-ps {
      xr:xr-xml-map "mpls_lcac:HardPreemptedLSPs";
      type uint16;
      description "Number of LSPs hardly preempted";
    }
    leaf total-preempted-bandwidth-bc0 {
      xr:xr-xml-map "mpls_lcac:TotalPreemptedBandwidthBC0";
      type uint64;
      description "Total amount of preempted class 0 bandwidth";
    }
    leaf total-preempted-bandwidth-bc1 {
      xr:xr-xml-map "mpls_lcac:TotalPreemptedBandwidthBC1";
      type uint64;
      description "Total amount of preempted class 1 bandwidth";
    }
    leaf softly-preempted-bandwidth-bc0 {
      xr:xr-xml-map "mpls_lcac:SoftlyPreemptedBandwidthBC0";
      type uint64;
      description "Amount of softly preempted class 0 bandwidth";
    }
    leaf softly-preempted-bandwidth-bc1 {
      xr:xr-xml-map "mpls_lcac:SoftlyPreemptedBandwidthBC1";
      type uint64;
      description "Amount of softly preempted class 1 bandwidth";
    }
    leaf soft-preempted-fr-rrewrite-bandwidth-bc0 {
      xr:xr-xml-map "mpls_lcac:SoftPreemptedFRRrewriteBandwidthBC0";
      type uint64;
      description
        "Amount of softly preempted FRR RW class 0
        bandwidth";
    }
    leaf soft-preempted-fr-rrewrite-bandwidth-bc1 {
      xr:xr-xml-map "mpls_lcac:SoftPreemptedFRRrewriteBandwidthBC1";
      type uint64;
      description
        "Amount of softly preempted FRR RW class 1
        bandwidth";
    }
    leaf hard-preempted-bandwidth-bc0 {
      xr:xr-xml-map "mpls_lcac:HardPreemptedBandwidthBC0";
      type uint64;
      description "Amount of hard preempted class 0 bandwidth";
    }
    leaf hard-preempted-bandwidth-bc1 {
      xr:xr-xml-map "mpls_lcac:HardPreemptedBandwidthBC1";
      type uint64;
      description "Amount of hard preempted class 1 bandwidth";
    }
    leaf tunnels {
      xr:xr-xml-map "mpls_lcac:Tunnels";
      type uint16;
      description "Number of Tunnels";
    }
    leaf soft-preempted-tunnels {
      xr:xr-xml-map "mpls_lcac:SoftPreemptedTunnels";
      type uint16;
      description "Number of Tunnels softly preempted";
    }
    leaf soft-preempted-tunnels-fr-rrewrite {
      xr:xr-xml-map "mpls_lcac:SoftPreemptedTunnelsFRRrewrite";
      type uint16;
      description
        "Number of Tunnels softly preempted with traffic
        switched to backup";
    }
    leaf hard-preempted-tunnels {
      xr:xr-xml-map "mpls_lcac:HardPreemptedTunnels";
      type uint16;
      description "Number of Tunnels hardly preempted";
    }

    list lsp {
      description "List of preempted LSPs";
      uses MPLS-LM-PREEMPTED-LSP;
    }
  }

  grouping MPLS-LM-IGP-NBR-INFO {
    description "Neighbor information";
    leaf interface-name {
      xr:xr-xml-map "mpls_lcac:InterfaceName";
      type string;
      description
        "The interface on which this neighbor is
        discovered";
    }
    leaf neighbor-id {
      xr:xr-xml-map "mpls_lcac:NeighborID";
      type string;
      description "The neighbor's id";
    }
    leaf area-id {
      xr:xr-xml-map "mpls_lcac:AreaID";
      type string;
      description "The area id";
    }
    leaf neighbor-address {
      xr:xr-xml-map "mpls_lcac:NeighborAddress";
      type inet:ipv4-address;
      description "The neighbor's IP address";
    }
  }

  grouping MPLS-LM-IGP-NBRS-LINK-INFO {
    description "Neighbor information based on the link";

    list neighbor {
      description "Neighbors of the specified link id";
      uses MPLS-LM-IGP-NBR-INFO;
    }
  }

  grouping MPLS-TE-AFFINITY-MAP-BAG {
    description "A set of affinity maps";

    list affinity-map-array {
      description "Affinity map array";
      uses MPLS-TE-AFFINITY-MAP-INFO;
    }
  }

  grouping MPLS-TE-BFD-SUMMARY {
    description "TE BFD Summary Info";
    leaf tunnel-count-total {
      xr:xr-xml-map "mpls_lcac:TunnelCountTotal";
      type uint16;
      description "Total number of tunnel interface";
    }
    leaf tunnel-count-bfd-enabled {
      xr:xr-xml-map "mpls_lcac:TunnelCountBFDEnabled";
      type uint16;
      description "Number of tunnel interface with BFD enabled";
    }
    leaf tunnel-count-session-up {
      xr:xr-xml-map "mpls_lcac:TunnelCountSessionUp";
      type uint16;
      description "Number of tunnel with BFD session in up state";
    }
    leaf head-lsp-count-session-created {
      xr:xr-xml-map "mpls_lcac:HeadLSPCountSessionCreated";
      type uint16;
      description "Number of head end LSP with BFD session created";
    }
    leaf head-lsp-count-up {
      xr:xr-xml-map "mpls_lcac:HeadLSPCountUp";
      type uint16;
      description
        "Number of head end LSP with BFD session in up
        state";
    }
    leaf tail-lsp-count-session-created {
      xr:xr-xml-map "mpls_lcac:TailLSPCountSessionCreated";
      type uint16;
      description "Number of tail end LSP with BFD session created";
    }
    leaf tail-lsp-count-session-up {
      xr:xr-xml-map "mpls_lcac:TailLSPCountSessionUp";
      type uint16;
      description
        "Number of tail end LSP with BFD session in up
        state";
    }
    leaf link-count-bfd-enabled {
      xr:xr-xml-map "mpls_lcac:LinkCountBFDEnabled";
      type uint16;
      description "Number of link with BFD enabled";
    }
    leaf link-count-session-created {
      xr:xr-xml-map "mpls_lcac:LinkCountSessionCreated";
      type uint16;
      description "Number of link with BFD session created";
    }
    leaf link-count-session-up {
      xr:xr-xml-map "mpls_lcac:LinkCountSessionUp";
      type uint16;
      description "Number of link with BFD session in state Up";
    }
  }

  grouping MPLS-TE-TAIL-BFD-LSP-INFO {
    description "TE Tail End BFDOverLSP Info";

    container lsp-fec {
      description "FEC for the LSP";
      uses TE-LSP-FEC;
    }
    leaf signaled-name {
      xr:xr-xml-map "mpls_lcac:SignaledName";
      type string;
      description "Signaled Name";
    }
    leaf bfd-session-state {
      xr:xr-xml-map "mpls_lcac:BFDSessionState";
      type Te-bfd-lsp-session-state;
      description "BFD Session State";
    }
  }

  grouping MPLS-TE-HEAD-BFD-LSP-INFO {
    description "TE Head End BFDOverLSP Info";
    leaf lsp-id {
      xr:xr-xml-map "mpls_lcac:LSP_ID";
      type uint16;
      description "LSP ID";
    }
    leaf bfd-session-state {
      xr:xr-xml-map "mpls_lcac:BFDSessionState";
      type Te-bfd-lsp-session-state;
      description "BFD Session State";
    }
  }

  grouping MPLS-TE-HEAD-BFD-VIF-INFO {
    description "TE Head End Tunnel BFD Info";

    container current-lspbfd-info {
      description "Current LSP BFD Info";
      uses MPLS-TE-HEAD-BFD-LSP-INFO;
    }

    container standby-lspbfd-info {
      description "Standby LSP BFD Info";
      uses MPLS-TE-HEAD-BFD-LSP-INFO;
    }

    container reoptimized-lspbfd-info {
      description "Reoptimized LSP BFD Info";
      uses MPLS-TE-HEAD-BFD-LSP-INFO;
    }
    leaf tunnel-name-xr {
      xr:xr-xml-map "mpls_lcac:tunnel-name-xr";
      type string;
      description "Tunnel name";
    }
    leaf destination-address {
      xr:xr-xml-map "mpls_lcac:DestinationAddress";
      type inet:ipv4-address;
      description "Destination Address";
    }
  }

  grouping MPLS-TE-SR-S2L-PATH-BAG {
    description "Segment-Routing S2L path";
    leaf is-primary {
      xr:xr-xml-map "mpls_lcac:IsPrimary";
      type boolean;
      description "True if path is primary";
    }
    leaf is-backup {
      xr:xr-xml-map "mpls_lcac:IsBackup";
      type boolean;
      description "True if path is backup";
    }
    leaf outgoing-interface {
      xr:xr-xml-map "mpls_lcac:OutgoingInterface";
      type string;
      description "Outgoing Interface Name";
    }
    leaf path-id {
      xr:xr-xml-map "mpls_lcac:path_id";
      type uint32;
      description "Path Identifier";
    }
    leaf backup-path-id {
      xr:xr-xml-map "mpls_lcac:backup_path_id";
      type uint32;
      description "Backup Path Identifier";
    }
    leaf next-hop {
      xr:xr-xml-map "mpls_lcac:NextHop";
      type inet:ipv4-address;
      description "Next hop";
    }
    leaf-list outgoing-labels-stack {
      xr:xr-xml-map "mpls_lcac:OutgoingLabelsStack";
      type uint32;
      description "Outgoing Labels Stack";
    }
  }

  grouping MPLS-TE-S2L-FORWARDING-S2L-ID-BAG {
    description "S2L Forwarding identifiers";
    leaf destination-address {
      xr:xr-xml-map "mpls_lcac:DestinationAddress";
      type inet:ipv4-address;
      description "Destination";
    }
    leaf sub-group-id {
      xr:xr-xml-map "mpls_lcac:SubGroupID";
      type uint16;
      description "S2L Sub-Group ID";
    }
    leaf sub-group-original-id {
      xr:xr-xml-map "mpls_lcac:SubGroupOriginalID";
      type inet:ipv4-address;
      description "S2L Sub-Group Originator ID";
    }
  }

  grouping TE-S2L-OUTPUT-RW-FIELDS-BAG {
    description "An entry of output label rewrite data";

    container primary-s2l {
      description "Properties of the S2L rewrite";
      uses TE-S2L-OUTPUT-RW-OUTPUT-INFO-BAG;
    }

    container backup-tunnel-rewrite {
      description "Properties of the S2L's backup tunnel rewrite";
      uses TE-S2L-OUTPUT-RW-OUTPUT-INFO-BAG;
    }
    leaf timestamp {
      xr:xr-xml-map "mpls_lcac:Timestamp";
      type uint32;
      units "second";
      description "Time stamp of the entry (secs since 1/1/70)";
    }
    leaf out-rewrite-role {
      xr:xr-xml-map "mpls_lcac:OutRewriteRole";
      type Mpls-te-tunnel-role;
      description "Role of the associated S2L";
    }
    leaf label {
      xr:xr-xml-map "mpls_lcac:Label";
      type uint32;
      description "Local label of the rewrite";
    }
    leaf backup-active {
      xr:xr-xml-map "mpls_lcac:BackupActive";
      type boolean;
      description "Backup is active";
    }
    leaf s2l-source {
      xr:xr-xml-map "mpls_lcac:S2LSource";
      type inet:ipv4-address;
      description "Source of the S2L";
    }
    leaf explicit-null {
      xr:xr-xml-map "mpls_lcac:ExplicitNull";
      type Te-s2l-output-rw-explicit-null;
      description "Imposition of explicit NULL";
    }
    leaf protocol-transported {
      xr:xr-xml-map "mpls_lcac:ProtocolTransported";
      type uint16;
      description "Protocol transported in the S2L";
    }
  }

  grouping TE-S2L-OUTPUT-RW-FEC-SUBFAMILY-BAG {
    description "LMRIB S2L Output label rewrite FEC subfamily";

    container lsp-fec {
      description "LSP FEC";
      uses TE-LSP-FEC;
    }
    leaf next-hop-address {
      xr:xr-xml-map "mpls_lcac:NextHopAddress";
      type inet:ipv4-address;
      description "Next hop address";
    }
    leaf previous-hop-address {
      xr:xr-xml-map "mpls_lcac:PreviousHopAddress";
      type inet:ipv4-address;
      description "Previous hop address";
    }
  }

  grouping MPLS-TE-S2L-OUTPUT-RW-BAG {
    description "S2L output rewrite";

    container subfamily {
      description "Subfamily identifiers";
      uses TE-S2L-OUTPUT-RW-FEC-SUBFAMILY-BAG;
    }

    container successful-rewrite {
      description "Successful rewrite details";
      uses TE-S2L-OUTPUT-RW-FIELDS-BAG;
    }

    container failed-rewrite {
      description "Failed rewrite details";
      uses TE-S2L-OUTPUT-RW-FIELDS-BAG;
    }

    container pending-rewrite {
      description "Pending rewrite details";
      uses TE-S2L-OUTPUT-RW-FIELDS-BAG;
    }
  }

  grouping MPLS-TE-S2L-FORWARDING-BAG {
    description "Output label forwarding details for S2Ls";

    container s2l-output-rewrite {
      description "Output rewrite shared between S2Ls";
      uses MPLS-TE-S2L-OUTPUT-RW-BAG;
    }
    leaf original-input-interface {
      xr:xr-xml-map "mpls_lcac:OriginalInputInterface";
      type string;
      description "Input interface of the S2Ls";
    }
    leaf output-interface-name {
      xr:xr-xml-map "mpls_lcac:OutputInterfaceName";
      type string;
      description "The output interface of the S2Ls";
    }
    leaf backup-tunnel-name {
      xr:xr-xml-map "mpls_lcac:BackupTunnelName";
      type string;
      description "Backup tunnel name";
    }
    leaf is-segment-routing {
      xr:xr-xml-map "mpls_lcac:IsSegmentRouting";
      type boolean;
      description "TRUE if the s2l path is Segment-Routing";
    }

    list s2l {
      description
        "Unique identifiers for the S2L sharing the
        rewrite";
      uses MPLS-TE-S2L-FORWARDING-S2L-ID-BAG;
    }

    list s2lsr-path {
      description "Segment-Routing Paths";
      uses MPLS-TE-SR-S2L-PATH-BAG;
    }
  }

  grouping TE-S2L-TUN-RW-FIELDS-P2MP-BAG {
    description "LMRIB Tunnel rewrite fields";
    leaf local-label {
      xr:xr-xml-map "mpls_lcac:LocalLabel";
      type uint32;
      description "Local Label";
    }
  }

  grouping TE-S2L-OUTPUT-RW-OUTPUT-INFO-BAG {
    description "Output rewrite tunnel information";
    leaf physica-interface-name {
      xr:xr-xml-map "mpls_lcac:PhysicaInterfaceName";
      type xr:Interface-name;
      description "Physical interface associated with the entry";
    }
    leaf tunnel-interface-name {
      xr:xr-xml-map "mpls_lcac:TunnelInterfaceName";
      type xr:Interface-name;
      description "Interface handle of the associated tunnel";
    }
    leaf parent-interface-name {
      xr:xr-xml-map "mpls_lcac:ParentInterfaceName";
      type xr:Interface-name;
      description "Interface name of the parent intf";
    }
    leaf next-hop-address {
      xr:xr-xml-map "mpls_lcac:NextHopAddress";
      type inet:ipv4-address;
      description "Next hop address associated with the entry";
    }
    leaf out-label {
      xr:xr-xml-map "mpls_lcac:OutLabel";
      type uint32;
      description "Output label associated with the entry";
    }
    leaf-list sr-label-stack {
      xr:xr-xml-map "mpls_lcac:SRLabelStack";
      type uint32;
      description "Segment-Routing labels stack";
    }
  }

  grouping TE-S2L-TUN-RW-FIELDS-P2P-BAG {
    description "LSD Tunnel rewrite fields";

    container primary-s2l {
      description "Properties of the primary S2L of tunnel rewrite";
      uses TE-S2L-OUTPUT-RW-OUTPUT-INFO-BAG;
    }

    container backup-tunnel-rewrite {
      description
        "Properties of the S2L's backup for tunnel
        rewrite";
      uses TE-S2L-OUTPUT-RW-OUTPUT-INFO-BAG;
    }
    leaf local-label {
      xr:xr-xml-map "mpls_lcac:LocalLabel";
      type uint32;
      description "Local label of the tunnel rewrite";
    }
    leaf tunnel-id {
      xr:xr-xml-map "mpls_lcac:TunnelID";
      type uint16;
      description "Tunnel ID for this rewrite data";
    }
    leaf source-pe {
      xr:xr-xml-map "mpls_lcac:SourcePE";
      type inet:ipv4-address;
      description "source address of the tunnel";
    }
    leaf destination-address {
      xr:xr-xml-map "mpls_lcac:DestinationAddress";
      type inet:ipv4-address;
      description "Destination";
    }
    leaf extended-tunnel-id {
      xr:xr-xml-map "mpls_lcac:ExtendedTunnelID";
      type inet:ipv4-address;
      description "Extended Tunnel ID";
    }
    leaf backup-active {
      xr:xr-xml-map "mpls_lcac:BackupActive";
      type boolean;
      description "FRR is active on the backup tunnel";
    }
    leaf original-input-interface {
      xr:xr-xml-map "mpls_lcac:OriginalInputInterface";
      type string;
      description "Input interface of the S2Ls";
    }
    leaf previous-hop-address {
      xr:xr-xml-map "mpls_lcac:PreviousHopAddress";
      type inet:ipv4-address;
      description "Previous hop";
    }
    leaf output-interface-name {
      xr:xr-xml-map "mpls_lcac:OutputInterfaceName";
      type string;
      description "The output interface of the S2Ls";
    }
    leaf backup-tunnel-name {
      xr:xr-xml-map "mpls_lcac:BackupTunnelName";
      type string;
      description "Backup tunnel name";
    }
  }

  grouping TE-S2L-TUN-RW-FIELD-CTYPE-BAG {
    description "C-type-specific LSP FEC data";

    container p2p-tunnel-rewrite {
      when "../fec-ctype = 'mpls-lib-c-type-ipv4-p2p-tunnel'" {
        description
          "../FEC_CType = 'MPLS_LIB_CTYPE_IPV4_P2P_TUNNEL'";
      }
      description "Tunnel rewrite data specific to P2P";
      uses TE-S2L-TUN-RW-FIELDS-P2P-BAG;
    }

    container p2mp-tunnel-rewrite {
      when "../fec-ctype = 'mpls-lib-c-type-ipv4-p2mp-tunnel'" {
        description
          "../FEC_CType =
          'MPLS_LIB_CTYPE_IPV4_P2MP_TUNNEL'";
      }
      description "Tunnel rewrite data specific to P2MP";
      uses TE-S2L-TUN-RW-FIELDS-P2MP-BAG;
    }
    leaf fec-ctype {
      xr:xr-xml-map "mpls_lcac:FEC_CType";
      type Mpls-lib-c;
      description "FEC CType";
    }
  }

  grouping TE-S2L-TUN-RW-FIELDS-BAG {
    description "LMRIB S2L Tunnel rewrite fields";

    container tunnel-rewrite {
      description "Union of p2p and p2mp tun rewrite data";
      uses TE-S2L-TUN-RW-FIELD-CTYPE-BAG;
    }
    leaf timestamp {
      xr:xr-xml-map "mpls_lcac:Timestamp";
      type uint32;
      description "Time stamp of the entry";
    }
  }

  grouping MPLS-TE-S2L-TUN-RW-BAG {
    description "LMRIB S2L Tunnel rewrite";

    container successful-rewrite {
      description "Successful rewrite details";
      uses TE-S2L-TUN-RW-FIELDS-BAG;
    }

    container failed-rewrite {
      description "Failed rewrite details";
      uses TE-S2L-TUN-RW-FIELDS-BAG;
    }

    container pending-rewrite {
      description "Pending rewrite details";
      uses TE-S2L-TUN-RW-FIELDS-BAG;
    }
    leaf tunnel-interface {
      xr:xr-xml-map "mpls_lcac:TunnelInterface";
      type string;
      description "Tunnel interface name";
    }
    leaf tunnel-signal-name {
      xr:xr-xml-map "mpls_lcac:TunnelSignalName";
      type string;
      description "Tunnel signaled-name";
    }
    leaf is-segment-routing {
      xr:xr-xml-map "mpls_lcac:IsSegmentRouting";
      type boolean;
      description "TRUE if the s2l path is Segment-Routing";
    }
  }

  grouping TE-PP-SW-LOG-BAG {
    description
      "The full log of the path protection switchover
      events";
    leaf path-protection-switchovers {
      xr:xr-xml-map "mpls_lcac:PathProtectionSwitchovers";
      type uint32;
      description
        "Total number of path protection switchover
        events. This could be more than the entries in
        the array";
    }
    leaf maximum-switchover-millisec {
      xr:xr-xml-map "mpls_lcac:MaximumSwitchoverMillisec";
      type uint32;
      units "millisecond";
      description
        "The maximum delay for a switchover in
        milliseconds";
    }
    leaf average-switchover-millisec {
      xr:xr-xml-map "mpls_lcac:AverageSwitchoverMillisec";
      type uint32;
      units "millisecond";
      description
        "The average delay for a switchover in
        milliseconds";
    }

    list path-protection-switchover-entry {
      description "The array of path protection switchover entries";
      uses TE-PP-SW-LOG-ENTRY-BAG;
    }
  }

  grouping TUNNEL-MAX-INFO {
    description "Tunnel maximum information bag";
    leaf current-maximum-tunnels {
      xr:xr-xml-map "mpls_lcac:CurrentMaximumTunnels";
      type uint32;
      description "Current Maximum Tunnels";
    }
    leaf current-maximum-destinations {
      xr:xr-xml-map "mpls_lcac:CurrentMaximumDestinations";
      type uint32;
      description "Current Maximum Destinations";
    }
    leaf current-maximum-p2mp-tunnels {
      xr:xr-xml-map "mpls_lcac:CurrentMaximumP2MPTunnels";
      type uint32;
      description "Current Maximum P2MP Tunnel Count";
    }
    leaf current-maximum-p2mp-destnation-per-tunnel {
      xr:xr-xml-map "mpls_lcac:CurrentMaximumP2MPDestnationPerTunne"+
        "l";
      type uint32;
      description
        "Current Maximum P2MP Destinations Per Tunnel
        Count";
    }
    leaf absolute-maximum {
      xr:xr-xml-map "mpls_lcac:AbsoluteMaximum";
      type uint32;
      description "Absolute Maximum";
    }
    leaf current-maximum-autobackups {
      xr:xr-xml-map "mpls_lcac:CurrentMaximumAutobackups";
      type uint32;
      description "Current Maximum Autotunnel Backups Allowed";
    }
    leaf current-maximum-auto-mesh {
      xr:xr-xml-map "mpls_lcac:CurrentMaximumAutoMesh";
      type uint32;
      description "Current Maximum Autotunnel Mesh Allowed";
    }
    leaf current-tunnel-count {
      xr:xr-xml-map "mpls_lcac:CurrentTunnelCount";
      type uint32;
      description "Current tunnel count";
    }
    leaf current-destination-count {
      xr:xr-xml-map "mpls_lcac:CurrentDestinationCount";
      type uint32;
      description "Current Destination Count";
    }
    leaf current-p2mp-tunnel-count {
      xr:xr-xml-map "mpls_lcac:CurrentP2MPTunnelCount";
      type uint32;
      description "Current P2MP tunnel count";
    }
    leaf current-p2mp-destnation-per-tunnel-count {
      xr:xr-xml-map "mpls_lcac:CurrentP2MPDestnationPerTunnelCount";
      type uint32;
      description "Current P2MP Destination per tunnel count";
    }
    leaf is-autobackup-range-configured {
      xr:xr-xml-map "mpls_lcac:IsAutobackupRangeConfigured";
      type boolean;
      description "TRUE if the autobackup range is configured";
    }
    leaf current-autobackups {
      xr:xr-xml-map "mpls_lcac:CurrentAutobackups";
      type uint32;
      description "Current Autotunnel Backup count";
    }
    leaf is-auto-mesh-range-configured {
      xr:xr-xml-map "mpls_lcac:IsAutoMeshRangeConfigured";
      type boolean;
      description "TRUE if the automesh range is configured";
    }
    leaf current-auto-mesh {
      xr:xr-xml-map "mpls_lcac:CurrentAutoMesh";
      type uint32;
      description "Current Autotunnel Mesh count";
    }
    leaf current-maximum-gmpls-unitunnels {
      xr:xr-xml-map "mpls_lcac:CurrentMaximumGMPLS_UNITunnels";
      type uint32;
      description "Current Maximum GMPLS-UNI Tunnel Count";
    }
    leaf current-gmpls-uni {
      xr:xr-xml-map "mpls_lcac:CurrentGMPLS_UNI";
      type uint32;
      description "Current GMPLS-UNI tunnel count";
    }
  }

  grouping MPLS-TE-PATH-PROTECTION-LSP {
    description "MPLS TE Path Protected LSP Information";
    leaf lsp-uptime {
      xr:xr-xml-map "mpls_lcac:LSPUptime";
      type uint32;
      description "LSP Uptime";
    }
    leaf path-protection-lsp-id {
      xr:xr-xml-map "mpls_lcac:PathProtectionLSP_ID";
      type uint32;
      description "LSP ID ";
    }
    leaf lsp-local-label {
      xr:xr-xml-map "mpls_lcac:LSPLocalLabel";
      type uint32;
      description "Local label ";
    }
    leaf lsp-output-interface {
      xr:xr-xml-map "mpls_lcac:LSPOutputInterface";
      type string;
      description "Output interface of LSP";
    }
    leaf lsp-output-label {
      xr:xr-xml-map "mpls_lcac:LSPOutputLabel";
      type uint32;
      description "Output label of the LSP";
    }
    leaf lsp-state {
      xr:xr-xml-map "mpls_lcac:LSPState";
      type Mpls-te-tunnel-state;
      description "LSP State";
    }

    list lsp-hop {
      description "Path used by LSP";
      uses RSVP-MGMT-ERO-SUBOBJ;
    }
  }

  grouping MPLS-TE-PATH-PROTECTION {
    description "MPLS TE Path Protected Information";

    container path-protection {
      description "Path Protect Info";
      uses MPLS-TE-PP-INFO;
    }

    container current-lsp {
      description " Current LSP info";
      uses MPLS-TE-PATH-PROTECTION-LSP;
    }

    container standby-lsp {
      description " Standby LSP info";
      uses MPLS-TE-PATH-PROTECTION-LSP;
    }
    leaf is-tunnel-up {
      xr:xr-xml-map "mpls_lcac:IsTunnelUp";
      type boolean;
      description "Tunnel UP";
    }
    leaf source-address {
      xr:xr-xml-map "mpls_lcac:SourceAddress";
      type inet:ipv4-address;
      description "Source";
    }
    leaf destination-address {
      xr:xr-xml-map "mpls_lcac:DestinationAddress";
      type inet:ipv4-address;
      description "Destination";
    }
    leaf extended-tunnel-id {
      xr:xr-xml-map "mpls_lcac:ExtendedTunnelID";
      type inet:ipv4-address;
      description "Extended Tunnel ID";
    }
  }

  grouping MPLS-TE-AUTOTUN-P2P-INFO {
    description "P2P auto-tunnel summary per client information";
    leaf auto-p2p-tunnel {
      xr:xr-xml-map "mpls_lcac:AutoP2PTunnel";
      type uint32;
      description "Total number of client P2P auto-tunnels";
    }
    leaf up-auto-p2p-tunnels {
      xr:xr-xml-map "mpls_lcac:UpAutoP2PTunnels";
      type uint32;
      description
        "Total number of client P2P auto-tunnels that are
        up";
    }
    leaf down-auto-p2p-tunnels {
      xr:xr-xml-map "mpls_lcac:DownAutoP2PTunnels";
      type uint32;
      description
        "Total number of client P2P auto-tunnels that are
        down";
    }
  }

  grouping MPLS-TE-AUTOTUN-P2MP-INFO {
    description "P2MP auto-tunnel summary per client information";
    leaf auto-p2mp-tunnel {
      xr:xr-xml-map "mpls_lcac:AutoP2MPTunnel";
      type uint32;
      description "Total number of client P2MP auto-tunnels";
    }
    leaf auto-p2mp-destinations {
      xr:xr-xml-map "mpls_lcac:AutoP2MPDestinations";
      type uint32;
      description
        "Total number of client P2MP auto-tunnel
        destinations";
    }
    leaf up-auto-p2mp-destinations {
      xr:xr-xml-map "mpls_lcac:UpAutoP2MPDestinations";
      type uint32;
      description
        "Total number of client P2MP auto-tunnel
        destinations that are up";
    }
    leaf down-auto-p2mp-destinations {
      xr:xr-xml-map "mpls_lcac:DownAutoP2MPDestinations";
      type uint32;
      description
        "Total number of client P2MP auto-tunnel
        destinations that are down";
    }
    leaf up-auto-p2mp-tunnels {
      xr:xr-xml-map "mpls_lcac:UpAutoP2MPTunnels";
      type uint32;
      description
        "Total number of client P2MP auto-tunnels that
        are up";
    }
    leaf down-auto-p2mp-tunnels {
      xr:xr-xml-map "mpls_lcac:DownAutoP2MPTunnels";
      type uint32;
      description
        "Total number of client P2MP auto-tunnels that
        are down";
    }
    leaf frr-auto-p2mp-tunnels {
      xr:xr-xml-map "mpls_lcac:FRRAutoP2MPTunnels";
      type uint32;
      description
        "Total number of client P2MP auto-tunnels that
        are FRR enabled";
    }
  }

  grouping MPLS-TE-AUTOTUN-SVR-INFO {
    description "Auto-tunnel server client summary";

    container p2mp-info {
      description "P2MP info for a client";
      uses MPLS-TE-AUTOTUN-P2MP-INFO;
    }

    container p2p-info {
      description "P2P info for a client";
      uses MPLS-TE-AUTOTUN-P2P-INFO;
    }
    leaf protocol-type {
      xr:xr-xml-map "mpls_lcac:ProtocolType";
      type Te-serv-tun-client;
      description "Client's protocol type";
    }
    leaf client-instance-name {
      xr:xr-xml-map "mpls_lcac:ClientInstanceName";
      type string;
      description "Client Instance name";
    }
    leaf client-id {
      xr:xr-xml-map "mpls_lcac:ClientID";
      type uint32;
      description "Client ID";
    }
  }

  grouping MPLS-TE-AUTOTUN-SVR-SUMMARY-INFO {
    description "Auto-tunnel server summary information";

    container total-auto-p2mp-tunnels {
      description "Total number of P2MP auto-tunnels";
      uses MPLS-TE-AUTOTUN-P2MP-INFO;
    }

    container total-auto-p2p-tunnels {
      description "Total number of P2P auto-tunnels";
      uses MPLS-TE-AUTOTUN-P2P-INFO;
    }

    list clients-summary {
      description "List of auto-tunnel server clients";
      uses MPLS-TE-AUTOTUN-SVR-INFO;
    }
  }

  grouping TE-TABLE-DATAPOINT-INFO {
    description "Convergence table bag entry";
  }

  grouping TE-CONV-TBL-SUMMARY-BAG {
    description "TE tunnels convergence summary information bag";

    container table-path-out {
      description "Table path-out entry";
      uses TE-TABLE-DATAPOINT-INFO;
    }

    container table-resv-in {
      description "Table resv-in entry";
      uses TE-TABLE-DATAPOINT-INFO;
    }

    container table-label-rewrite {
      description "Table label rewrite entry";
      uses TE-TABLE-DATAPOINT-INFO;
    }

    container table-pcalc {
      description "Table PCALC entry";
      uses TE-TABLE-DATAPOINT-INFO;
    }

    container table-tunnel-rewrite {
      description "Table Tunnel rewrite entry";
      uses TE-TABLE-DATAPOINT-INFO;
    }

    container table-frr-trigger {
      description "Table FRR trigger entry";
      uses TE-TABLE-DATAPOINT-INFO;
    }
    leaf tunnel-frr-active-count {
      xr:xr-xml-map "mpls_lcac:TunnelFRRActiveCount";
      type uint32;
      description "FRR active Tunnel count";
    }
    leaf tunnel-frr-total-count {
      xr:xr-xml-map "mpls_lcac:TunnelFRRTotalCount";
      type uint32;
      description "FRR triggered Tunnel count";
    }
    leaf tunnel-converged-count {
      xr:xr-xml-map "mpls_lcac:TunnelConvergedCount";
      type uint32;
      description "Tunnel converged count";
    }
    leaf tunnel-total-convergence-complete-time {
      xr:xr-xml-map "mpls_lcac:TunnelTotalConvergenceCompleteTime";
      type uint64;
      units "nanosecond";
      description
        "Tunnel convergence complete timestamp (clocktime
        in nsecs)";
    }
  }

  grouping MPLS-TE-GMPLS-NNI-SUMMARY-INFO {
    description "GMPLS-NNI summary information";
    leaf heads-up {
      xr:xr-xml-map "mpls_lcac:HeadsUp";
      type uint32;
      description "Tunnel heads in up state";
    }
    leaf heads-down {
      xr:xr-xml-map "mpls_lcac:HeadsDown";
      type uint32;
      description "Tunnel heads in down state";
    }
    leaf mids-up {
      xr:xr-xml-map "mpls_lcac:MidsUp";
      type uint32;
      description "Tunnel mids in up state";
    }
    leaf mids-down {
      xr:xr-xml-map "mpls_lcac:MidsDown";
      type uint32;
      description "Tunnel mids in down state";
    }
    leaf tails-up {
      xr:xr-xml-map "mpls_lcac:TailsUp";
      type uint32;
      description "Tunnel tails in up state";
    }
    leaf tails-down {
      xr:xr-xml-map "mpls_lcac:TailsDown";
      type uint32;
      description "Tunnel tails in down state";
    }
  }

  grouping MPLS-TE-GMPLS-UNI-SUMMARY-INFO {
    description "GMPLS-UNI summary information";
    leaf heads-up {
      xr:xr-xml-map "mpls_lcac:HeadsUp";
      type uint32;
      description "Tunnel heads in up state";
    }
    leaf heads-down {
      xr:xr-xml-map "mpls_lcac:HeadsDown";
      type uint32;
      description "Tunnel heads in down state";
    }
    leaf tails-up {
      xr:xr-xml-map "mpls_lcac:TailsUp";
      type uint32;
      description "Tunnel tails in up state";
    }
    leaf tails-down {
      xr:xr-xml-map "mpls_lcac:TailsDown";
      type uint32;
      description "Tunnel tails in down state";
    }
  }

  grouping MPLS-TE-TUNNELS-SUMMARY-INFO-BAG {
    description "MPLS TE Tunnel Summary Information";

    container autobackup-summary {
      description "Autobackup summary";
      uses MPLS-TE-AUTOTUN-BACKUP-SUMMARY-INFO;
    }

    container auto-mesh-summary {
      description "Automesh summary";
      uses MPLS-TE-AUTOTUN-MESH-SUMMARY-INFO;
    }

    container auto-mesh-one-hop-summary {
      description "Automesh Onehop summary";
      uses MPLS-TE-AUTOTUN-MESH-ONEHOP-SUMMARY-INFO;
    }

    container gmpls-uni-summary {
      description "GMPLS-UNI summary";
      uses MPLS-TE-GMPLS-UNI-SUMMARY-INFO;
    }

    container gmpls-nni-summary {
      description "GMPLS-NNI summary";
      uses MPLS-TE-GMPLS-NNI-SUMMARY-INFO;
    }

    container current-tunnel-convergence-summary {
      description "Current Tunnel convergemce summary information";
      uses TE-CONV-TBL-SUMMARY-BAG;
    }

    container last-tunnel-convergence-summary {
      description "Last Tunnel convergemce summary information";
      uses TE-CONV-TBL-SUMMARY-BAG;
    }

    container auto-tun-server-summary {
      description "Auto-tunnel server tunnel summary";
      uses MPLS-TE-AUTOTUN-SVR-SUMMARY-INFO;
    }
    leaf pcalc-tiebreaker {
      xr:xr-xml-map "mpls_lcac:PCALCTiebreaker";
      type uint32;
      description "PCALC tiebreaker";
    }
    leaf tiebreaker-qualifier {
      xr:xr-xml-map "mpls_lcac:TiebreakerQualifier";
      type Mpls-te-metric-qualifier;
      description
        "Describes how the path selection tiebreaker was
        specified:default, or globally set";
    }
    leaf te-process-status {
      xr:xr-xml-map "mpls_lcac:TEProcessStatus";
      type Mpls-te-tunnels-process-status;
      description "Status of te_control";
    }
    leaf is-rsvp-process-enabled {
      xr:xr-xml-map "mpls_lcac:IsRSVPProcessEnabled";
      type boolean;
      description "Status of rsvp";
    }
    leaf is-forwarding-enabled {
      xr:xr-xml-map "mpls_lcac:IsForwardingEnabled";
      type boolean;
      description "TRUE if forwarding is enabled";
    }
    leaf activated-heads {
      xr:xr-xml-map "mpls_lcac:ActivatedHeads";
      type uint32;
      description "Total tunnel heads activated";
    }
    leaf deactivated-heads {
      xr:xr-xml-map "mpls_lcac:DeactivatedHeads";
      type uint32;
      description "Total tunnel heads deactivated";
    }
    leaf recovered-heads {
      xr:xr-xml-map "mpls_lcac:RecoveredHeads";
      type uint32;
      description "Number of heads recovered";
    }
    leaf is-periodic-reoptimization-on {
      xr:xr-xml-map "mpls_lcac:IsPeriodicReoptimizationOn";
      type boolean;
      description "TRUE if periodic reoptimization is on";
    }
    leaf reoptimization-period {
      xr:xr-xml-map "mpls_lcac:ReoptimizationPeriod";
      type uint32;
      units "second";
      description "Reoptimization period in seconds";
    }
    leaf next-reoptimization-timer {
      xr:xr-xml-map "mpls_lcac:NextReoptimizationTimer";
      type uint32;
      units "second";
      description "Time left till next reoptimization (seconds)";
    }
    leaf auto-bandwidth-tunnels {
      xr:xr-xml-map "mpls_lcac:AutoBandwidthTunnels";
      type uint32;
      description "Counter with number of auto-bw enabled tunnels";
    }
    leaf auto-bandwidth-collection-period {
      xr:xr-xml-map "mpls_lcac:AutoBandwidthCollectionPeriod";
      type uint32;
      units "minute";
      description "Collection period in minutes";
    }
    leaf is-promotion-on {
      xr:xr-xml-map "mpls_lcac:IsPromotionOn";
      type boolean;
      description "TRUE if periodic frr promotion is on";
    }
    leaf promotion-period {
      xr:xr-xml-map "mpls_lcac:PromotionPeriod";
      type uint32;
      units "second";
      description "FRR promotion period in seconds";
    }
    leaf next-promotion-timer {
      xr:xr-xml-map "mpls_lcac:NextPromotionTimer";
      type uint32;
      units "second";
      description "Time left till next FRR promotion (seconds)";
    }
    leaf tunnel-check-period {
      xr:xr-xml-map "mpls_lcac:TunnelCheckPeriod";
      type uint32;
      units "second";
      description "Tunnel head check period (seconds)";
    }
    leaf next-check-time {
      xr:xr-xml-map "mpls_lcac:NextCheckTime";
      type uint32;
      units "second";
      description "Time left till next FRR promotion (seconds)";
    }
    leaf tunnel-verify-period {
      xr:xr-xml-map "mpls_lcac:TunnelVerifyPeriod";
      type uint32;
      units "second";
      description "Tunnel head verify period (seconds)";
    }
    leaf next-verify-timer {
      xr:xr-xml-map "mpls_lcac:NextVerifyTimer";
      type uint32;
      units "second";
      description "Time left till next FRR promotion (seconds)";
    }
    leaf frr-head-tunnels {
      xr:xr-xml-map "mpls_lcac:FRRHeadTunnels";
      type uint32;
      description "FRR tunnels in Up state at head end";
    }
    leaf protected-head-tunnels {
      xr:xr-xml-map "mpls_lcac:ProtectedHeadTunnels";
      type uint32;
      description "FRR protected tunnels in Up state at head end";
    }
    leaf rerouted-head-tunnels {
      xr:xr-xml-map "mpls_lcac:ReroutedHeadTunnels";
      type uint32;
      description "FRR rerouted tunnels in Up state at head end";
    }
    leaf frr-mid-point-tunnels {
      xr:xr-xml-map "mpls_lcac:FRRMidPointTunnels";
      type uint32;
      description "FRR tunnels at mid point";
    }
    leaf protected-mid-point-tunnels {
      xr:xr-xml-map "mpls_lcac:ProtectedMidPointTunnels";
      type uint32;
      description "FRR protected tunnels at mid point";
    }
    leaf rerouted-mid-point-tunnels {
      xr:xr-xml-map "mpls_lcac:ReroutedMidPointTunnels";
      type uint32;
      description "FRR rerouted tunnels at mid point";
    }
    leaf link-protected-tunnels {
      xr:xr-xml-map "mpls_lcac:LinkProtectedTunnels";
      type uint32;
      description "FRR link protected tunnels";
    }
    leaf node-protected-tunnels {
      xr:xr-xml-map "mpls_lcac:NodeProtectedTunnels";
      type uint32;
      description "FRR node protected tunnels";
    }
    leaf bw-protected-tunnels {
      xr:xr-xml-map "mpls_lcac:BWProtectedTunnels";
      type uint32;
      description "FRR BW protected tunnels";
    }
    leaf frr-p2p-head-tunnels {
      xr:xr-xml-map "mpls_lcac:FRR_P2PHeadTunnels";
      type uint32;
      description "P2P FRR tunnels in Up state at head end";
    }
    leaf protected-p2p-head-tunnels {
      xr:xr-xml-map "mpls_lcac:ProtectedP2PHeadTunnels";
      type uint32;
      description
        "P2P FRR protected tunnels in Up state at head
        end";
    }
    leaf rerouted-p2p-head-tunnels {
      xr:xr-xml-map "mpls_lcac:ReroutedP2PHeadTunnels";
      type uint32;
      description
        "P2P FRR rerouted tunnels in Up state at head end";
    }
    leaf frr-p2p-mid-point-tunnels {
      xr:xr-xml-map "mpls_lcac:FRR_P2PMidPointTunnels";
      type uint32;
      description "P2P FRR tunnels at mid point";
    }
    leaf protected-p2p-mid-point-tunnels {
      xr:xr-xml-map "mpls_lcac:ProtectedP2PMidPointTunnels";
      type uint32;
      description "P2P FRR protected tunnels at mid point";
    }
    leaf rerouted-p2p-mid-point-tunnels {
      xr:xr-xml-map "mpls_lcac:ReroutedP2PMidPointTunnels";
      type uint32;
      description "P2P FRR rerouted tunnels at mid point";
    }
    leaf link-protected-p2p-tunnels {
      xr:xr-xml-map "mpls_lcac:LinkProtectedP2PTunnels";
      type uint32;
      description "P2P FRR link protected tunnels";
    }
    leaf node-protected-p2p-tunnels {
      xr:xr-xml-map "mpls_lcac:NodeProtectedP2PTunnels";
      type uint32;
      description "P2P FRR node protected tunnels";
    }
    leaf bw-protected-p2p-tunnels {
      xr:xr-xml-map "mpls_lcac:BWProtectedP2PTunnels";
      type uint32;
      description "P2P FRR BW protected tunnels";
    }
    leaf backup-tunnels {
      xr:xr-xml-map "mpls_lcac:BackupTunnels";
      type uint32;
      description "FRR backup tunnels in Up state";
    }
    leaf backups-assigned {
      xr:xr-xml-map "mpls_lcac:BackupsAssigned";
      type uint32;
      description "FRR backup tunnels assigned";
    }
    leaf frr-protected-interfaces {
      xr:xr-xml-map "mpls_lcac:FRRProtectedInterfaces";
      type uint32;
      description "FRR Protected Interfaces";
    }
    leaf rerouted-interfaces {
      xr:xr-xml-map "mpls_lcac:ReroutedInterfaces";
      type uint32;
      description "FRR Rerouted Interfaces";
    }
    leaf p2p-head-tunnels {
      xr:xr-xml-map "mpls_lcac:P2PHeadTunnels";
      type uint32;
      description "p2p Tunnel interfaces";
    }
    leaf up-p2p-head-tunnels {
      xr:xr-xml-map "mpls_lcac:UpP2PHeadTunnels";
      type uint32;
      description "p2p Tunnel interfaces in Up state";
    }
    leaf dynamic-up-p2p-head-tunnels {
      xr:xr-xml-map "mpls_lcac:DynamicUpP2PHeadTunnels";
      type uint32;
      description "p2p Tunnel up via a dynamic path";
    }
    leaf frr-config-p2p-head-tunnels {
      xr:xr-xml-map "mpls_lcac:FRRConfigP2PHeadTunnels";
      type uint32;
      description "p2p Tunnel interfaces with FRR configuration";
    }
    leaf p2p-head-destinations {
      xr:xr-xml-map "mpls_lcac:P2PHeadDestinations";
      type uint32;
      description "p2p Destinations at Head";
    }
    leaf p2p-head-destinations-up {
      xr:xr-xml-map "mpls_lcac:P2PHeadDestinationsUp";
      type uint32;
      description "p2p Destinations in Up state at Head";
    }
    leaf bw-protected-p2p-s2-ls {
      xr:xr-xml-map "mpls_lcac:BWProtectedP2P_S2Ls";
      type uint32;
      description "p2p S2Ls BW Protected";
    }
    leaf link-protected-p2p-s2-ls {
      xr:xr-xml-map "mpls_lcac:LinkProtectedP2P_S2Ls";
      type uint32;
      description "p2p S2Ls Link Protected";
    }
    leaf up-p2p-head-s2-ls {
      xr:xr-xml-map "mpls_lcac:UpP2PHeadS2Ls";
      type uint32;
      description "p2p S2Ls in Up state at Head";
    }
    leaf proceeding-p2p-head-s2-ls {
      xr:xr-xml-map "mpls_lcac:ProceedingP2PHeadS2Ls";
      type uint32;
      description "p2p S2Ls in signalling-proceeding state at Head";
    }
    leaf recovering-p2p-head-s2-ls {
      xr:xr-xml-map "mpls_lcac:RecoveringP2PHeadS2Ls";
      type uint32;
      description "p2p S2Ls recovering at Head";
    }
    leaf frr-p2p-head-s2-ls {
      xr:xr-xml-map "mpls_lcac:FRR_P2PHeadS2Ls";
      type uint32;
      description "p2p S2Ls with FRR requested at Head";
    }
    leaf protected-p2p-head-s2-ls {
      xr:xr-xml-map "mpls_lcac:ProtectedP2PHeadS2Ls";
      type uint32;
      description "p2p S2Ls FRR Protected at Head";
    }
    leaf rerouted-p2p-head-s2-ls {
      xr:xr-xml-map "mpls_lcac:ReroutedP2PHeadS2Ls";
      type uint32;
      description "p2p S2Ls FRR Rerouted at Head";
    }
    leaf p2p-mid-point-s2-ls {
      xr:xr-xml-map "mpls_lcac:P2PMidPointS2Ls";
      type uint32;
      description "p2p S2Ls at Mid";
    }
    leaf up-p2p-mid-point-s2-ls {
      xr:xr-xml-map "mpls_lcac:UpP2PMidPointS2Ls";
      type uint32;
      description "p2p S2Ls in Up state at Mid";
    }
    leaf proceeding-p2p-mid-point-s2-ls {
      xr:xr-xml-map "mpls_lcac:ProceedingP2PMidPointS2Ls";
      type uint32;
      description "p2p S2Ls in signalling=proceeding state at Mid";
    }
    leaf frr-p2p-mid-point-s2-ls {
      xr:xr-xml-map "mpls_lcac:FRR_P2PMidPointS2Ls";
      type uint32;
      description "p2p S2Ls with FRR requested at Mid";
    }
    leaf protected-p2p-mid-point-s2-ls {
      xr:xr-xml-map "mpls_lcac:ProtectedP2PMidPointS2Ls";
      type uint32;
      description "p2p S2Ls FRR Protected at Mid";
    }
    leaf rerouted-p2p-mid-point-s2-ls {
      xr:xr-xml-map "mpls_lcac:ReroutedP2PMidPointS2Ls";
      type uint32;
      description "p2p S2Ls FRR Rerouted at Mid";
    }
    leaf p2p-tail-s2-ls {
      xr:xr-xml-map "mpls_lcac:P2PTailS2Ls";
      type uint32;
      description "p2p S2Ls at Tail";
    }
    leaf up-p2p-tail-s2-ls {
      xr:xr-xml-map "mpls_lcac:UpP2PTailS2Ls";
      type uint32;
      description "p2p S2Ls in Up state at Tail";
    }
    leaf p2p-tail-tunnels {
      xr:xr-xml-map "mpls_lcac:P2PTailTunnels";
      type uint32;
      description "p2p Tunnel tail interfaces";
    }
    leaf path-protect-configured-tunnels {
      xr:xr-xml-map "mpls_lcac:PathProtectConfiguredTunnels";
      type uint16;
      description "Tunnels configured with Path Protect";
    }
    leaf path-protect-configured-tunnels-up {
      xr:xr-xml-map "mpls_lcac:PathProtectConfiguredTunnelsUp";
      type uint16;
      description "Path Protect configured tunnels connected/up";
    }
    leaf path-protect-configured-tunnels-standby-up {
      xr:xr-xml-map "mpls_lcac:PathProtectConfiguredTunnelsStandbyU"+
        "p";
      type uint16;
      description "Tunnels with standby LSP up";
    }
    leaf link-diverse-paths {
      xr:xr-xml-map "mpls_lcac:LinkDiversePaths";
      type uint16;
      description "Link diverse paths";
    }
    leaf node-diverse-paths {
      xr:xr-xml-map "mpls_lcac:NodeDiversePaths";
      type uint16;
      description "Node diverse paths";
    }
    leaf link-and-node-diverse-paths {
      xr:xr-xml-map "mpls_lcac:LinkAndNodeDiversePaths";
      type uint16;
      description "Link and Node diverse paths";
    }
    leaf user-defined-paths {
      xr:xr-xml-map "mpls_lcac:UserDefinedPaths";
      type uint16;
      description "User defined paths";
    }
    leaf p2mp-head-tunnels {
      xr:xr-xml-map "mpls_lcac:P2MPHeadTunnels";
      type uint32;
      description "P2MP Tunnel interfaces";
    }
    leaf up-p2mp-head-tunnels {
      xr:xr-xml-map "mpls_lcac:UpP2MPHeadTunnels";
      type uint32;
      description "P2MP Tunnel interfaces in Up state";
    }
    leaf frr-config-p2mp-head-tunnels {
      xr:xr-xml-map "mpls_lcac:FRRConfigP2MPHeadTunnels";
      type uint32;
      description "P2MP Tunnel interfaces with FRR configuration";
    }
    leaf p2mp-head-destinations {
      xr:xr-xml-map "mpls_lcac:P2MPHeadDestinations";
      type uint32;
      description "P2MP Destinations at Head";
    }
    leaf up-p2mp-head-destinations {
      xr:xr-xml-map "mpls_lcac:UpP2MPHeadDestinations";
      type uint32;
      description "P2MP Destinations in Up state at Head";
    }
    leaf bw-protected-p2mp-s2-ls {
      xr:xr-xml-map "mpls_lcac:BWProtectedP2MP_S2Ls";
      type uint32;
      description "P2MP S2Ls BW Protected";
    }
    leaf link-protected-p2mp-s2-ls {
      xr:xr-xml-map "mpls_lcac:LinkProtectedP2MP_S2Ls";
      type uint32;
      description "P2MP S2Ls Link Protected";
    }
    leaf up-p2mp-head-s2-ls {
      xr:xr-xml-map "mpls_lcac:UpP2MPHeadS2Ls";
      type uint32;
      description "P2MP S2Ls in Up state at Head";
    }
    leaf proceeding-p2mp-head-s2-ls {
      xr:xr-xml-map "mpls_lcac:ProceedingP2MPHeadS2Ls";
      type uint32;
      description
        "P2MP S2Ls in signalling-proceeding state at Head";
    }
    leaf frr-p2mp-head-s2-ls {
      xr:xr-xml-map "mpls_lcac:FRR_P2MPHeadS2Ls";
      type uint32;
      description "P2MP S2Ls with FRR requested at Head";
    }
    leaf protected-p2mp-head-s2-ls {
      xr:xr-xml-map "mpls_lcac:ProtectedP2MPHeadS2Ls";
      type uint32;
      description "P2MP S2Ls FRR Protected at Head";
    }
    leaf rerouted-p2mp-head-s2-ls {
      xr:xr-xml-map "mpls_lcac:ReroutedP2MPHeadS2Ls";
      type uint32;
      description "P2MP S2Ls FRR Rerouted at Head";
    }
    leaf p2mp-mid-point-s2-ls {
      xr:xr-xml-map "mpls_lcac:P2MPMidPointS2Ls";
      type uint32;
      description "P2MP S2Ls at Mid";
    }
    leaf up-p2mp-mid-point-s2-ls {
      xr:xr-xml-map "mpls_lcac:UpP2MPMidPointS2Ls";
      type uint32;
      description "P2MP S2Ls in Up state at Mid";
    }
    leaf proceeding-p2mp-mid-point-s2-ls {
      xr:xr-xml-map "mpls_lcac:ProceedingP2MPMidPointS2Ls";
      type uint32;
      description "P2MP S2Ls in signalling=proceeding state at Mid";
    }
    leaf frr-p2mp-mid-point-s2-ls {
      xr:xr-xml-map "mpls_lcac:FRR_P2MPMidPointS2Ls";
      type uint32;
      description "P2MP S2Ls with FRR requested at Mid";
    }
    leaf protected-p2mp-mid-point-s2-ls {
      xr:xr-xml-map "mpls_lcac:ProtectedP2MPMidPointS2Ls";
      type uint32;
      description "P2MP S2Ls FRR Protected at Mid";
    }
    leaf rerouted-p2mp-mid-point-s2-ls {
      xr:xr-xml-map "mpls_lcac:ReroutedP2MPMidPointS2Ls";
      type uint32;
      description "P2MP S2Ls FRR Rerouted at Mid";
    }
    leaf p2mp-tail-s2-ls {
      xr:xr-xml-map "mpls_lcac:P2MPTailS2Ls";
      type uint32;
      description "P2MP S2Ls at Tail";
    }
    leaf up-p2mp-tail-s2-ls {
      xr:xr-xml-map "mpls_lcac:UpP2MPTailS2Ls";
      type uint32;
      description "P2MP S2Ls in Up state at Tail";
    }
    leaf bidir-head-tunnels {
      xr:xr-xml-map "mpls_lcac:BidirHeadTunnels";
      type uint32;
      description "Bidirectional Head Tunnel interfaces";
    }
    leaf bidir-head-tunnels-up {
      xr:xr-xml-map "mpls_lcac:BidirHeadTunnelsUp";
      type uint32;
      description "Connected Bidirectional Head Tunnel interfaces";
    }
    leaf bidir-head-tunnels-associated {
      xr:xr-xml-map "mpls_lcac:BidirHeadTunnelsAssociated";
      type uint32;
      description "Associated Bidirectional Head Tunnels";
    }
    leaf bidir-head-tunnels-corouted {
      xr:xr-xml-map "mpls_lcac:BidirHeadTunnelsCorouted";
      type uint32;
      description "Corouted Bidirectional Head Tunnels";
    }
    leaf bidir-head-ls-ps-up {
      xr:xr-xml-map "mpls_lcac:BidirHeadLSPsUp";
      type uint32;
      description "Connected Bidirectional Head Tunnel interfaces";
    }
    leaf bidir-head-ls-ps-proceeding {
      xr:xr-xml-map "mpls_lcac:BidirHeadLSPsProceeding";
      type uint32;
      description "Proceeding Bidirectional Head LSPs";
    }
    leaf bidir-head-ls-ps-associated {
      xr:xr-xml-map "mpls_lcac:BidirHeadLSPsAssociated";
      type uint32;
      description "Associated Bidirectional Head LSPs";
    }
    leaf bidir-head-ls-ps-standby {
      xr:xr-xml-map "mpls_lcac:BidirHeadLSPsStandby";
      type uint32;
      description "Standby Bidirectional Head LSPs";
    }
    leaf bidir-mid-tunnels {
      xr:xr-xml-map "mpls_lcac:BidirMidTunnels";
      type uint32;
      description "Bidirectional Mid Tunnel interfaces";
    }
    leaf bidir-mid-tunnels-up {
      xr:xr-xml-map "mpls_lcac:BidirMidTunnelsUp";
      type uint32;
      description "Connected Bidirectional Mid Tunnel interfaces";
    }
    leaf bidir-mid-ls-ps-proceeding {
      xr:xr-xml-map "mpls_lcac:BidirMidLSPsProceeding";
      type uint32;
      description "Proceeding Bidirectional Mid LSPs";
    }
    leaf bidir-mid-ls-ps-associated {
      xr:xr-xml-map "mpls_lcac:BidirMidLSPsAssociated";
      type uint32;
      description "Associated Bidirectional Mid LSPs";
    }
    leaf bidir-mid-ls-ps-standby {
      xr:xr-xml-map "mpls_lcac:BidirMidLSPsStandby";
      type uint32;
      description "Standby Bidirectional Mid LSPs";
    }
    leaf bidir-tail-ls-ps {
      xr:xr-xml-map "mpls_lcac:BidirTailLSPs";
      type uint32;
      description "Bidirectional Tail LSPs";
    }
    leaf bidir-tail-ls-ps-up {
      xr:xr-xml-map "mpls_lcac:BidirTailLSPsUp";
      type uint32;
      description "Connected Bidirectional Tail LSPs";
    }
    leaf bidir-tail-ls-ps-proceeding {
      xr:xr-xml-map "mpls_lcac:BidirTailLSPsProceeding";
      type uint32;
      description "Proceeding Bidirectional Tail LSPs";
    }
    leaf bidir-tail-ls-ps-associated {
      xr:xr-xml-map "mpls_lcac:BidirTailLSPsAssociated";
      type uint32;
      description "Associated Bidirectional Tail LSPs";
    }
    leaf bidir-tail-ls-ps-standby {
      xr:xr-xml-map "mpls_lcac:BidirTailLSPsStandby";
      type uint32;
      description "Standby Bidirectional Tail LSPs";
    }
    leaf bidir-tail-ls-ps-corouted {
      xr:xr-xml-map "mpls_lcac:BidirTailLSPsCorouted";
      type uint32;
      description "Corouted Bidirectional Tail LSPs";
    }
  }

  grouping MPLS-TE-TUNNELS-AUTOBW-BRIEF {
    description "MPLS TE Tunnel AutoBandwidth Brief Information";

    container auto-bandwidth-status {
      description "Tunnels's AutoBandwidth Status information";
      uses MPLS-TE-TUNNELS-AUTOBW-STATUS;
    }
    leaf tunnel-name-xr {
      xr:xr-xml-map "mpls_lcac:tunnel-name-xr";
      type string;
      description "Tunnel name";
    }
    leaf signaled-name {
      xr:xr-xml-map "mpls_lcac:SignaledName";
      type string;
      description "Tunnel signaled name";
    }
    leaf tunnel-lsp-id {
      xr:xr-xml-map "mpls_lcac:TunnelLSP_ID";
      type uint32;
      description "Tunnel Lsp Id";
    }
    leaf bandwidth-applications {
      xr:xr-xml-map "mpls_lcac:BandwidthApplications";
      type uint32;
      description
        "Total number of bandwidth applications requested
        by auto-bw";
    }
    leaf last-bandwidth-applied {
      xr:xr-xml-map "mpls_lcac:LastBandwidthApplied";
      type uint32;
      description
        "Last bandwidth requested by auto-bw for the
        tunnel";
    }
    leaf tunnel-requested-bandwidth {
      xr:xr-xml-map "mpls_lcac:TunnelRequestedBandwidth";
      type uint32;
      description "Requested Bandwidth for the tunnel";
    }
    leaf signalled-bandwith {
      xr:xr-xml-map "mpls_lcac:SignalledBandwith";
      type uint32;
      description "Signalled bandwidth for the tunnel";
    }
    leaf highest-bandwidth {
      xr:xr-xml-map "mpls_lcac:HighestBandwidth";
      type uint32;
      description
        "Highest bandwidth registered within current
        application period";
    }
    leaf last-sample-bandwidth {
      xr:xr-xml-map "mpls_lcac:LastSampleBandwidth";
      type uint32;
      description "Last sample bandwidth collected";
    }
    leaf samples-collected {
      xr:xr-xml-map "mpls_lcac:SamplesCollected";
      type uint32;
      description
        "Number of samples collected within current
        application period";
    }
    leaf time-left-application {
      xr:xr-xml-map "mpls_lcac:TimeLeftApplication";
      type uint32;
      description
        "Time left until next auto-bw application
        algorithm is performed";
    }
  }

  grouping MPLS-TE-FLEX-LSP-REV-LSP {
    description "MPLS TE Flex LSP Reverse LSP information";

    container reverse-lsp-fec {
      description "Reverse Associated Bidir LSP FEC";
      uses TE-LSP-FEC;
    }

    container association {
      description "Association Object";
      uses MPLS-TE-S2L-ASSOCIATION-OBJECT;
    }

    container protection {
      description "Protection Object";
      uses MPLS-TE-S2L-PROTECTION-OBJECT;
    }
    leaf reverse-lsp-present {
      xr:xr-xml-map "mpls_lcac:ReverseLSPPresent";
      type boolean;
      description "Reverse Associated Bidir LSP Present";
    }
    leaf reverse-lsp-connected {
      xr:xr-xml-map "mpls_lcac:ReverseLSPConnected";
      type boolean;
      description "Reverse Associated Bidir LSP Connected";
    }
  }

  grouping MPLS-TE-FLEX-LSP-LSP {
    description "MPLS TE FLEX LSP Information";

    container flex-info {
      description "Flex Info";
      uses MPLS-TE-S2L-FLEX-INFO;
    }

    container association {
      description "Association Object";
      uses MPLS-TE-S2L-ASSOCIATION-OBJECT;
    }

    container protection {
      description "Protection Object";
      uses MPLS-TE-S2L-PROTECTION-OBJECT;
    }

    container reverse-lsp {
      description "Reverse LSP information";
      uses MPLS-TE-FLEX-LSP-REV-LSP;
    }
    leaf is-operational {
      xr:xr-xml-map "mpls_lcac:IsOperational";
      type boolean;
      description "Operational";
    }
    leaf lsp-uptime {
      xr:xr-xml-map "mpls_lcac:LSPUptime";
      type uint32;
      description "LSP Uptime";
    }
    leaf path-protection-lsp-id {
      xr:xr-xml-map "mpls_lcac:PathProtectionLSP_ID";
      type uint32;
      description "LSP ID ";
    }
    leaf lsp-mode {
      xr:xr-xml-map "mpls_lcac:LspMode";
      type Mpls-te-lsp-mode;
      description "LSP mode";
    }
    leaf lsp-local-label {
      xr:xr-xml-map "mpls_lcac:LSPLocalLabel";
      type uint32;
      description "Local label ";
    }
    leaf lsp-output-interface {
      xr:xr-xml-map "mpls_lcac:LSPOutputInterface";
      type string;
      description "Output interface of LSP";
    }
    leaf lsp-output-label {
      xr:xr-xml-map "mpls_lcac:LSPOutputLabel";
      type uint32;
      description "Output label of the LSP";
    }
    leaf lsp-state {
      xr:xr-xml-map "mpls_lcac:LSPState";
      type Mpls-te-tunnel-state;
      description "LSP State";
    }

    list lsp-hop {
      description "Path used by LSP";
      uses RSVP-MGMT-ERO-SUBOBJ;
    }
  }

  grouping MPLS-TE-FLEX-LSP {
    description "MPLS TE Flex LSP Information";

    container working-lsp {
      description " Working LSP info";
      uses MPLS-TE-FLEX-LSP-LSP;
    }

    container protect-lsp {
      description " Protect LSP info";
      uses MPLS-TE-FLEX-LSP-LSP;
    }
    leaf is-tunnel-up {
      xr:xr-xml-map "mpls_lcac:IsTunnelUp";
      type boolean;
      description "Tunnel UP";
    }
    leaf tun-id {
      xr:xr-xml-map "mpls_lcac:tun_id";
      type uint16;
      description "Tunnel ID";
    }
    leaf source-address {
      xr:xr-xml-map "mpls_lcac:SourceAddress";
      type inet:ipv4-address;
      description "Source";
    }
    leaf destination-address {
      xr:xr-xml-map "mpls_lcac:DestinationAddress";
      type inet:ipv4-address;
      description "Destination";
    }
    leaf extended-tunnel-id {
      xr:xr-xml-map "mpls_lcac:ExtendedTunnelID";
      type inet:ipv4-address;
      description "Extended Tunnel ID";
    }
  }

  grouping MPLS-TE-FASTREROUTE-PROMOTION-BAG {
    description "MPLS TE Fast Reroute Promotion Information";
    leaf promotion-period {
      xr:xr-xml-map "mpls_lcac:PromotionPeriod";
      type uint32;
      units "second";
      description "Promotion period in seconds";
    }
    leaf remaining-time {
      xr:xr-xml-map "mpls_lcac:RemainingTime";
      type uint32;
      units "second";
      description "Remaining time for next promotion in seconds";
    }
    leaf is-configured {
      xr:xr-xml-map "mpls_lcac:IsConfigured";
      type boolean;
      description "Indicate if periodic promotion is configured ";
    }
  }

  grouping MPLS-TE-FASTREROUTE-PROTECTION-BAG {
    description "MPLS TE Fast Reroute Protected LSP Information";
    leaf source-address-xr {
      xr:xr-xml-map "mpls_lcac:source-address-xr";
      type inet:ipv4-address;
      description "Source";
    }
    leaf destination-address-xr {
      xr:xr-xml-map "mpls_lcac:destination-address-xr";
      type inet:ipv4-address;
      description "Destination";
    }
    leaf tunnel-id-xr {
      xr:xr-xml-map "mpls_lcac:tunnel-id-xr";
      type uint32;
      description "Tunnel ID";
    }
    leaf extended-tunnel-id-xr {
      xr:xr-xml-map "mpls_lcac:extended-tunnel-id-xr";
      type inet:ipv4-address;
      description "Extended Tunnel ID";
    }
    leaf tunnel-name {
      xr:xr-xml-map "mpls_lcac:TunnelName";
      type string;
      description "Tunnel Name";
    }
    leaf tunnel-instance {
      xr:xr-xml-map "mpls_lcac:TunnelInstance";
      type uint32;
      description "Tunnel instance";
    }
    leaf role {
      xr:xr-xml-map "mpls_lcac:Role";
      type Mpls-te-tunnel-role;
      description "Role of LSP";
    }
    leaf admin-status {
      xr:xr-xml-map "mpls_lcac:AdminStatus";
      type Mpls-te-tunnel-state;
      description "Tunnel Admin status";
    }
    leaf operation-status {
      xr:xr-xml-map "mpls_lcac:OperationStatus";
      type Mpls-te-tunnel-state;
      description "Tunnel operational status";
    }
    leaf is-signalled {
      xr:xr-xml-map "mpls_lcac:IsSignalled";
      type boolean;
      description "Indicates whether signalled";
    }
    leaf is-frr-requested {
      xr:xr-xml-map "mpls_lcac:IsFRRRequested";
      type boolean;
      description "TRUE if frr protection is on";
    }
    leaf outbound-frr-state {
      xr:xr-xml-map "mpls_lcac:OutboundFRRState";
      type Mpls-te-frr-state;
      description "Indicates outbound FRR state";
    }
    leaf inbound-frr-state {
      xr:xr-xml-map "mpls_lcac:InboundFRRState";
      type Mpls-te-frr-state;
      description "Indicates inbound FRR state";
    }
    leaf output-interface-lsp {
      xr:xr-xml-map "mpls_lcac:OutputInterfaceLSP";
      type string;
      description "Output intface of the LSP";
    }
    leaf output-label {
      xr:xr-xml-map "mpls_lcac:OutputLabel";
      type uint32;
      description "Output label";
    }
    leaf next-hop-address {
      xr:xr-xml-map "mpls_lcac:NextHopAddress";
      type inet:ipv4-address;
      description "Next hop";
    }
    leaf frr-output-tunnel-interface {
      xr:xr-xml-map "mpls_lcac:FRROutputTunnelInterface";
      type string;
      description "FRR output tunnel intface";
    }
    leaf frr-output-label {
      xr:xr-xml-map "mpls_lcac:FRROutputLabel";
      type uint32;
      description "FRR output label";
    }
    leaf backup-status {
      xr:xr-xml-map "mpls_lcac:BackupStatus";
      type Mpls-te-backup-status;
      description "Backup status";
    }
    leaf bandwidth-pool-type {
      xr:xr-xml-map "mpls_lcac:BandwidthPoolType";
      type Mpls-te-bw-pool;
      description "Bandwidth pool type";
    }
    leaf bandwidth-limit-type {
      xr:xr-xml-map "mpls_lcac:BandwidthLimitType";
      type Mpls-te-bw-limit;
      description "Bandwidth limit type";
    }
    leaf original-input-interface {
      xr:xr-xml-map "mpls_lcac:OriginalInputInterface";
      type string;
      description "Input intface of the LSP";
    }
    leaf input-label {
      xr:xr-xml-map "mpls_lcac:InputLabel";
      type uint32;
      description "Input label";
    }
    leaf previous-hop-address {
      xr:xr-xml-map "mpls_lcac:PreviousHopAddress";
      type inet:ipv4-address;
      description "Previous hop";
    }
    leaf backup-bandwidth {
      xr:xr-xml-map "mpls_lcac:BackupBandwidth";
      type uint32;
      description "Backup bandwidth";
    }
    leaf frr-output-interface {
      xr:xr-xml-map "mpls_lcac:FRROutputInterface";
      type string;
      description "Output interface of bkup tunnel";
    }
    leaf backup-next-hop-address {
      xr:xr-xml-map "mpls_lcac:BackupNextHopAddress";
      type inet:ipv4-address;
      description "S2L Nexthop of the backup tunnel";
    }
    leaf lsp-bandwidth-type {
      xr:xr-xml-map "mpls_lcac:LSPBandwidthType";
      type Mpls-te-bw-pool;
      description "LSP bandwidth type";
    }
    leaf sharing-type {
      xr:xr-xml-map "mpls_lcac:SharingType";
      type Mpls-te-frr-sharing;
      description "Outgoing i/f Sharing type";
    }
    leaf is-p2mp-tunnel {
      xr:xr-xml-map "mpls_lcac:IsP2MPTunnel";
      type boolean;
      description "Is P2P or P2MP Tunnel";
    }
    leaf sub-group-original-id {
      xr:xr-xml-map "mpls_lcac:SubGroupOriginalID";
      type inet:ipv4-address;
      description "S2L Sub-Group Originator ID";
    }
    leaf sub-group-id-xr {
      xr:xr-xml-map "mpls_lcac:sub-group-id-xr";
      type uint16;
      description "S2L Sub-Group ID";
    }
    leaf p2mp-id-xr {
      xr:xr-xml-map "mpls_lcac:p2mp-id-xr";
      type uint32;
      description "S2L P2MP ID";
    }
  }

  grouping MPLS-TE-FASTREROUTE-BAG {
    description "MPLS TE Fast Reroute Information";
    leaf backup-tunnel-id {
      xr:xr-xml-map "mpls_lcac:BackupTunnelID";
      type uint32;
      description "Backup tunnel ID";
    }
    leaf backup-status {
      xr:xr-xml-map "mpls_lcac:BackupStatus";
      type Mpls-te-backup-status;
      description "Backup state";
    }
    leaf backup-type {
      xr:xr-xml-map "mpls_lcac:BackupType";
      type Mpls-te-backup;
      description "Backup type";
    }
    leaf backup-usage {
      xr:xr-xml-map "mpls_lcac:BackupUsage";
      type Mpls-te-backup-usage;
      description "Backup usage";
    }
    leaf prot-interface-autobackup-config {
      xr:xr-xml-map "mpls_lcac:ProtInterfaceAutobackupConfig";
      type Auto-backup-protection;
      description "Protected interface Autobackup config";
    }
    leaf prot-interface-srlg-config {
      xr:xr-xml-map "mpls_lcac:ProtInterfaceSRLGConfig";
      type Auto-backup-srlg-mode;
      description "Protected interface SRLG config";
    }
    leaf tunnel-attribute-set-name {
      xr:xr-xml-map "mpls_lcac:TunnelAttributeSetName";
      type string;
      description "Attribute Set Name";
    }
    leaf has-attribute-set {
      xr:xr-xml-map "mpls_lcac:HasAttributeSet";
      type boolean;
      description
        "TRUE if the auto-backup has an attribute set
        defined";
    }
    leaf is-attribute-set-in-db {
      xr:xr-xml-map "mpls_lcac:IsAttributeSetInDB";
      type boolean;
      description
        "Flag to indicate the existence of attribute set
        found in database";
    }
    leaf recreate-timer-is-running {
      xr:xr-xml-map "mpls_lcac:RecreateTimerIsRunning";
      type boolean;
      description "Indicates if the recreate timer is running";
    }
    leaf recreate-remaining-time {
      xr:xr-xml-map "mpls_lcac:RecreateRemainingTime";
      type uint32;
      units "second";
      description "Time Remaining in Recreate Timer (seconds)";
    }
    leaf source-address {
      xr:xr-xml-map "mpls_lcac:SourceAddress";
      type inet:ipv4-address;
      description "Backup's source";
    }
    leaf destination-address {
      xr:xr-xml-map "mpls_lcac:DestinationAddress";
      type inet:ipv4-address;
      description "Backup's destination";
    }
    leaf general-status {
      xr:xr-xml-map "mpls_lcac:GeneralStatus";
      type Mpls-te-tunnel-state;
      description "Backup's general status";
    }
    leaf connection-status {
      xr:xr-xml-map "mpls_lcac:ConnectionStatus";
      type Mpls-te-tunnel-state;
      description "Backup's connection's status";
    }
    leaf output-interface-name {
      xr:xr-xml-map "mpls_lcac:OutputInterfaceName";
      type string;
      description "The output intf of the tunnel";
    }
    leaf bandwidth-pool-type {
      xr:xr-xml-map "mpls_lcac:BandwidthPoolType";
      type Mpls-te-bw-pool;
      description "Bandwidth pool type";
    }
    leaf bandwidth-limit-type {
      xr:xr-xml-map "mpls_lcac:BandwidthLimitType";
      type Mpls-te-bw-limit;
      description "Bandwidth limit type";
    }
    leaf bandwidth {
      xr:xr-xml-map "mpls_lcac:Bandwidth";
      type uint32;
      units "kbit/s";
      description "Bandwidth (kbps)";
    }
    leaf tunnel-instance {
      xr:xr-xml-map "mpls_lcac:TunnelInstance";
      type uint32;
      description "Tunnel instance";
    }
    leaf in-use-bandwidth {
      xr:xr-xml-map "mpls_lcac:InUseBandwidth";
      type uint32;
      units "kbit/s";
      description "Bandwidth currently in use (kbps)";
    }
    leaf soft-preempted-in-use-bandwidth {
      xr:xr-xml-map "mpls_lcac:SoftPreemptedInUseBandwidth";
      type uint32;
      units "kbit/s";
      description
        "Bandwidth soft preempted and rerouted over the
        backup(kbps)";
    }
    leaf ls-ps {
      xr:xr-xml-map "mpls_lcac:LSPs";
      type uint32;
      description "Number of LSPs";
    }
    leaf s2l-families {
      xr:xr-xml-map "mpls_lcac:S2LFamilies";
      type uint32;
      description "Number of S2L Families";
    }
    leaf s2-ls {
      xr:xr-xml-map "mpls_lcac:S2Ls";
      type uint32;
      description "Number of P2MP S2Ls";
    }
    leaf frr-active-ls-ps {
      xr:xr-xml-map "mpls_lcac:FRRActiveLSPs";
      type uint32;
      description "Number of LSPs in FRR active state";
    }
    leaf frr-active-soft-preempted-ls-ps {
      xr:xr-xml-map "mpls_lcac:FRRActiveSoftPreemptedLSPs";
      type uint32;
      description
        "Number of soft preempted LSPs routed over backup";
    }
  }

  grouping TE-TUNNEL-AUTOROUTE-DEST {
    description "TE TUNNEL AUTOROUTE DEST";
    leaf prefix-address {
      xr:xr-xml-map "mpls_lcac:PrefixAddress";
      type inet:ipv4-address;
      description "PrefixAddress";
    }
    leaf prefix-length {
      xr:xr-xml-map "mpls_lcac:PrefixLength";
      type uint32;
      description "PrefixLength";
    }
    leaf metric {
      xr:xr-xml-map "mpls_lcac:Metric";
      type uint32;
      description "Metric";
    }
    leaf install-time {
      xr:xr-xml-map "mpls_lcac:InstallTime";
      type uint32;
      description "InstallTime";
    }
    leaf interface-handle {
      xr:xr-xml-map "mpls_lcac:InterfaceHandle";
      type xr:Interface-name;
      description "InterfaceHandle";
    }
  }

  grouping TE-TUNNEL-AUTOROUTE-DESTINATIONS {
    description "TE TUNNEL AUTOROUTE DESTINATIONS";
    leaf tunnel-id-xr {
      xr:xr-xml-map "mpls_lcac:tunnel-id-xr";
      type uint16;
      description "tunnel id xr";
    }

    list tunnel-autoroute-dest {
      description "tunnel autoroute dest";
      uses TE-TUNNEL-AUTOROUTE-DEST;
    }
  }

  grouping TE-SYNC-STATUS-MASTER-INFO {
    description "Master Sync status information";

    container idt {
      description "Sync status IDT information";
      uses TE-SYNC-IDT-INFO;
    }
  }

  grouping TE-S2L-PENDING-INFO {
    description "Sync pending S2L information";
    leaf pending-reason {
      xr:xr-xml-map "mpls_lcac:PendingReason";
      type Te-sync-pending-reason;
      description "Pending reason";
    }
    leaf signaled-name {
      xr:xr-xml-map "mpls_lcac:SignaledName";
      type string;
      description "Signaled name";
    }
    leaf s2l-role {
      xr:xr-xml-map "mpls_lcac:S2LRole";
      type Mpls-te-tunnel-role;
      description "S2L role";
    }
  }

  grouping TE-VIF-PENDING-INFO {
    description "Sync pending VIF information";
    leaf pending-reason {
      xr:xr-xml-map "mpls_lcac:PendingReason";
      type Te-sync-pending-reason;
      description "Pending reason";
    }
    leaf tunnel-name {
      xr:xr-xml-map "mpls_lcac:TunnelName";
      type string;
      description "Tunnel name";
    }
  }

  grouping TE-IDT-STATUS {
    description "IDT status information";
    leaf is-ready-status {
      xr:xr-xml-map "mpls_lcac:IsReadyStatus";
      type boolean;
      description "Ready status";
    }
    leaf reason {
      xr:xr-xml-map "mpls_lcac:Reason";
      type Te-sync-not-ready-reason;
      description "Not ready reason";
    }
    leaf idt-start-time {
      xr:xr-xml-map "mpls_lcac:IDTStartTime";
      type uint32;
      units "second";
      description "IDT start timestampe in seconds";
    }
    leaf idt-end-time {
      xr:xr-xml-map "mpls_lcac:IDTEndTime";
      type uint32;
      units "second";
      description "IDT end timestampe in seconds";
    }
    leaf declare-time {
      xr:xr-xml-map "mpls_lcac:DeclareTime";
      type uint32;
      units "second";
      description "Declare ready timestampe in seconds";
    }
    leaf withdraw-time {
      xr:xr-xml-map "mpls_lcac:WithdrawTime";
      type uint32;
      units "second";
      description "Withdraw ready timestampe in seconds";
    }
  }

  grouping TE-SYNC-IDT-INFO {
    description "Sync Status information";

    container current-idt-info {
      description "Current IDT information";
      uses TE-IDT-STATUS;
    }

    container previous-idt-status {
      description "Previous IDT information";
      uses TE-IDT-STATUS;
    }
  }

  grouping TE-SYNC-STATUS-SLAVE-INFO {
    description "Sync status slave Information";

    container idt {
      description "Sync status IDT information";
      uses TE-SYNC-IDT-INFO;
    }
    leaf insync-tunnels {
      xr:xr-xml-map "mpls_lcac:InsyncTunnels";
      type uint32;
      description "Tunnels in sync";
    }
    leaf insync-sub-ls-ps {
      xr:xr-xml-map "mpls_lcac:InsyncSubLSPs";
      type uint32;
      description "Sub-LSPs in sync";
    }
    leaf pending-tunnels {
      xr:xr-xml-map "mpls_lcac:PendingTunnels";
      type uint32;
      description "Tunnels in sync pending";
    }
    leaf pending-sub-ls-ps {
      xr:xr-xml-map "mpls_lcac:PendingSubLSPs";
      type uint32;
      description "Sub-LSPs in sync pending";
    }

    list vif-pending {
      description "Pending tunnels details";
      uses TE-VIF-PENDING-INFO;
    }

    list s2l-pending {
      description "Pending sub-LSPs details";
      uses TE-S2L-PENDING-INFO;
    }
  }

  grouping TE-SYNC-STATUS-INFO {
    description
      "Sync information for the NSR and ISSU based on
      master or slave role";

    container slave-sync-information {
      when "../sync-show-type = 'slave-sync-status-show'" {
        description "../SyncShowType = 'SlaveSyncStatusShow'";
      }
      description "Slave sync information";
      uses TE-SYNC-STATUS-SLAVE-INFO;
    }

    container master-sync-information {
      when "../sync-show-type = 'master-sync-status-show'" {
        description "../SyncShowType = 'MasterSyncStatusShow'";
      }
      description "Master sync information";
      uses TE-SYNC-STATUS-MASTER-INFO;
    }
    leaf sync-show-type {
      xr:xr-xml-map "mpls_lcac:SyncShowType";
      type Te-sync-status-show;
      description "SyncShowType";
    }
  }

  grouping TE-NSR-ISSU-STATUS-INFO {
    description "NSR/ISSU sync status information";

    container sync-status-information {
      description "Sync information for the NSR and ISSU";
      uses TE-SYNC-STATUS-INFO;
    }
    leaf role {
      xr:xr-xml-map "mpls_lcac:Role";
      type Te-proc-role;
      description "Process role";
    }
  }

  grouping MPLS-TE-DSTE-CLASS {
    description "A DSTE class";
    leaf class-number {
      xr:xr-xml-map "mpls_lcac:ClassNumber";
      type uint8;
      description "The DS-TE class number from 0 to 7";
    }
    leaf class-type {
      xr:xr-xml-map "mpls_lcac:ClassType";
      type uint8;
      description "The class type of the TE class";
    }
    leaf priority {
      xr:xr-xml-map "mpls_lcac:Priority";
      type uint8;
      description "The priority of the TE class";
    }
    leaf class-status {
      xr:xr-xml-map "mpls_lcac:ClassStatus";
      type Mpls-te-dste-class-status;
      description "The status of the TE class";
    }
  }

  grouping MPLS-TE-DSTE-CLASSES {
    description " A set of DSTE classes";

    list te-class {
      max-elements "8";
      description "te class";
      uses MPLS-TE-DSTE-CLASS;
    }
  }

  grouping MPLS-TE-TOPO-SRLG-LINK {
    description "SRLG link address data";

    container link-address-generic {
      description "Link address";
      uses TE-ADDR;
    }
    leaf link-address {
      xr:xr-xml-map "mpls_lcac:LinkAddress";
      type inet:ipv4-address;
      description "Link address";
    }
    leaf te-router-id {
      xr:xr-xml-map "mpls_lcac:TERouterID";
      type inet:ipv4-address;
      description "Link TE router-id";
    }
  }

  grouping MPLS-TE-TOPO-SRLG-AREA {
    description "A MPLS TE topology link in a SRLG";
    leaf igp-type {
      xr:xr-xml-map "mpls_lcac:IGPType";
      type Igp-protocol;
      description "IGP type";
    }
    leaf igp-instance {
      xr:xr-xml-map "mpls_lcac:IGPInstance";
      type string;
      description "IGP Instance name";
    }
    leaf igp-area {
      xr:xr-xml-map "mpls_lcac:IGPArea";
      type uint32;
      description "IGP Area ID";
    }
    leaf igp-area-format {
      xr:xr-xml-map "mpls_lcac:IGPAreaFormat";
      type Igp-ospf-area-format;
      description "IGP-area format";
    }

    list srlg-link {
      description "Links in this SRLG/area";
      uses MPLS-TE-TOPO-SRLG-LINK;
    }
  }

  grouping MPLS-TE-TOPO-SRLG {
    description "A SRLG entry in the MPLS TE topology";
    leaf srlg-name {
      xr:xr-xml-map "mpls_lcac:SRLGName";
      type string;
      description "SRLG name";
    }
    leaf admin-weight {
      xr:xr-xml-map "mpls_lcac:AdminWeight";
      type uint32;
      description
        "The admin weight that is added to the link if
        the SRLG is shared with the protected link";
    }

    list srlg-areas {
      description "Topology areas in this SRLG";
      uses MPLS-TE-TOPO-SRLG-AREA;
    }
  }

  grouping MPLS-TE-TOPO-CFG-SRLG-LINK {
    description "A link associated with configured SRLG";
    leaf local-address {
      xr:xr-xml-map "mpls_lcac:LocalAddress";
      type inet:ipv4-address;
      description "Local address";
    }
    leaf remote-address {
      xr:xr-xml-map "mpls_lcac:RemoteAddress";
      type inet:ipv4-address;
      description "Remote address";
    }
  }

  grouping MPLS-TE-TOPO-CFG-SRLG {
    description "A configured SRLG entry";
    leaf srlg-number-xr {
      xr:xr-xml-map "mpls_lcac:srlg-number-xr";
      type uint32;
      description "SRLG number";
    }
    leaf srlg-name {
      xr:xr-xml-map "mpls_lcac:SRLGName";
      type string;
      description "SRLG name";
    }
    leaf admin-weight {
      xr:xr-xml-map "mpls_lcac:AdminWeight";
      type uint32;
      description
        "The admin weight that is added to the link if
        the SRLG is shared with the protected link";
    }
    leaf is-admin-weight-configured {
      xr:xr-xml-map "mpls_lcac:IsAdminWeightConfigured";
      type boolean;
      description
        "Set to TRUE if the admin weight is explicitely
        configured";
    }

    list srlg-link {
      description "Link associated with the SRLG";
      uses MPLS-TE-TOPO-CFG-SRLG-LINK;
    }
  }

  grouping MPLS-TE-TOPOLOGY-PATH-BAG {
    description "MPLS TE Topology Path Information";

    container affinity {
      description "Affinity";
      uses MPLS-TE-TUNNELS-AFFINITY-INFO;
    }
    leaf tunnel-id-xr {
      xr:xr-xml-map "mpls_lcac:tunnel-id-xr";
      type uint32;
      description "The tunnel ID to which this path belong";
    }
    leaf destination-address-xr {
      xr:xr-xml-map "mpls_lcac:destination-address-xr";
      type inet:ipv4-address;
      description "The path's destination";
    }
    leaf is-partial-path {
      xr:xr-xml-map "mpls_lcac:IsPartialPath";
      type boolean;
      description "TRUE if path is partial";
    }
    leaf is-full-path {
      xr:xr-xml-map "mpls_lcac:IsFullPath";
      type boolean;
      description "TRUE if path is full";
    }
    leaf is-topology-checked {
      xr:xr-xml-map "mpls_lcac:IsTopologyChecked";
      type boolean;
      description "TRUE if checking the topology is enabled";
    }
    leaf is-segment-routing-db-checked {
      xr:xr-xml-map "mpls_lcac:IsSegmentRoutingDBChecked";
      type boolean;
      description
        "TRUE if checking the Segment-Routing DB is
        enabled";
    }
    leaf requested-bandwidth {
      xr:xr-xml-map "mpls_lcac:RequestedBandwidth";
      type uint64;
      description "The path's requested bandwidth";
    }
    leaf bandwidth-type {
      xr:xr-xml-map "mpls_lcac:BandwidthType";
      type uint64;
      description "The path's bandwidth type";
    }
    leaf mininum-bandwidth {
      xr:xr-xml-map "mpls_lcac:MininumBandwidth";
      type uint64;
      description "The path's minimum bandwidth";
    }
    leaf accumulated-admin-weight {
      xr:xr-xml-map "mpls_lcac:AccumulatedAdminWeight";
      type uint64;
      description "The path's accumulated admin weight";
    }
    leaf setup-priority-xr {
      xr:xr-xml-map "mpls_lcac:setup-priority-xr";
      type uint32;
      description "The path's setup priority";
    }
    leaf hold-priority-xr {
      xr:xr-xml-map "mpls_lcac:hold-priority-xr";
      type uint32;
      description "The path's hold priority";
    }
    leaf node-hop-count {
      xr:xr-xml-map "mpls_lcac:NodeHopCount";
      type uint8;
      description "Path hop count";
    }
    leaf exclude-srlg-address {
      xr:xr-xml-map "mpls_lcac:ExcludeSRLGAddress";
      type inet:ipv4-address;
      description "The Exclude SRLG IP Addr";
    }
    leaf-list hop {
      xr:xr-xml-map "mpls_lcac:HopList";
      type inet:ipv4-address;
      description "The path's array of hops";
    }

    list shared-risk-link-group {
      description "The path's excluded srlg groups";
      uses MPLS-SRLG-INFO;
    }

    list sr-segment {
      description "The path's array of Segment-Routing segments";
      uses TE-S2L-SR-PATH-HOP;
    }
  }

  grouping MPLS-TE-AREA-INFO {
    description "Global information for an MPLS-TE area";

    container local-sid-and-srbg {
      description "Local SID and SRBG";
      uses TE-SR-NODE-INFO;
    }
    leaf protocol {
      xr:xr-xml-map "mpls_lcac:Protocol";
      type Igp-protocol;
      description "Protocol used";
    }
    leaf node-id {
      xr:xr-xml-map "mpls_lcac:NodeID";
      type string;
      description "The node's IGP id";
    }
    leaf area-id {
      xr:xr-xml-map "mpls_lcac:AreaID";
      type string;
      description "The area's id";
    }
  }

  grouping MPLS-TE-TOPOLOGY-GLOBAL-INFO-BAG {
    description "MPLS TE Topology Global Information";
    leaf hold-down-interval {
      xr:xr-xml-map "mpls_lcac:HoldDownInterval";
      type uint32;
      units "second";
      description
        "Interval in seconds to hold down a neighbor
        after a signalling error";
    }
    leaf link-add-remove-count {
      xr:xr-xml-map "mpls_lcac:LinkAddRemoveCount";
      type uint32;
      description "Link add/remove counter";
    }
    leaf local-model-id {
      xr:xr-xml-map "mpls_lcac:LocalModelID";
      type uint32;
      description "Local BC Model ID";
    }

    list areas {
      description "Information for areas";
      uses MPLS-TE-AREA-INFO;
    }
  }

  grouping MPLS-TE-LSP-WRAP-PROTECTION-BAG {
    description "MPLS TE LSP Wrap Protected LSP Information";
    leaf source-address-xr {
      xr:xr-xml-map "mpls_lcac:source-address-xr";
      type inet:ipv4-address;
      description "Source";
    }
    leaf destination-address-xr {
      xr:xr-xml-map "mpls_lcac:destination-address-xr";
      type inet:ipv4-address;
      description "Destination";
    }
    leaf tunnel-id-xr {
      xr:xr-xml-map "mpls_lcac:tunnel-id-xr";
      type uint16;
      description "Tunnel ID";
    }
    leaf extended-tunnel-id-xr {
      xr:xr-xml-map "mpls_lcac:extended-tunnel-id-xr";
      type inet:ipv4-address;
      description "Extended Tunnel ID";
    }
    leaf tunnel-name {
      xr:xr-xml-map "mpls_lcac:TunnelName";
      type string;
      description "Tunnel Name";
    }
    leaf tunnel-instance {
      xr:xr-xml-map "mpls_lcac:TunnelInstance";
      type uint32;
      description "Tunnel instance";
    }
    leaf lsp-wrap-protection-enable {
      xr:xr-xml-map "mpls_lcac:LSPWrapProtectionEnable";
      type boolean;
      description "LSP Wrap protection enabled";
    }
    leaf lsp-wrap-protection-label {
      xr:xr-xml-map "mpls_lcac:LSPWrapProtectionLabel";
      type uint32;
      description "LSP Wrap Merge Point Label";
    }
    leaf reverse-egress-interface {
      xr:xr-xml-map "mpls_lcac:ReverseEgressInterface";
      type string;
      description "Reverse Egress Interface";
    }
    leaf reverse-lsp-label {
      xr:xr-xml-map "mpls_lcac:ReverseLspLabel";
      type uint32;
      description "Reverse LSP label";
    }
    leaf lsp-wrap-protection-state {
      xr:xr-xml-map "mpls_lcac:LSPWrapProtectionState";
      type Mpls-te-lsp-wrap-state;
      description "LSP wrap protection state";
    }
    leaf sub-group-original-id {
      xr:xr-xml-map "mpls_lcac:SubGroupOriginalID";
      type inet:ipv4-address;
      description "S2L Sub-Group Originator ID";
    }
    leaf sub-group-id-xr {
      xr:xr-xml-map "mpls_lcac:sub-group-id-xr";
      type uint16;
      description "S2L Sub-Group ID";
    }
    leaf p2mp-id-xr {
      xr:xr-xml-map "mpls_lcac:p2mp-id-xr";
      type uint32;
      description "S2L P2MP ID";
    }
  }

  grouping TE-NEXTHOP-PATH {
    description "TE NEXTHOP PATH";
    leaf interface {
      xr:xr-xml-map "mpls_lcac:Interface";
      type xr:Interface-name;
      description "Interface";
    }
    leaf address {
      xr:xr-xml-map "mpls_lcac:Address";
      type inet:ipv4-address;
      description "Address";
    }
    leaf abr-address {
      xr:xr-xml-map "mpls_lcac:ABRAddress";
      type inet:ipv4-address;
      description "ABRAddress";
    }
  }

  grouping TE-RIB-ROUTE-BAG {
    description "TE RIB ROUTE BAG";
    leaf route-protocol-name {
      xr:xr-xml-map "mpls_lcac:RouteProtocolName";
      type string;
      description "RouteProtocolName";
    }
    leaf route-distance {
      xr:xr-xml-map "mpls_lcac:RouteDistance";
      type uint32;
      description "RouteDistance";
    }
    leaf route-metric {
      xr:xr-xml-map "mpls_lcac:RouteMetric";
      type uint32;
      description "RouteMetric";
    }
    leaf last-update-time {
      xr:xr-xml-map "mpls_lcac:LastUpdateTime";
      type uint32;
      description "LastUpdateTime";
    }
    leaf is-registered {
      xr:xr-xml-map "mpls_lcac:IsRegistered";
      type boolean;
      description "IsRegistered";
    }
    leaf is-stale {
      xr:xr-xml-map "mpls_lcac:IsStale";
      type boolean;
      description "IsStale";
    }
    leaf is-default {
      xr:xr-xml-map "mpls_lcac:IsDefault";
      type boolean;
      description "IsDefault";
    }
    leaf is-connected {
      xr:xr-xml-map "mpls_lcac:IsConnected";
      type boolean;
      description "IsConnected";
    }
    leaf is-populated {
      xr:xr-xml-map "mpls_lcac:IsPopulated";
      type boolean;
      description "IsPopulated";
    }
    leaf route-type {
      xr:xr-xml-map "mpls_lcac:RouteType";
      type uint16;
      description "RouteType";
    }

    list next-hop-path {
      description "next hop path";
      uses TE-NEXTHOP-PATH;
    }
  }

  grouping TE-TUNNEL-PATH {
    description "TE TUNNEL PATH";
    leaf tunnel-id {
      xr:xr-xml-map "mpls_lcac:TunnelID";
      type uint16;
      description "TunnelID";
    }
    leaf interface-handle {
      xr:xr-xml-map "mpls_lcac:InterfaceHandle";
      type xr:Interface-name;
      description "InterfaceHandle";
    }
    leaf install-time {
      xr:xr-xml-map "mpls_lcac:InstallTime";
      type uint32;
      description "InstallTime";
    }
    leaf installed-metric {
      xr:xr-xml-map "mpls_lcac:InstalledMetric";
      type uint32;
      description "InstalledMetric";
    }
  }

  grouping TE-NEXTHOP-ROUTE {
    description "TE NEXTHOP ROUTE";

    container active-route {
      description "active route";
      uses TE-RIB-ROUTE-BAG;
    }

    container backup-route {
      description "backup route";
      uses TE-RIB-ROUTE-BAG;
    }
    leaf prefix-address-xr {
      xr:xr-xml-map "mpls_lcac:prefix-address-xr";
      type inet:ipv4-address;
      description "prefix address xr";
    }
    leaf prefix-length-xr {
      xr:xr-xml-map "mpls_lcac:prefix-length-xr";
      type uint32;
      description "prefix length xr";
    }
    leaf exact-match {
      xr:xr-xml-map "mpls_lcac:ExactMatch";
      type boolean;
      description "ExactMatch";
    }
    leaf create-time {
      xr:xr-xml-map "mpls_lcac:CreateTime";
      type uint32;
      description "CreateTime";
    }
    leaf last-used-time {
      xr:xr-xml-map "mpls_lcac:LastUsedTime";
      type uint32;
      description "LastUsedTime";
    }
    leaf expire-time {
      xr:xr-xml-map "mpls_lcac:ExpireTime";
      type uint32;
      description "ExpireTime";
    }
    leaf installed-tunnel-path-num {
      xr:xr-xml-map "mpls_lcac:InstalledTunnelPathNum";
      type uint32;
      description "InstalledTunnelPathNum";
    }

    list tunnel-path {
      description "tunnel path";
      uses TE-TUNNEL-PATH;
    }
  }

  grouping TE-SH-IGP-AREA-STATS {
    description "Statistics for an IGP-area";
    leaf area-adjacency-request-messages {
      xr:xr-xml-map "mpls_lcac:AreaAdjacencyRequestMessages";
      type uint32;
      description "Number of adjacency request messages sent";
    }
    leaf area-adjacency-announce-messages {
      xr:xr-xml-map "mpls_lcac:AreaAdjacencyAnnounceMessages";
      type uint32;
      description
        "Number of adjacency announcement messages
        received";
    }
    leaf area-flood-messages {
      xr:xr-xml-map "mpls_lcac:AreaFloodMessages";
      type uint32;
      description "Number of local LSA floods sent";
    }
    leaf area-lsa-announce-messages {
      xr:xr-xml-map "mpls_lcac:AreaLSAAnnounceMessages";
      type uint32;
      description "Number of LSA announcement messages received";
    }
    leaf area-lsa-fragment-announce-messages {
      xr:xr-xml-map "mpls_lcac:AreaLSAFragmentAnnounceMessages";
      type uint32;
      description
        "Number of LSA fragment announcement messages
        received";
    }
    leaf area-lsa-delete-messages {
      xr:xr-xml-map "mpls_lcac:AreaLSADeleteMessages";
      type uint32;
      description "Number of LSA delete messages received";
    }
    leaf area-lsa-fragment-delete-messages {
      xr:xr-xml-map "mpls_lcac:AreaLSAFragmentDeleteMessages";
      type uint32;
      description "Number of LSA fragment delete messages received";
    }
    leaf area-tunnel-announce-messages {
      xr:xr-xml-map "mpls_lcac:AreaTunnelAnnounceMessages";
      type uint32;
      description "Number of tunnel announcement messages sent";
    }
  }

  grouping TE-SH-IGP-AREA-ACTIVE {
    description "Data relating to an active IGP area";

    container area-statistics {
      description "Area communication statistics";
      uses TE-SH-IGP-AREA-STATS;
    }
    leaf interfaces-count {
      xr:xr-xml-map "mpls_lcac:InterfacesCount";
      type uint32;
      description "Number of interfaces running over this area";
    }
    leaf link-idt-received {
      xr:xr-xml-map "mpls_lcac:LinkIDTReceived";
      type boolean;
      description
        "Flag to indicate IDT for link adjacencies was
        received";
    }
    leaf topology-idt-received {
      xr:xr-xml-map "mpls_lcac:TopologyIDTReceived";
      type boolean;
      description "Flag to indicate IDT topology was received";
    }
    leaf p2p-heads-count {
      xr:xr-xml-map "mpls_lcac:P2PHeadsCount";
      type uint32;
      description
        "Number of p2p tunnel heads whose path was
        calculated over this area";
    }
    leaf p2p-autoroute-announced-count {
      xr:xr-xml-map "mpls_lcac:P2PAutorouteAnnouncedCount";
      type uint32;
      description
        "Number of p2p tunnel heads which have been
        autoroute-announced into this area";
    }
    leaf p2p-forwarding-adjacency-count {
      xr:xr-xml-map "mpls_lcac:P2PForwardingAdjacencyCount";
      type uint32;
      description
        "Number of p2p tunnel heads which have been
        announced as forwarding adjacencies in this area";
    }
    leaf p2mp-destination-count {
      xr:xr-xml-map "mpls_lcac:P2MPDestinationCount";
      type uint32;
      description
        "Number of P2MP destinations whose path was
        calculated over this area";
    }
    leaf tunnel-loose-hops {
      xr:xr-xml-map "mpls_lcac:TunnelLooseHops";
      type uint32;
      description
        "Number of tunnels with a loose hop ERO expanded
        in this area";
    }
  }

  grouping TE-SH-IGP-AREA {
    description "An IGP area";

    container active-data {
      description "Data which applies only to an active area";
      uses TE-SH-IGP-AREA-ACTIVE;
    }
    leaf area-index {
      xr:xr-xml-map "mpls_lcac:AreaIndex";
      type uint32;
      description "Internal area index";
    }
    leaf area-number {
      xr:xr-xml-map "mpls_lcac:AreaNumber";
      type uint32;
      description "Area number";
    }
    leaf area-format {
      xr:xr-xml-map "mpls_lcac:AreaFormat";
      type Igp-ospf-area-format;
      description "IGP Area Format";
    }
    leaf is-config-ready {
      xr:xr-xml-map "mpls_lcac:IsConfigReady";
      type boolean;
      description
        "Indicates whether or not the area is correctly
        configured under the IGP submode to run TE";
    }
  }

  grouping TE-SH-IGP {
    description "An IGP instance";
    leaf igp-system-id {
      xr:xr-xml-map "mpls_lcac:IGPSystemID";
      type string;
      description
        " The IGP instance's system/router-id; interpret
        appropriately depending on IGP type";
    }
    leaf configured-te-router-id {
      xr:xr-xml-map "mpls_lcac:ConfiguredTERouterID";
      type inet:ipv4-address;
      description "Configured TE router-id";
    }
    leaf global-router-id {
      xr:xr-xml-map "mpls_lcac:GlobalRouterID";
      type inet:ipv4-address;
      description "Global router-id";
    }
    leaf globall-router-id-optical {
      xr:xr-xml-map "mpls_lcac:GloballRouterIDOptical";
      type inet:ipv4-address;
      description "Global router-id for GMPLS (optical TE)";
    }
    leaf in-use-te-router-id {
      xr:xr-xml-map "mpls_lcac:InUseTERouterID";
      type inet:ipv4-address;
      description "TE router-id in use";
    }
    leaf is-connection-up {
      xr:xr-xml-map "mpls_lcac:IsConnectionUp";
      type boolean;
      description
        "Flag to indicate whether the IGP connection is
        open or not";
    }
    leaf connection-up-count {
      xr:xr-xml-map "mpls_lcac:ConnectionUpCount";
      type uint32;
      description "Number of times IGP connection has gone up";
    }
    leaf connection-down-count {
      xr:xr-xml-map "mpls_lcac:ConnectionDownCount";
      type uint32;
      description "Number of times IGP connection has gone down";
    }

    list area {
      description "IGP area information";
      uses TE-SH-IGP-AREA;
    }
  }

  grouping MPLS-TE-FWD-ADJ-INFO {
    description "A forwarding-adjacency";
    leaf tunnel-name {
      xr:xr-xml-map "mpls_lcac:TunnelName";
      type string;
      description "The tunnel name";
    }
    leaf traffic-share {
      xr:xr-xml-map "mpls_lcac:TrafficShare";
      type uint32;
      description "Traffic Share";
    }
    leaf hold-time {
      xr:xr-xml-map "mpls_lcac:HoldTime";
      type uint32;
      units "second";
      description "Hold time in seconds";
    }
    leaf is-adjacency-up {
      xr:xr-xml-map "mpls_lcac:IsAdjacencyUp";
      type boolean;
      description "True if adj is up";
    }

    list ig-ps {
      description "List of IGPs to which it is announced";
      uses MPLS-TE-AREA-AFI-INFO;
    }
  }

  grouping MPLS-TE-FWD-ADJ-BAG {
    description " A list of forwarding-adjacencies";
    leaf adjacencies {
      xr:xr-xml-map "mpls_lcac:Adjacencies";
      type uint32;
      description "Number of Forwarding Adjacencies";
    }
    leaf ipv6-adjacencies {
      xr:xr-xml-map "mpls_lcac:IPv6Adjacencies";
      type uint32;
      description "Number of IPv6 Forwarding Adjacencies";
    }
    leaf destination-address-xr {
      xr:xr-xml-map "mpls_lcac:destination-address-xr";
      type inet:ipv4-address;
      description "The tunnel destination";
    }

    list forward-adjacency {
      description "Forwarding-adjacency list";
      uses MPLS-TE-FWD-ADJ-INFO;
    }
  }

  grouping MPLS-TE-AUTOTUN-BACKUP-CONFIG-INFO {
    description
      "Auto-tunnel backup feature configuration
      information";
    leaf is-configured {
      xr:xr-xml-map "mpls_lcac:IsConfigured";
      type boolean;
      description
        "Indicate if auto-tunnel bacukp feature is
        configured ";
    }
    leaf interface-count {
      xr:xr-xml-map "mpls_lcac:InterfaceCount";
      type uint32;
      description
        "Number of TE link interfaces with auto-tunnel
        backup configured";
    }
    leaf unused-removal-timeout-configured {
      xr:xr-xml-map "mpls_lcac:UnusedRemovalTimeoutConfigured";
      type uint32;
      units "second";
      description
        "Configured value of unused removal timer in
        seconds";
    }
    leaf min-tunnel-id {
      xr:xr-xml-map "mpls_lcac:MinTunnelID";
      type uint16;
      description "Lower bound of configured tunnel ID range";
    }
    leaf max-tunnel-id {
      xr:xr-xml-map "mpls_lcac:MaxTunnelID";
      type uint16;
      description "Upper bound of configured tunnel ID range";
    }
  }

  grouping MPLS-TE-AUTOTUN-BACKUP-SUMMARY-INFO {
    description "Autotunnel backup summary information";
    leaf autobackups {
      xr:xr-xml-map "mpls_lcac:Autobackups";
      type uint32;
      description "Total number of autobackup tunnels";
    }
    leaf up-autobackups {
      xr:xr-xml-map "mpls_lcac:UpAutobackups";
      type uint32;
      description "Total number of autobackup tunnels that are up";
    }
    leaf down-autobackups {
      xr:xr-xml-map "mpls_lcac:DownAutobackups";
      type uint32;
      description
        "Total number of autobackup tunnels that are down";
    }
    leaf unused-autobackups {
      xr:xr-xml-map "mpls_lcac:UnusedAutobackups";
      type uint32;
      description
        "Total number of autobackup tunnels that are
        unused";
    }
    leaf next-hop-autobackups {
      xr:xr-xml-map "mpls_lcac:NextHopAutobackups";
      type uint32;
      description
        "Total number of autobackup tunnels that are NHOP";
    }
    leaf next-next-hop-autobackups {
      xr:xr-xml-map "mpls_lcac:NextNextHopAutobackups";
      type uint32;
      description
        "Total number of autobackup tunnels that are
        NNHOP";
    }
    leaf srlg-strict-autobackups {
      xr:xr-xml-map "mpls_lcac:SRLGStrictAutobackups";
      type uint32;
      description
        "Total number of autobackup tunnels that are
        using SRLG strict";
    }
    leaf srlg-preferred-autobackups {
      xr:xr-xml-map "mpls_lcac:SRLGPreferredAutobackups";
      type uint32;
      description
        "Total number of autobackup tunnels that are
        using SRLG preferred";
    }
    leaf srlg-weighted-autobackups {
      xr:xr-xml-map "mpls_lcac:SRLGWeightedAutobackups";
      type uint32;
      description
        "Total number of autobackup tunnels that are
        using weighted SRLG";
    }
    leaf next-hop-autobackup-protected-ls-ps {
      xr:xr-xml-map "mpls_lcac:NextHopAutobackupProtectedLSPs";
      type uint32;
      description
        "Total number of autobackup protected LSPs with
        NHOP and no SRLG";
    }
    leaf next-next-hop-autobackup-protected-ls-ps {
      xr:xr-xml-map "mpls_lcac:NextNextHopAutobackupProtectedLSPs";
      type uint32;
      description
        "Total number of autobackup protected LSPs with
        NNHOP and no SRLG";
    }
    leaf next-hop-srlg-autobackup-protected-ls-ps {
      xr:xr-xml-map "mpls_lcac:NextHopSRLGAutobackupProtectedLSPs";
      type uint32;
      description
        "Total number of autobackup protected LSPs with
        NHOP and SRLG";
    }
    leaf next-next-hop-srlg-autobackup-protected-ls-ps {
      xr:xr-xml-map "mpls_lcac:NextNextHopSRLGAutobackupProtectedLS"+
        "Ps";
      type uint32;
      description
        "Total number of autobackup protected LSPs with
        NNHOP and SRLG";
    }
    leaf next-hop-autobackup-protected-s2l-families {
      xr:xr-xml-map "mpls_lcac:NextHopAutobackupProtectedS2LFamilie"+
        "s";
      type uint32;
      description
        "Total number of autobackup protected S2L
        Families with NHOP and no SRLG";
    }
    leaf next-next-hop-autobackup-protected-s2l-families {
      xr:xr-xml-map "mpls_lcac:NextNextHopAutobackupProtectedS2LFam"+
        "ilies";
      type uint32;
      description
        "Total number of autobackup protected S2L
        Families with NNHOP and no SRLG";
    }
    leaf next-hop-srlg-autobackup-protected-s2l-families {
      xr:xr-xml-map "mpls_lcac:NextHopSRLGAutobackupProtectedS2LFam"+
        "ilies";
      type uint32;
      description
        "Total number of autobackup protected S2L
        Families with NHOP and SRLG";
    }
    leaf next-next-hop-srlg-autobackup-protected-s2l-families {
      xr:xr-xml-map "mpls_lcac:NextNextHopSRLGAutobackupProtectedS2"+
        "LFamilies";
      type uint32;
      description
        "Total number of autobackup protected S2L
        Families with NNHOP and SRLG";
    }
    leaf next-hop-autobackup-protected-s2-ls {
      xr:xr-xml-map "mpls_lcac:NextHopAutobackupProtectedS2Ls";
      type uint32;
      description
        "Total number of autobackup protected S2Ls with
        NHOP and no SRLG";
    }
    leaf next-next-hop-autobackup-protected-s2-ls {
      xr:xr-xml-map "mpls_lcac:NextNextHopAutobackupProtectedS2Ls";
      type uint32;
      description
        "Total number of autobackup protected S2Ls with
        NNHOP and no SRLG";
    }
    leaf next-hop-srlg-autobackup-protected-s2-ls {
      xr:xr-xml-map "mpls_lcac:NextHopSRLGAutobackupProtectedS2Ls";
      type uint32;
      description
        "Total number of autobackup protected S2Ls with
        NHOP and SRLG";
    }
    leaf next-next-hop-srlg-autobackup-protected-s2-ls {
      xr:xr-xml-map "mpls_lcac:NextNextHopSRLGAutobackupProtectedS2"+
        "Ls";
      type uint32;
      description
        "Total number of autobackup protected S2Ls with
        NNHOP and SRLG";
    }
  }

  grouping MPLS-TE-AUTOTUN-BACKUP-TUNNEL-INFO {
    description "Auto-tunnel backup brief tunnel information";
    leaf tunnel-name {
      xr:xr-xml-map "mpls_lcac:TunnelName";
      type string;
      description "Tunnel Name";
    }
    leaf operational-status {
      xr:xr-xml-map "mpls_lcac:OperationalStatus";
      type Mpls-te-tunnel-state;
      description "Tunnel operational status";
    }
    leaf srlg-mode {
      xr:xr-xml-map "mpls_lcac:SRLGMode";
      type Auto-backup-srlg-mode;
      description "SRLG exclude mode for this auto-tunnel backup";
    }
    leaf atb-protection-type {
      xr:xr-xml-map "mpls_lcac:ATBProtectionType";
      type Auto-backup-protection;
      description
        "Type of protection offered by this auto-tunnel
        backup";
    }
    leaf protected-flows {
      xr:xr-xml-map "mpls_lcac:ProtectedFlows";
      type uint32;
      description "Number of protected flows";
    }
    leaf protected-interface-name {
      xr:xr-xml-map "mpls_lcac:ProtectedInterfaceName";
      type string;
      description "Interface protected by this auto-tunnel backup";
    }
    leaf protected-router-id {
      xr:xr-xml-map "mpls_lcac:ProtectedRouterID";
      type inet:ipv4-address;
      description
        "Router ID of node protected by this auto-tunnel
        backup";
    }
  }

  grouping MPLS-TE-AUTOTUN-MESH-ONEHOP-SUMMARY-INFO {
    description "Autotunnel mesh onehop summary information";
    leaf auto-mesh-one-hop-tunnels {
      xr:xr-xml-map "mpls_lcac:AutoMeshOneHopTunnels";
      type uint32;
      description "Total number of automesh onehop tunnels";
    }
    leaf up-auto-mesh-one-hop-tunnels {
      xr:xr-xml-map "mpls_lcac:UpAutoMeshOneHopTunnels";
      type uint32;
      description
        "Total number of automesh onehop tunnels that are
        up";
    }
    leaf down-auto-mesh-one-hop-tunnels {
      xr:xr-xml-map "mpls_lcac:DownAutoMeshOneHopTunnels";
      type uint32;
      description
        "Total number of automesh onehop tunnels that are
        down";
    }
    leaf frr-auto-mesh-tunnels {
      xr:xr-xml-map "mpls_lcac:FRRAutoMeshTunnels";
      type uint32;
      description
        "Total number of automesh onehop tunnels that are
        FRR enabled";
    }
    leaf auto-mesh-one-hop-groups {
      xr:xr-xml-map "mpls_lcac:AutoMeshOneHopGroups";
      type uint32;
      description "Total number of automesh onehop mesh-groups";
    }
    leaf auto-mesh-one-hop-destinations {
      xr:xr-xml-map "mpls_lcac:AutoMeshOneHopDestinations";
      type uint32;
      description "Total number of automesh onehop destinations";
    }
  }

  grouping MPLS-TE-AUTOMESH-ONEHOP-TUNNEL {
    description "TE Automesh Onehop Tunnel";
    leaf tunnel-id {
      xr:xr-xml-map "mpls_lcac:TunnelID";
      type uint16;
      description "Tunnel ID";
    }
    leaf destination-address {
      xr:xr-xml-map "mpls_lcac:DestinationAddress";
      type inet:ipv4-address;
      description "Destination Address";
    }
    leaf tunnel-lspid {
      xr:xr-xml-map "mpls_lcac:TunnelLSPID";
      type uint16;
      description "LSP ID";
    }
    leaf mesh-group-id {
      xr:xr-xml-map "mpls_lcac:MeshGroupID";
      type uint32;
      description "Meshgroup ID";
    }
    leaf tunnel-state {
      xr:xr-xml-map "mpls_lcac:TunnelState";
      type Mpls-te-tunnel-state;
      description "Tunnel state";
    }
  }

  grouping MPLS-TE-AUTOMESH-ONEHOP-INTERFACE {
    description "TE Automesh Onehop Interface";
    leaf interface-name-xr {
      xr:xr-xml-map "mpls_lcac:interface-name-xr";
      type string;
      description "Interface name";
    }

    list tunnel {
      description "Onehop tunnels created for this interface";
      uses MPLS-TE-AUTOMESH-ONEHOP-TUNNEL;
    }
  }

  grouping MPLS-TE-AUTOTUN-MESH-CONFIG-INFO {
    description
      "Auto-tunnel mesh feature configuration
      information";
    leaf is-configured {
      xr:xr-xml-map "mpls_lcac:IsConfigured";
      type boolean;
      description
        "Indicate if auto-tunnel mesh feature is
        configured ";
    }
    leaf unused-removal-timeout-configured {
      xr:xr-xml-map "mpls_lcac:UnusedRemovalTimeoutConfigured";
      type uint32;
      units "second";
      description
        "Configured value of unused removal timer in
        seconds";
    }
    leaf min-tunnel-id {
      xr:xr-xml-map "mpls_lcac:MinTunnelID";
      type uint16;
      description "Lower bound of configured tunnel ID range";
    }
    leaf max-tunnel-id {
      xr:xr-xml-map "mpls_lcac:MaxTunnelID";
      type uint16;
      description "Upper bound of configured tunnel ID range";
    }
  }

  grouping MPLS-TE-AUTOTUN-MESH-SUMMARY-INFO {
    description "Autotunnel mesh summary information";
    leaf auto-mesh-tunnels {
      xr:xr-xml-map "mpls_lcac:AutoMeshTunnels";
      type uint32;
      description "Total number of automesh tunnels";
    }
    leaf up-auto-mesh-tunnels {
      xr:xr-xml-map "mpls_lcac:UpAutoMeshTunnels";
      type uint32;
      description "Total number of automesh tunnels that are up";
    }
    leaf down-auto-mesh-tunnels {
      xr:xr-xml-map "mpls_lcac:DownAutoMeshTunnels";
      type uint32;
      description "Total number of automesh tunnels that are down";
    }
    leaf frr-auto-mesh-tunnels {
      xr:xr-xml-map "mpls_lcac:FRRAutoMeshTunnels";
      type uint32;
      description
        "Total number of automesh tunnels that are FRR
        enabled";
    }
    leaf auto-mesh-groups {
      xr:xr-xml-map "mpls_lcac:AutoMeshGroups";
      type uint32;
      description "Total number of automesh mesh-groups";
    }
    leaf auto-mesh-destinations {
      xr:xr-xml-map "mpls_lcac:AutoMeshDestinations";
      type uint32;
      description "Total number of automesh destinations";
    }
  }

  grouping MPLS-TE-MESHGROUP-DEST {
    description "TE Meshgroup destination info";
    leaf destination-address {
      xr:xr-xml-map "mpls_lcac:DestinationAddress";
      type inet:ipv4-address;
      description "Destination address";
    }
    leaf tunnel-id {
      xr:xr-xml-map "mpls_lcac:TunnelID";
      type uint16;
      description "Tunnel ID";
    }
    leaf operational-status {
      xr:xr-xml-map "mpls_lcac:OperationalStatus";
      type Mpls-te-tunnel-state;
      description "Tunnel operational status";
    }
    leaf remaining-time {
      xr:xr-xml-map "mpls_lcac:RemainingTime";
      type uint32;
      units "second";
      description "Remaining time for unused timer in seconds";
    }
  }

  grouping MPLS-TE-MESHGROUP {
    description "TE Meshgroup info";
    leaf mesh-group-id-xr {
      xr:xr-xml-map "mpls_lcac:mesh-group-id-xr";
      type uint32;
      description "Meshgroup ID";
    }
    leaf is-meshgroup-disabled {
      xr:xr-xml-map "mpls_lcac:IsMeshgroupDisabled";
      type boolean;
      description "Is the meshgroup disabled";
    }
    leaf attribute-set-name {
      xr:xr-xml-map "mpls_lcac:AttributeSetName";
      type string;
      description "Attribute set name";
    }
    leaf is-attribute-set-configured {
      xr:xr-xml-map "mpls_lcac:IsAttributeSetConfigured";
      type boolean;
      description
        "Is any attribute-set associated to this
        meshgroup";
    }
    leaf is-attribute-set-in-db {
      xr:xr-xml-map "mpls_lcac:IsAttributeSetInDB";
      type boolean;
      description
        "Flag to indicate the existence of attribute set
        found in database";
    }
    leaf destination-list-name {
      xr:xr-xml-map "mpls_lcac:DestinationListName";
      type string;
      description "Destination List name";
    }
    leaf is-destination-list-configured {
      xr:xr-xml-map "mpls_lcac:IsDestinationListConfigured";
      type boolean;
      description
        "Is any destiantion-list associated to this
        meshgroup";
    }
    leaf destination-list-type {
      xr:xr-xml-map "mpls_lcac:DestinationListType";
      type Te-acl;
      description "Type of the  destlist";
    }
    leaf remaining-time {
      xr:xr-xml-map "mpls_lcac:RemainingTime";
      type uint32;
      units "second";
      description "Remaining time for recreate timer in seconds";
    }
    leaf auto-mesh-tunnels {
      xr:xr-xml-map "mpls_lcac:AutoMeshTunnels";
      type uint32;
      description "Total number of automesh tunnels";
    }
    leaf auto-mesh-total-destinations {
      xr:xr-xml-map "mpls_lcac:AutoMeshTotalDestinations";
      type uint32;
      description "Total number of destinations";
    }
    leaf up-auto-mesh-tunnels {
      xr:xr-xml-map "mpls_lcac:UpAutoMeshTunnels";
      type uint32;
      description "Total number of automesh tunnels that are up";
    }
    leaf down-auto-mesh-tunnels {
      xr:xr-xml-map "mpls_lcac:DownAutoMeshTunnels";
      type uint32;
      description "Total number of automesh tunnels that are down";
    }
    leaf frr-auto-mesh-tunnels {
      xr:xr-xml-map "mpls_lcac:FRRAutoMeshTunnels";
      type uint32;
      description
        "Total number of automesh tunnels that are FRR
        enabled";
    }
    leaf auto-mesh-group-type {
      xr:xr-xml-map "mpls_lcac:AutoMeshGroupType";
      type Te-meshgroup;
      description "Meshgroup Type";
    }

    list destination {
      description "List of destinations for this meshgroup";
      uses MPLS-TE-MESHGROUP-DEST;
    }
  }

  grouping MPLS-TE-AUTOTUN-PCC-SUMMARY-INFO {
    description
      "Stateful PCE client auto-tunnel summary
      information";
    leaf pcc-auto-tunnel {
      xr:xr-xml-map "mpls_lcac:PCCAutoTunnel";
      type uint32;
      description
        "Total number of stateful PCE client auto-tunnels";
    }
    leaf up-pcc-auto-tunnels {
      xr:xr-xml-map "mpls_lcac:UpPCCAutoTunnels";
      type uint32;
      description
        "Total number of stateful PCE client auto-tunnels
        that are up";
    }
    leaf down-pcc-auto-tunnels {
      xr:xr-xml-map "mpls_lcac:DownPCCAutoTunnels";
      type uint32;
      description
        "Total number of stateful PCE client auto-tunnels
        that are down";
    }
  }

  grouping MPLS-TE-P2MP-TIMER-B {
    description "Description of a P2MP timer";
    leaf timer-type {
      xr:xr-xml-map "mpls_lcac:TimerType";
      type Mpls-te-p2mp-timer;
      description "Timer Type";
    }
    leaf timer-name {
      xr:xr-xml-map "mpls_lcac:TimerName";
      type string;
      description "Timer Name";
    }
    leaf start-time {
      xr:xr-xml-map "mpls_lcac:StartTime";
      type uint32;
      units "second";
      description "Date when timer was last started in seconds";
    }
    leaf expiry-time {
      xr:xr-xml-map "mpls_lcac:ExpiryTime";
      type uint32;
      units "second";
      description "Date when the timer last expired in seconds";
    }
    leaf stop-time {
      xr:xr-xml-map "mpls_lcac:StopTime";
      type uint32;
      units "second";
      description "Date when the timer was last stopped in seconds";
    }
    leaf duration {
      xr:xr-xml-map "mpls_lcac:Duration";
      type uint32;
      units "second";
      description "The expiry delay in seconds";
    }
    leaf is-running {
      xr:xr-xml-map "mpls_lcac:IsRunning";
      type boolean;
      description "True if the timer is running";
    }
  }

  grouping MPLS-TE-P2MP-TIMERS-B {
    description "Description of P2MP timers";

    list p2mp-timer {
      max-elements "22";
      description "Description of all P2MP timers";
      uses MPLS-TE-P2MP-TIMER-B;
    }
  }

  grouping MPLS-TE-AREA-AFI-INFO {
    description "IGP area information including AFI";
    leaf igp-area-id {
      xr:xr-xml-map "mpls_lcac:IGPAreaID";
      type string;
      description "The IGP Instance and Area ID";
    }
    leaf afi {
      xr:xr-xml-map "mpls_lcac:AFI";
      type Mpls-te-afi;
      description "AFI";
    }
  }

  grouping MPLS-TE-AUTOROUTE-BAG {
    description "MPLS TE Autoroute Information";
    leaf tunnel-name {
      xr:xr-xml-map "mpls_lcac:TunnelName";
      type string;
      description "The tunnel name";
    }
    leaf tunnel-sig-name {
      xr:xr-xml-map "mpls_lcac:TunnelSigName";
      type string;
      description "The tunnel signaled-name";
    }
    leaf tunnel-loadshare {
      xr:xr-xml-map "mpls_lcac:TunnelLoadshare";
      type uint32;
      description "Tunnel loadshare";
    }
    leaf announce-type {
      xr:xr-xml-map "mpls_lcac:AnnounceType";
      type Mpls-te-tunnel-announce;
      description "Announcement type";
    }
    leaf mode {
      xr:xr-xml-map "mpls_lcac:Mode";
      type Igpte-aa-metric-mode;
      description "Autoroute mode";
    }
    leaf igp-metric {
      xr:xr-xml-map "mpls_lcac:IGPMetric";
      type int32;
      description "IGP metric";
    }
    leaf hold-time {
      xr:xr-xml-map "mpls_lcac:HoldTime";
      type uint32;
      units "second";
      description "Hold time in seconds";
    }
    leaf area-format {
      xr:xr-xml-map "mpls_lcac:AreaFormat";
      type Igp-ospf-area-format;
      description "IGP Area Format";
    }
    leaf is-auto-mesh-aa {
      xr:xr-xml-map "mpls_lcac:IsAutoMeshAA";
      type boolean;
      description "True if this is auto-tunnel mesh AA";
    }
    leaf mesh-group-idaa {
      xr:xr-xml-map "mpls_lcac:MeshGroupIDAA";
      type uint32;
      description "MeshGroup ID for AA";
    }

    list ig-ps {
      description "List of IGPs to which it is announced";
      uses MPLS-TE-AREA-AFI-INFO;
    }
  }

  grouping MPLS-TE-ANNOUNCEMENT-DEST-BAG {
    description
      "The summary info of announcements for a
      destination and an IGP area";
    leaf igp-type {
      xr:xr-xml-map "mpls_lcac:IGPType";
      type Igp-protocol;
      description "IGP type";
    }
    leaf igp-instance {
      xr:xr-xml-map "mpls_lcac:IGPInstance";
      type string;
      description "IGP Instance name";
    }
    leaf igp-area {
      xr:xr-xml-map "mpls_lcac:IGPArea";
      type uint32;
      description "IGP Area ID";
    }
    leaf destination {
      xr:xr-xml-map "mpls_lcac:Destination";
      type inet:ipv4-address;
      description "Destination";
    }
    leaf announced-tunnels-count {
      xr:xr-xml-map "mpls_lcac:AnnouncedTunnelsCount";
      type uint16;
      description "The number of announced tunnels";
    }
    leaf autorouted-tunnels-count {
      xr:xr-xml-map "mpls_lcac:AutoroutedTunnelsCount";
      type uint16;
      description
        "The number of tunnels that are announced as
        shortcuts";
    }
    leaf forwarding-adjacency-tunnels-count {
      xr:xr-xml-map "mpls_lcac:ForwardingAdjacencyTunnelsCount";
      type uint16;
      description
        "The number of tunnels that are announced as
        forwarding adjacencies";
    }
    leaf area-format {
      xr:xr-xml-map "mpls_lcac:AreaFormat";
      type Igp-ospf-area-format;
      description
        "The format for the area: IPv4 address or a
        positive integer";
    }

    list total-tunnel {
      description "Announced tunnels for this destination";
      uses MPLS-TE-AUTOROUTE-BAG;
    }
  }

  grouping MPLS-TE-TOPOLOGY-LINK-BW-STD-DETAIL {
    description "Detailed DSTE bandwidth information for a link";
    leaf-list topo-link-std-bw-allocated {
      xr:xr-xml-map "mpls_lcac:TopoLinkStdBWAllocated";
      type uint32;
      max-elements "8";
      description "Link's allocated bandwidth per class";
    }
    leaf-list topo-link-std-bw-available {
      xr:xr-xml-map "mpls_lcac:TopoLinkStdBWAvailable";
      type uint32;
      max-elements "8";
      description "Link's available bandwidth per class";
    }
  }

  grouping MPLS-TE-TOPOLOGY-LINK-BW-STD {
    description
      "IETF_standard bandwidth information for a link
      belonging to a node in the MPLS TE topology";

    container topo-link-std-bw-detail {
      description "Detailed bandwidth information for this link";
      uses MPLS-TE-TOPOLOGY-LINK-BW-STD-DETAIL;
    }
    leaf topo-link-std-bw-physical {
      xr:xr-xml-map "mpls_lcac:TopoLinkStdBWPhysical";
      type uint32;
      description "The link's physical bandwidth";
    }
    leaf topo-link-std-bw-res-max {
      xr:xr-xml-map "mpls_lcac:TopoLinkStdBWResMax";
      type uint32;
      description "The link's maximum reservable bandwidth";
    }
    leaf topo-link-std-bw-res-pool0 {
      xr:xr-xml-map "mpls_lcac:TopoLinkStdBWResPool0";
      type uint32;
      description "The link's reservable BC0 bandwidth";
    }
    leaf topo-link-std-bw-res-pool1 {
      xr:xr-xml-map "mpls_lcac:TopoLinkStdBWResPool1";
      type uint32;
      description "The link's reservable BC1 bandwidth";
    }
  }

  grouping MPLS-TE-TOPOLOGY-LINK-BW-PRESTD-DETAIL {
    description
      "Detailed pre-standard bandwidth information for a
      link";
    leaf-list topology-link-prestandard-bandwidth-allocated {
      xr:xr-xml-map "mpls_lcac:TopologyLinkPrestandardBandwidthAllo"+
        "cated";
      type uint32;
      max-elements "8";
      description
        "Link's allocated bandwidth at priority levels
        (priority 0 to priority 7)";
    }
    leaf-list topology-link-prestandard-bandwidth-available-global {
      xr:xr-xml-map "mpls_lcac:TopologyLinkPrestandardBandwidthAvai"+
        "lableGlobal";
      type uint32;
      max-elements "8";
      description
        "Link's available global-pool bandwidth at
        priority levels (priority 0 to priority 7)";
    }
    leaf-list topology-link-prestandard-bandwidth-available-subpool {
      xr:xr-xml-map "mpls_lcac:TopologyLinkPrestandardBandwidthAvai"+
        "lableSubpool";
      type uint32;
      max-elements "8";
      description
        "Link's available sub-pool bandwidth at priority
        levels (priority 0 to priority 7)";
    }
  }

  grouping MPLS-TE-TOPOLOGY-LINK-BW-PRESTD {
    description
      "Pre-standard bandwidth information for a link
      belonging to a node in the MPLS TE topology";

    container topology-link-prestandard-bandwidth-detail {
      description "Detailed bandwidth information for this link";
      uses MPLS-TE-TOPOLOGY-LINK-BW-PRESTD-DETAIL;
    }
    leaf topology-link-prestandard-bandwidth-physical {
      xr:xr-xml-map "mpls_lcac:TopologyLinkPrestandardBandwidthPhys"+
        "ical";
      type uint32;
      description "The link's physical bandwidth";
    }
    leaf topology-link-prestandard-bandwidth-reservation-global {
      xr:xr-xml-map "mpls_lcac:TopologyLinkPrestandardBandwidthRese"+
        "rvationGlobal";
      type uint32;
      description "The link's reservable global bandwidth";
    }
    leaf topology-link-prestandard-bandwidth-reservation-subpool {
      xr:xr-xml-map "mpls_lcac:TopologyLinkPrestandardBandwidthRese"+
        "rvationSubpool";
      type uint32;
      description "The link's reservable subpool bandwidth";
    }
  }

  grouping MPLS-TE-TOPOLOGY-LINK-BW {
    description "Bandwidth information for a link";

    container topology-link-bandwidth-prestandard {
      when "../bandwidth-migration-mode ="+
        " 'rrr-dste-mode-prestandard'" {
          description
            "../BandwidthMigrationMode =
            'RRR_DSTEModePrestandard'";
      }
      description
        "Pre-standard bandwidth information for this link";
      uses MPLS-TE-TOPOLOGY-LINK-BW-PRESTD;
    }

    container topology-link-bandwidth-standard {
      when "../bandwidth-migration-mode ="+
        " 'rrr-dste-mode-standard'" {
          description
            "../BandwidthMigrationMode =
            'RRR_DSTEModeStandard'";
      }
      description
        "IETF-standard bandwidth information for this
        link";
      uses MPLS-TE-TOPOLOGY-LINK-BW-STD;
    }
    leaf bandwidth-migration-mode {
      xr:xr-xml-map "mpls_lcac:BandwidthMigrationMode";
      type Rrr-dste-migration-mode;
      description "BandwidthMigrationMode";
    }
  }

  grouping MPLS-TE-TOPOLOGY-LINK {
    description
      "A link belonging to a node in the MPLS TE
      topology";

    container topology-link-bandwidth {
      description "Bandwidth information for this link";
      uses MPLS-TE-TOPOLOGY-LINK-BW;
    }

    container odu-link-capabilities {
      description "ODU Link Capabilities";
      uses ODU-LINK-CAPABILITIES;
    }
    leaf topology-link-type {
      xr:xr-xml-map "mpls_lcac:TopologyLinkType";
      type Igp-subnet;
      description "Link type";
    }
    leaf topology-link-interface-address {
      xr:xr-xml-map "mpls_lcac:TopologyLinkInterfaceAddress";
      type inet:ipv4-address;
      description "Link's local interface address";
    }
    leaf topology-link-interface-id {
      xr:xr-xml-map "mpls_lcac:TopologyLinkInterfaceID";
      type uint32;
      description "Link's local interface ID";
    }
    leaf topology-link-neighbor-address {
      xr:xr-xml-map "mpls_lcac:TopologyLinkNeighborAddress";
      type inet:ipv4-address;
      description "Link's neighbor interface address";
    }
    leaf topology-link-neighbor-id {
      xr:xr-xml-map "mpls_lcac:TopologyLinkNeighborID";
      type uint32;
      description "Link's neighbor interface ID";
    }
    leaf topology-link-neighbor-system-id {
      xr:xr-xml-map "mpls_lcac:TopologyLinkNeighborSystemID";
      type string;
      description "System id of neighbor";
    }
    leaf topology-link-neighbor-node-id {
      xr:xr-xml-map "mpls_lcac:TopologyLinkNeighborNodeID";
      type uint32;
      description "Node id of neighbor";
    }
    leaf topology-link-neighbor-generation {
      xr:xr-xml-map "mpls_lcac:TopologyLinkNeighborGeneration";
      type uint32;
      description "Neighbor's link version counter";
    }
    leaf topology-link-fragment-id {
      xr:xr-xml-map "mpls_lcac:TopologyLinkFragmentID";
      type uint32;
      description "Neighbor's link version counter";
    }
    leaf topology-link-te-metric {
      xr:xr-xml-map "mpls_lcac:TopologyLinkTEMetric";
      type uint32;
      description "The link's TE metric";
    }
    leaf topology-link-igp-metric {
      xr:xr-xml-map "mpls_lcac:TopologyLinkIGPMetric";
      type uint32;
      description "The link's IGP metric";
    }
    leaf topology-link-uni-delay {
      xr:xr-xml-map "mpls_lcac:TopologyLinkUniDelay";
      type uint32;
      description "Unidirectional Link Delay in micro-sec";
    }
    leaf topology-link-affinity-bits {
      xr:xr-xml-map "mpls_lcac:TopologyLinkAffinityBits";
      type uint32;
      description "Deprecated";
    }
    leaf topology-link-switching-capability {
      xr:xr-xml-map "mpls_lcac:TopologyLinkSwitchingCapability";
      type uint8;
      description "The link's switching capability";
    }
    leaf topology-link-encoding {
      xr:xr-xml-map "mpls_lcac:TopologyLinkEncoding";
      type uint8;
      description "The link's encoding";
    }
    leaf topology-link-bandwidth-model {
      xr:xr-xml-map "mpls_lcac:TopologyLinkBandwidthModel";
      type Igpte-lib-bw-model;
      description "The link's topology bandwidth model";
    }
    leaf-list topology-link-extended-affinity-bit {
      xr:xr-xml-map "mpls_lcac:TopologyLinkExtendedAffinityBits";
      type uint32;
      description "The link's affinity bits (colors)";
    }

    list shared-risk-link-group {
      description "The link's shared risk link groups";
      uses MPLS-SRLG-INFO;
    }

    list adjacency-sid {
      description "Adjacency SIDs assigned for adjacency nodes";
      uses TE-SR-ADJ-SID;
    }
  }

  grouping MPLS-TE-TOPOLOGY-NODE {
    description "A node in the MPLS TE topology";

    container topology-node-sid-and-srbg {
      description "This node's SID and SRBG information";
      uses TE-SR-NODE-INFO;
    }
    leaf topology-node-te-router-id {
      xr:xr-xml-map "mpls_lcac:TopologyNodeTERouterID";
      type inet:ipv4-address;
      description
        "The node's TE router-id. Not set for network
        nodes";
    }
    leaf topology-node-overloaded {
      xr:xr-xml-map "mpls_lcac:TopologyNodeOverloaded";
      type boolean;
      description
        "Flag to indicate whether this node is overloaded";
    }

    list topology-node-link {
      description "This node's link information";
      uses MPLS-TE-TOPOLOGY-LINK;
    }
  }

  grouping NODE-ID {
    description "NODE ID";
    leaf node-id {
      xr:xr-xml-map "mpls_lcac:NodeID";
      type string;
      description "Node Identifier";
    }
  }

  grouping TE-SR-BACKUP-PATH {
    description "Segment-Routing backup path";
    leaf outgoing-interface {
      xr:xr-xml-map "mpls_lcac:OutgoingInterface";
      type string;
      description "Outgoing Interface Name";
    }
    leaf next-hop {
      xr:xr-xml-map "mpls_lcac:NextHop";
      type inet:ipv4-address;
      description "Next hop";
    }
    leaf-list outgoing-labels-stack {
      xr:xr-xml-map "mpls_lcac:OutgoingLabelsStack";
      type uint32;
      description "Outgoing Labels Stack";
    }
  }

  grouping TE-SR-PRIMARY-PATH {
    description "Segment-Routing primary path";
    leaf outgoing-interface {
      xr:xr-xml-map "mpls_lcac:OutgoingInterface";
      type string;
      description "Outgoing Interface Name";
    }
    leaf outgoing-label {
      xr:xr-xml-map "mpls_lcac:OutgoingLabel";
      type uint32;
      description "Outgoing Label";
    }
    leaf next-hop {
      xr:xr-xml-map "mpls_lcac:NextHop";
      type inet:ipv4-address;
      description "Next hop";
    }
    leaf path-id {
      xr:xr-xml-map "mpls_lcac:path_id";
      type uint32;
      description "Path Identifier";
    }
    leaf backup-path-id {
      xr:xr-xml-map "mpls_lcac:backup_path_id";
      type uint32;
      description "Backup Path Identifier";
    }
  }

  grouping TE-SR-PATH {
    description "Segment-Routing path";

    container primary-path {
      description "Primary Segment-Routing Path";
      uses TE-SR-PRIMARY-PATH;
    }

    container backup-path {
      description "Backup Segment-Routing Path";
      uses TE-SR-BACKUP-PATH;
    }
    leaf has-backup-path {
      xr:xr-xml-map "mpls_lcac:HasBackupPath";
      type boolean;
      description "Backup Path is available";
    }
  }

  grouping TE-SR-PREFIX {
    description "MPLS TE Segment-Routing Prefix information";

    container igp-area {
      description "An IGP area where the prefix belongs to";
      uses TE-SR-IGP-AREA;
    }
    leaf prefix-xr {
      xr:xr-xml-map "mpls_lcac:prefix-xr";
      type inet:ipv4-address;
      description "Prefix";
    }
    leaf prefix-length-xr {
      xr:xr-xml-map "mpls_lcac:prefix-length-xr";
      type uint8;
      description "Length of the prefix";
    }
    leaf prefix-sid {
      xr:xr-xml-map "mpls_lcac:PrefixSID";
      type uint32;
      description "Segment-Routing prefix SID";
    }
    leaf flag-r {
      xr:xr-xml-map "mpls_lcac:Flag_R";
      type boolean;
      description "Prefix-SID subTLV R-flag";
    }
    leaf flag-n {
      xr:xr-xml-map "mpls_lcac:Flag_N";
      type boolean;
      description "Prefix-SID subTLV N-flag";
    }
    leaf flag-p {
      xr:xr-xml-map "mpls_lcac:Flag_P";
      type boolean;
      description "Prefix-SID subTLV P-flag";
    }
    leaf flag-e {
      xr:xr-xml-map "mpls_lcac:Flag_E";
      type boolean;
      description "Prefix-SID subTLV E-flag";
    }
    leaf flag-v {
      xr:xr-xml-map "mpls_lcac:Flag_V";
      type boolean;
      description "Prefix-SID subTLV V-flag";
    }
    leaf flag-l {
      xr:xr-xml-map "mpls_lcac:Flag_L";
      type boolean;
      description "Prefix-SID subTLV L-flag";
    }

    list sr-path {
      description "Segment-Routing paths to prefix";
      uses TE-SR-PATH;
    }

    list advertizing-node {
      description "Advertizing nodes";
      uses NODE-ID;
    }
  }

  grouping TE-SR-ADJ-SID {
    description "A link's Segment-Routing Adjacency information";
    leaf adjacency-sid {
      xr:xr-xml-map "mpls_lcac:AdjacencySID";
      type uint32;
      description
        "The adjacency SID assigned for the topology node";
    }
    leaf link-type {
      xr:xr-xml-map "mpls_lcac:LinkType";
      type Igp-subnet;
      description "Link Type";
    }
    leaf local-addr {
      xr:xr-xml-map "mpls_lcac:LocalAddr";
      type inet:ipv4-address;
      description "Local Address";
    }
    leaf remote-addr {
      xr:xr-xml-map "mpls_lcac:RemoteAddr";
      type inet:ipv4-address;
      description "Remote Address";
    }
    leaf nbr-node-igpid {
      xr:xr-xml-map "mpls_lcac:NbrNodeIGPID";
      type string;
      description "The neighbor node's IGP ID";
    }
    leaf nbr-node-te-router-id {
      xr:xr-xml-map "mpls_lcac:NbrNodeTERouterID";
      type inet:ipv4-address;
      description "The neigbor node's TE router-id";
    }
    leaf flag-f {
      xr:xr-xml-map "mpls_lcac:Flag_F";
      type boolean;
      description "IGP Flag F";
    }
    leaf flag-b {
      xr:xr-xml-map "mpls_lcac:Flag_B";
      type boolean;
      description "IGP Flag B";
    }
    leaf flag-v {
      xr:xr-xml-map "mpls_lcac:Flag_V";
      type boolean;
      description "IGP Flag V";
    }
    leaf flag-l {
      xr:xr-xml-map "mpls_lcac:Flag_L";
      type boolean;
      description "IGP Flag L";
    }
    leaf flag-s {
      xr:xr-xml-map "mpls_lcac:Flag_S";
      type boolean;
      description "IGP Flag S";
    }
  }

  grouping TE-SR-NODE-INFO {
    description "MPLS TE Node's Segment-Routing Information";
    leaf segment-id {
      xr:xr-xml-map "mpls_lcac:SegmentID";
      type uint32;
      description "Segment-Routing Node-SID";
    }
    leaf segment-id-local-absolute-value {
      xr:xr-xml-map "mpls_lcac:SegmentIDLocalAbsoluteValue";
      type uint32;
      description "Node-SID local absolute value";
    }
    leaf srgb-start {
      xr:xr-xml-map "mpls_lcac:SRGBStart";
      type uint32;
      description "Segment-Routring global block start value";
    }
    leaf srgb-size {
      xr:xr-xml-map "mpls_lcac:SRGBSize";
      type uint32;
      description "Segment-Routing global block size";
    }
  }

  grouping TE-SR-NODE {
    description "MPLS TE Segment-Routing Node topology information";

    container igp-area {
      description "IGP area which the SID belongs to";
      uses TE-SR-IGP-AREA;
    }

    container sr-node-info {
      description "Segment-Routing Node information";
      uses TE-SR-NODE-INFO;
    }
    leaf local-node-te-router-id {
      xr:xr-xml-map "mpls_lcac:LocalNodeTERouterID";
      type inet:ipv4-address;
      description "The local node's TE router-id";
    }
    leaf local-node-igp-id {
      xr:xr-xml-map "mpls_lcac:LocalNodeIGP_ID";
      type string;
      description "The local node's IGP id formatted as string";
    }

    list adjacency-sid {
      description
        "Array of adjacency SIDs locally assigned to
        adjacent nodes";
      uses TE-SR-ADJ-SID;
    }
  }

  grouping TE-SR-IGP-AREA {
    description "A IGP area information for Segment-Routing";
    leaf segment-routing-enabled {
      xr:xr-xml-map "mpls_lcac:SegmentRoutingEnabled";
      type boolean;
      description
        "True if the Segment-Routing is enabled in this
        area";
    }
    leaf igp-type {
      xr:xr-xml-map "mpls_lcac:IGPType";
      type Igp-protocol;
      description "IGP type";
    }
    leaf igp-instance-xr {
      xr:xr-xml-map "mpls_lcac:igp-instance-xr";
      type string;
      description "IGP Instance name";
    }
    leaf igp-area {
      xr:xr-xml-map "mpls_lcac:IGPArea";
      type uint32;
      description "IGP Area ID";
    }
    leaf igp-area-format {
      xr:xr-xml-map "mpls_lcac:IGPAreaFormat";
      type Igp-ospf-area-format;
      description "IGP-area format";
    }
  }

  grouping MPLS-TE-TUNNEL-FLEX-INFO {
    description "TE Tunnel FlexLSP Information";
    leaf fault-ldi-lockout {
      xr:xr-xml-map "mpls_lcac:FaultLdiLockout";
      type boolean;
      description "Fault LDI Lockout";
    }
    leaf fault-ldi {
      xr:xr-xml-map "mpls_lcac:FaultLdi";
      type boolean;
      description "Fault LDI";
    }
    leaf fault-lkr {
      xr:xr-xml-map "mpls_lcac:FaultLkr";
      type boolean;
      description "Fault LKR";
    }
    leaf fault-ais {
      xr:xr-xml-map "mpls_lcac:FaultAis";
      type boolean;
      description "Fault AIS";
    }
    leaf fault-time {
      xr:xr-xml-map "mpls_lcac:FaultTime";
      type uint32;
      description "Fault Time";
    }
    leaf fault-in-label {
      xr:xr-xml-map "mpls_lcac:FaultInLabel";
      type uint32;
      description "Fault In Label";
    }
    leaf is-lockout {
      xr:xr-xml-map "mpls_lcac:IsLockout";
      type boolean;
      description "Lockout Status";
    }
    leaf lockout-timestamp {
      xr:xr-xml-map "mpls_lcac:LockoutTimestamp";
      type uint32;
      description "The timestamp when the lockout is set";
    }
    leaf lockout-lsp-id {
      xr:xr-xml-map "mpls_lcac:LockoutLSP_ID";
      type uint16;
      description "The LSP ID of the locked out LSP";
    }
  }

  grouping TE-VIF-CONVERGENCE-INFO {
    description "TE tunnel convergence related information";

    container convergence-lsp {
      description "TE LSP convergence related information";
      uses TE-LSP-CONVERGENCE-INFO;
    }
    leaf is-convergence-in-progress {
      xr:xr-xml-map "mpls_lcac:IsConvergenceInProgress";
      type boolean;
      description "TE convergence in progress";
    }
    leaf frr-trigger-time {
      xr:xr-xml-map "mpls_lcac:FRRTriggerTime";
      type uint64;
      description "FRR trigger time";
    }
    leaf pcalc-complete-time {
      xr:xr-xml-map "mpls_lcac:PCALCCompleteTime";
      type uint64;
      units "nanosecond";
      description
        "Path computation completion timestamp (clocktime
        in nsecs)";
    }
    leaf convergence-complete-time {
      xr:xr-xml-map "mpls_lcac:ConvergenceCompleteTime";
      type uint64;
      description "TE convergence completion time";
    }
  }

  grouping MPLS-TE-TUNNELS-REVERSE-ERO-ERROR-BAG {
    description "MPLS TE Tunnel Reverse ERO Error Information";
    leaf reverse-lsp-id {
      xr:xr-xml-map "mpls_lcac:ReverseLSP_ID";
      type uint16;
      description "Reverse LSP ID";
    }
    leaf path-reject-reason-bw {
      xr:xr-xml-map "mpls_lcac:PathRejectReasonBW";
      type boolean;
      description "Path Reject due to bw";
    }
    leaf path-reject-reason-affinity {
      xr:xr-xml-map "mpls_lcac:PathRejectReasonAffinity";
      type boolean;
      description "Path Reject due to affinity";
    }
    leaf path-reject-reason-ip-addr {
      xr:xr-xml-map "mpls_lcac:PathRejectReasonIPAddr";
      type boolean;
      description "Path Reject due to IP address";
    }
    leaf path-reject-reason-reverse-link {
      xr:xr-xml-map "mpls_lcac:PathRejectReasonReverseLink";
      type boolean;
      description "Path Reject due to reverse link";
    }
    leaf path-reject-reason-ixcd {
      xr:xr-xml-map "mpls_lcac:PathRejectReasonIXCD";
      type boolean;
      description "Path Reject due to IXCD";
    }
    leaf path-reject-reason-holddown {
      xr:xr-xml-map "mpls_lcac:PathRejectReasonHolddown";
      type boolean;
      description "Path Reject due to holddown";
    }
    leaf path-reject-reason-exclude-node {
      xr:xr-xml-map "mpls_lcac:PathRejectReasonExcludeNode";
      type boolean;
      description "Path Reject due to exclude node";
    }
    leaf path-reject-reason-exclude-link {
      xr:xr-xml-map "mpls_lcac:PathRejectReasonExcludeLink";
      type boolean;
      description "Path Reject due to exclude link";
    }
    leaf path-reject-reason-exclude-srlg {
      xr:xr-xml-map "mpls_lcac:PathRejectReasonExcludeSRLG";
      type boolean;
      description "Path Reject due to exclude SRLG";
    }
    leaf path-reject-reason-hop-limit {
      xr:xr-xml-map "mpls_lcac:PathRejectReasonHopLimit";
      type boolean;
      description "Path Reject due to hop limit";
    }
    leaf path-reject-reason-node-ol-unknown {
      xr:xr-xml-map "mpls_lcac:PathRejectReasonNodeOLUnknown";
      type boolean;
      description "Path Reject due to unknown node overload";
    }
    leaf path-reject-reason-node-ol-head {
      xr:xr-xml-map "mpls_lcac:PathRejectReasonNodeOLHead";
      type boolean;
      description "Path Reject due to head node overload";
    }
    leaf path-reject-reason-node-ol-mid {
      xr:xr-xml-map "mpls_lcac:PathRejectReasonNodeOLMid";
      type boolean;
      description "Path Reject due to mid node overload";
    }
    leaf path-reject-reason-node-ol-tail {
      xr:xr-xml-map "mpls_lcac:PathRejectReasonNodeOLTail";
      type boolean;
      description "Path Reject due to head node overload";
    }
    leaf path-reject-reason-reverse-bw {
      xr:xr-xml-map "mpls_lcac:PathRejectReasonReverseBW";
      type boolean;
      description "Path Reject due to reverse bw";
    }
    leaf path-reject-reason-node-unreachable {
      xr:xr-xml-map "mpls_lcac:PathRejectReasonNodeUnreachable";
      type boolean;
      description "Path Reject due to unreachable node";
    }
    leaf path-option-index {
      xr:xr-xml-map "mpls_lcac:PathOptionIndex";
      type uint16;
      description "Path Option Index";
    }
    leaf path-option-type {
      xr:xr-xml-map "mpls_lcac:PathOptionType";
      type Mte-path-option;
      description "Path Option Type";
    }
    leaf ero-reject-reason {
      xr:xr-xml-map "mpls_lcac:ERORejectReason";
      type Te-rev-ero-reject-reasons;
      description "Reverse ERO Reject Reason";
    }

    list path-calculation-error {
      description "Path Computation Information";
      uses MPLS-TE-P2MP-PCALC-ERROR;
    }
  }

  grouping MPLS-TE-TUNNEL-BIDIR-INFO {
    description "MPLS TE Tunnel Bidir Information";

    container reverse-ero-error-current {
      description "Reverse ERO Error Current LSP";
      uses MPLS-TE-TUNNELS-REVERSE-ERO-ERROR-BAG;
    }

    container reverse-ero-error-reopt {
      description "Reverse ERO Error Reopt LSP";
      uses MPLS-TE-TUNNELS-REVERSE-ERO-ERROR-BAG;
    }

    container reverse-ero-error-standby {
      description "Reverse ERO Error Standby LSP";
      uses MPLS-TE-TUNNELS-REVERSE-ERO-ERROR-BAG;
    }

    container reverse-ero-error-standby-reopt {
      description "Reverse ERO Error Standby Reopt LSP";
      uses MPLS-TE-TUNNELS-REVERSE-ERO-ERROR-BAG;
    }
    leaf reverse-bandwidth {
      xr:xr-xml-map "mpls_lcac:ReverseBandwidth";
      type uint32;
      units "kbit/s";
      description "Reverse Bandwidth value in kbps";
    }
    leaf reverse-bandwidth-standby {
      xr:xr-xml-map "mpls_lcac:ReverseBandwidthStandby";
      type uint32;
      units "kbit/s";
      description "Reverse Bandwidth value for standby in kbps";
    }
  }

  grouping MPLS-TE-TUNNEL-RESTORATION-INFO {
    description "Restoration info of tunnel";
    leaf revert-option {
      xr:xr-xml-map "mpls_lcac:RevertOption";
      type Te-pnr-revert-options;
      description "Revertive or non-revertive";
    }
    leaf diverse-lsp {
      xr:xr-xml-map "mpls_lcac:DiverseLSP";
      type Mpls-te-lsp-mode;
      description "LSP from which restoration LSP is DIVERSED";
    }
    leaf diversity-type {
      xr:xr-xml-map "mpls_lcac:DiversityType";
      type Te-pp-diversity;
      description "Restoration path diversity type";
    }
  }

  grouping MPLS-TE-TUNNEL-APS-INFO {
    description "APS Protection Info of tunnel";

    container protection-profile {
      description "Protection Profile Information of tunnel";
      uses MPLS-TE-ATTRIBUTE-SET-APS-PP;
    }
    leaf active-lsp {
      xr:xr-xml-map "mpls_lcac:ActiveLSP";
      type Mpls-te-lsp-mode;
      description "Active LSP for Incoming Data";
    }
    leaf diversity-type {
      xr:xr-xml-map "mpls_lcac:DiversityType";
      type Te-pp-diversity;
      description "Standby path diversity type";
    }
  }

  grouping MPLS-TE-TUNNEL-OTN-BIDIR-INFO {
    description "Bidirectional Tunnel Information";

    container aps {
      description "APS Protection Info";
      uses MPLS-TE-TUNNEL-APS-INFO;
    }

    container restoration {
      description "Restoration Info";
      uses MPLS-TE-TUNNEL-RESTORATION-INFO;
    }
  }

  grouping MPLS-TE-PATH-OPTION-DAMPENING-INFO {
    description "MPLS TE Path Option Dampening Information";
    leaf option-index {
      xr:xr-xml-map "mpls_lcac:OptionIndex";
      type uint32;
      description "Path option index";
    }
    leaf hold-down-time {
      xr:xr-xml-map "mpls_lcac:HoldDownTime";
      type uint32;
      description "Hold down time in second";
    }
    leaf remained-time {
      xr:xr-xml-map "mpls_lcac:RemainedTime";
      type uint32;
      description "Remained time to resignal in second";
    }
    leaf backoff-count {
      xr:xr-xml-map "mpls_lcac:BackoffCount";
      type uint32;
      description "Backoff count";
    }
  }

  grouping MPLS-TE-TUNNEL-BFD-INFO {
    description "MPLS TE Tunnel BFD Session Information";

    container event-counters {
      description "Per tunnel BFD session event counters";
      uses MPLS-TE-BFD-LSP-COUNTERS;
    }
    leaf bfd-session-up {
      xr:xr-xml-map "mpls_lcac:BFDSessionUp";
      type boolean;
      description "Tunnel BFD session state up or down";
    }
    leaf session-up-time {
      xr:xr-xml-map "mpls_lcac:SessionUpTime";
      type uint32;
      units "second";
      description "Time in seconds since the last session state up";
    }
    leaf failure-diagnostic-code {
      xr:xr-xml-map "mpls_lcac:FailureDiagnosticCode";
      type uint32;
      description "BFD session failure diagnostic code";
    }
    leaf failure-reason {
      xr:xr-xml-map "mpls_lcac:FailureReason";
      type string;
      description "BFD session failure reason";
    }
    leaf minimum-session-up-interval {
      xr:xr-xml-map "mpls_lcac:MinimumSessionUpInterval";
      type uint32;
      description
        "Minimum time in mini second for session to come
        up";
    }
    leaf maximum-session-up-interval {
      xr:xr-xml-map "mpls_lcac:MaximumSessionUpInterval";
      type uint32;
      description
        "Maximum time in mini second for session to come
        up";
    }

    list dampening-info {
      description "Path option dampening info";
      uses MPLS-TE-PATH-OPTION-DAMPENING-INFO;
    }
  }

  grouping MPLS-TE-TUNNEL-VIF-DIVERSITY-INFO {
    description "Circuit diversity information";
    leaf tunnel-id {
      xr:xr-xml-map "mpls_lcac:TunnelID";
      type uint16;
      description "Dependent Tunnel ID";
    }
  }

  grouping MPLS-TE-TUNNEL-STATIC-UNI-INFO {
    description "static UNI info for both head and tail";
    leaf client-port {
      xr:xr-xml-map "mpls_lcac:ClientPort";
      type string;
      description "Ingress Client Port";
    }
    leaf client-if-handle {
      xr:xr-xml-map "mpls_lcac:ClientIfHandle";
      type xr:Interface-name;
      description "Ingress Client Port Ifhandle";
    }
    leaf client-odu-name {
      xr:xr-xml-map "mpls_lcac:ClientOduName";
      type string;
      description "Client Odu Name";
    }
    leaf client-odu-if-handle {
      xr:xr-xml-map "mpls_lcac:ClientOduIfHandle";
      type xr:Interface-name;
      description "Client Odu Interface";
    }
    leaf cross-connect-id {
      xr:xr-xml-map "mpls_lcac:CrossConnectID";
      type uint32;
      description "Cross connect id";
    }
    leaf is-connected {
      xr:xr-xml-map "mpls_lcac:IsConnected";
      type boolean;
      description "True if client port is connected";
    }
    leaf uptime {
      xr:xr-xml-map "mpls_lcac:Uptime";
      type uint32;
      description "Client Port Uptime";
    }
    leaf local-termination {
      xr:xr-xml-map "mpls_lcac:LocalTermination";
      type Mpls-te-termination;
      description "Local Termination Type";
    }
    leaf static-uni-type {
      xr:xr-xml-map "mpls_lcac:StaticUniType";
      type Mpls-te-uni;
      description "Static uni type";
    }
    leaf term-client-port {
      xr:xr-xml-map "mpls_lcac:TermClientPort";
      type string;
      description "Termination Ingress Client Port";
    }
    leaf term-client-if-handle {
      xr:xr-xml-map "mpls_lcac:TermClientIfHandle";
      type xr:Interface-name;
      description "Termination Ingress Client Port Ifhandle";
    }
  }

  grouping MPLS-TE-TUNNEL-OTN-INFO {
    description "OTN tunnel's OTN technology information";

    container bandwidth-cfg {
      description "Configured OTN Bandwidth for tunnel";
      uses TE-ODU-V3-BW;
    }
  }

  grouping MPLS-TE-TRANSPORT-TUNNEL-INFO {
    description "Transport Tunnel information";

    container otn {
      description "Info Related to OTN technology in S2L";
      uses MPLS-TE-TUNNEL-OTN-INFO;
    }

    container static-uni {
      description "Tunnel Static UNI Info";
      uses MPLS-TE-TUNNEL-STATIC-UNI-INFO;
    }

    container egress-static-uni {
      description "Tunnel EgressStatic UNI Info";
      uses MPLS-TE-TUNNEL-EGRESS-STATIC-UNI-INFO;
    }
    leaf status-homepath-working {
      xr:xr-xml-map "mpls_lcac:StatusHomepathWorking";
      type boolean;
      description "Status of working homepath";
    }

    list homepath-ero {
      description "Homepath ero for working lsp";
      uses RSVP-MGMT-ERO-SUBOBJ;
    }

    list diversity-info {
      description "Diversity Info";
      uses MPLS-TE-TUNNEL-VIF-DIVERSITY-INFO;
    }
  }

  grouping MPLS-TE-MGMT-WDM-UNI-TUNNEL-INFO {
    description "GMPLS WDM-UNI tunnel information";
    leaf tunnel-state {
      xr:xr-xml-map "mpls_lcac:TunnelState";
      type Mpls-te-tunnel-state;
      description "Tunnel state";
    }
    leaf tunnel-role {
      xr:xr-xml-map "mpls_lcac:TunnelRole";
      type Mpls-te-tunnel-role;
      description "Tunnel Role";
    }
    leaf tunnel-id {
      xr:xr-xml-map "mpls_lcac:TunnelID";
      type uint16;
      description "Tunnel ID";
    }
    leaf lsp-id {
      xr:xr-xml-map "mpls_lcac:LSP_ID";
      type uint16;
      description "LSP ID";
    }
    leaf local-optical-router-id {
      xr:xr-xml-map "mpls_lcac:LocalOpticalRouterID";
      type inet:ipv4-address;
      description "Local optical router id";
    }
    leaf remote-optical-router-id {
      xr:xr-xml-map "mpls_lcac:RemoteOpticalRouterID";
      type inet:ipv4-address;
      description "Remote optical router id";
    }
    leaf controlled-interface {
      xr:xr-xml-map "mpls_lcac:ControlledInterface";
      type string;
      description "Interface being controlled";
    }
    leaf source-address {
      xr:xr-xml-map "mpls_lcac:SourceAddress";
      type inet:ipv4-address;
      description "Source address";
    }
    leaf destination-address {
      xr:xr-xml-map "mpls_lcac:DestinationAddress";
      type inet:ipv4-address;
      description "Destination address";
    }
    leaf extended-tunnel-id {
      xr:xr-xml-map "mpls_lcac:ExtendedTunnelID";
      type inet:ipv4-address;
      description "Extended tunnel-id";
    }
    leaf label-origin {
      xr:xr-xml-map "mpls_lcac:LabelOrigin";
      type Mpls-te-mgmt-gmpls-label-origin;
      description "Label origin";
    }
    leaf srlg-discovery {
      xr:xr-xml-map "mpls_lcac:SRLGDiscovery";
      type boolean;
      description "SRLG-discovery enabled";
    }
  }

  grouping MPLS-TE-SOFT-PREEMPTION-HEAD-COUNTERS {
    description "Headend Soft Preemption Counters";
    leaf soft-preemption-events {
      xr:xr-xml-map "mpls_lcac:SoftPreemptionEvents";
      type uint32;
      description "The number of soft preemption events";
    }
    leaf reopt-completed-ls-ps {
      xr:xr-xml-map "mpls_lcac:ReoptCompletedLSPs";
      type uint32;
      description
        "The number of soft preempted LSPs that were torn
        down by the ingress router after the reopt LSP
        was successfully setup.";
    }
    leaf torn-down-ls-ps {
      xr:xr-xml-map "mpls_lcac:TornDownLSPs";
      type uint32;
      description
        "The number of soft preempted LSPs that were torn
        down by the              headend or any remote
        node before the reoptimization is done.";
    }
    leaf path-protection-switchover-ls-ps {
      xr:xr-xml-map "mpls_lcac:PathProtectionSwitchoverLSPs";
      type uint32;
      description
        "The number of soft preempted LSPs that were
        switched over to a             standby LSP.";
    }
    leaf frr-triggered-ls-ps {
      xr:xr-xml-map "mpls_lcac:FRRTriggeredLSPs";
      type uint32;
      description
        "The number of soft preempted LSPs that were fast
        rerouted at the             headend or any
        remote node before the reoptimization is done.";
    }
    leaf time-in-preemption-pending-min {
      xr:xr-xml-map "mpls_lcac:TimeInPreemptionPendingMin";
      type uint16;
      units "second";
      description
        "The minimum time in seconds that an LSP was in
        preemption pending state";
    }
    leaf time-in-preemption-pending-max {
      xr:xr-xml-map "mpls_lcac:TimeInPreemptionPendingMax";
      type uint16;
      units "second";
      description
        "The maximum time in seconds that an LSP was in
        preemption pending state";
    }
    leaf time-in-preemption-pending-avg {
      xr:xr-xml-map "mpls_lcac:TimeInPreemptionPendingAvg";
      type uint16;
      units "second";
      description
        "The average time in seconds that an LSP was in
        preemption pending state";
    }
  }

  grouping MPLS-TE-SOFT-PREEMPTION-PATH-ERROR {
    description "Information for a soft preemption path error";
    leaf timestamp {
      xr:xr-xml-map "mpls_lcac:Timestamp";
      type uint32;
      description
        "The POSIX timestamp when the soft preemption
        error is received";
    }
    leaf preempting-link-address {
      xr:xr-xml-map "mpls_lcac:PreemptingLinkAddress";
      type inet:ipv4-address;
      description
        "The address of the link where the preemption
        happened";
    }
  }

  grouping MPLS-TE-SOFT-PREEMPTION-TUNNEL-INFO {
    description "Headend Soft Preemption Tunnel Info";

    container soft-preemption-counters {
      description
        "The soft preemption counters for this tunnel
        head";
      uses MPLS-TE-SOFT-PREEMPTION-HEAD-COUNTERS;
    }
    leaf status {
      xr:xr-xml-map "mpls_lcac:Status";
      type Mpls-te-soft-preemption-state;
      description "The preemption state";
    }
    leaf time-in-preemption-pending {
      xr:xr-xml-map "mpls_lcac:TimeInPreemptionPending";
      type uint16;
      units "second";
      description
        "The number of seconds that were spent in the
        preemption-pending state";
    }
    leaf preemption-pending-resolution {
      xr:xr-xml-map "mpls_lcac:PreemptionPendingResolution";
      type Mpls-te-soft-preemption-resolution;
      description
        "Indicates how the soft preemption operation
        ended";
    }

    list soft-preemption-path-error {
      description
        "The array of soft preemption path errors info
        received for the LSP that is being soft
        preempted";
      uses MPLS-TE-SOFT-PREEMPTION-PATH-ERROR;
    }
  }

  grouping MPLS-TE-PCE-DELEGATION-INFO {
    description "MPLS TE PCE Delegation Information";
    leaf plsp-id {
      xr:xr-xml-map "mpls_lcac:PLSP_ID";
      type uint32;
      description "PLSP ID";
    }
    leaf symbolic-name {
      xr:xr-xml-map "mpls_lcac:SymbolicName";
      type string;
      description "Symbolic name";
    }
    leaf owner-address {
      xr:xr-xml-map "mpls_lcac:OwnerAddress";
      type inet:ipv4-address;
      description "Address of owner node";
    }
    leaf operationally-up {
      xr:xr-xml-map "mpls_lcac:OperationallyUp";
      type boolean;
      description "Operationally up";
    }
  }

  grouping MPLS-TE-AUTOPCC-INFO {
    description "MPLS TE Auto-PCC Information";
    leaf owner-address {
      xr:xr-xml-map "mpls_lcac:OwnerAddress";
      type inet:ipv4-address;
      description "Address of owner node";
    }
    leaf creator-address {
      xr:xr-xml-map "mpls_lcac:CreatorAddress";
      type inet:ipv4-address;
      description "Address of creating node";
    }
    leaf has-creator-id {
      xr:xr-xml-map "mpls_lcac:HasCreatorID";
      type boolean;
      description "Indicates if the ID of the creating node is set";
    }
    leaf creator-id {
      xr:xr-xml-map "mpls_lcac:CreatorID";
      type string;
      description "ID of creating node";
    }
    leaf plspid {
      xr:xr-xml-map "mpls_lcac:PLSPID";
      type uint32;
      description "PLSP ID";
    }
    leaf symbolic-name {
      xr:xr-xml-map "mpls_lcac:SymbolicName";
      type string;
      description "Symbolic name";
    }
    leaf operationally-up {
      xr:xr-xml-map "mpls_lcac:OperationallyUp";
      type boolean;
      description "Operationally up";
    }
  }

  grouping MPLS-TE-AUTOMESH-INFO {
    description "MPLS TE Automesh Information";
    leaf mesh-group-id {
      xr:xr-xml-map "mpls_lcac:MeshGroupID";
      type uint32;
      description "Auto-mesh tunnel Mesh Group ID";
    }
    leaf tunnel-destination-list-name {
      xr:xr-xml-map "mpls_lcac:TunnelDestinationListName";
      type string;
      description "Destination List name";
    }
    leaf is-tunnel-unused-timer-running {
      xr:xr-xml-map "mpls_lcac:IsTunnelUnusedTimerRunning";
      type boolean;
      description "Flag to indicate whether unused timer running";
    }
    leaf remaining-unused-time {
      xr:xr-xml-map "mpls_lcac:RemainingUnusedTime";
      type uint32;
      units "second";
      description "Remaining time for unused timer in seconds";
    }
    leaf mesh-group-type {
      xr:xr-xml-map "mpls_lcac:MeshGroupType";
      type Te-meshgroup;
      description "Auto-tunnel mesh group type";
    }
  }

  grouping MPLS-TE-IEP-HOP-BAG {
    description "MPLS IEP Hop information";
    leaf hop-index {
      xr:xr-xml-map "mpls_lcac:HopIndex";
      type uint32;
      description "Hop Index";
    }
    leaf iep-hop-type {
      xr:xr-xml-map "mpls_lcac:IEPHopType";
      type Mpls-te-iep-hop;
      description "IEP type";
    }
    leaf iep-hop-address {
      xr:xr-xml-map "mpls_lcac:IEPHopAddress";
      type inet:ipv4-address;
      description "IEP Hop Address";
    }
  }

  grouping MPLS-TE-IEP-BAG {
    description "MPLS TE IEP";
    leaf path-option-id {
      xr:xr-xml-map "mpls_lcac:PathOptionID";
      type uint32;
      description "Path option ID this IEP is associated with";
    }

    list iep-hop {
      description "IEP Hop List";
      uses MPLS-TE-IEP-HOP-BAG;
    }
  }

  grouping MPLS-TE-WSRLG-HOP-BAG {
    description
      "Weighted SRLG info for a hop of the autobackup
      tunnel";
    leaf from-address {
      xr:xr-xml-map "mpls_lcac:FromAddress";
      type inet:ipv4-address;
      description "Local IP address";
    }
    leaf to-address {
      xr:xr-xml-map "mpls_lcac:ToAddress";
      type inet:ipv4-address;
      description "Remote IP address";
    }
    leaf aggregate-admin-weight {
      xr:xr-xml-map "mpls_lcac:AggregateAdminWeight";
      type uint64;
      description
        "Sum of the admin weights for all the common SRLG
        values";
    }
    leaf-list common-srlg {
      xr:xr-xml-map "mpls_lcac:CommonSRLG";
      type uint32;
      description
        "Common SRLG between this hop and the protected
        interface";
    }
  }

  grouping MPLS-TE-WSRLG-VALUE-BAG {
    description "MPLS TE weighted SRLGs";
    leaf srlg {
      xr:xr-xml-map "mpls_lcac:SRLG";
      type uint32;
      description "SRLG number";
    }
    leaf srlg-name {
      xr:xr-xml-map "mpls_lcac:SRLGName";
      type string;
      description "SRLG name";
    }
    leaf admin-weight {
      xr:xr-xml-map "mpls_lcac:AdminWeight";
      type uint32;
      description "Admin weight";
    }
  }

  grouping MPLS-TE-WSRLG-INFO-BAG {
    description
      "MPLS TE weighted SRLG information for the
      autobackup tunnels";

    list protected-interface-srlg {
      description
        "SRLG values and admin weight penalties of the
        protected interface";
      uses MPLS-TE-WSRLG-VALUE-BAG;
    }

    list weighted-srlg-hop {
      description
        "Autobackup hops and the common SRLG with the
        protected interface";
      uses MPLS-TE-WSRLG-HOP-BAG;
    }
  }

  grouping MPLS-TE-AUTOBACKUP-INFO {
    description "MPLS TE Autobackup Information";

    container weighted-srlg-info {
      description "Weighted SRLG info for the autobackup tunnel";
      uses MPLS-TE-WSRLG-INFO-BAG;
    }
    leaf protected-ls-ps {
      xr:xr-xml-map "mpls_lcac:ProtectedLSPs";
      type uint32;
      description "Number Of Protected LSPs";
    }
    leaf protected-s2-ls {
      xr:xr-xml-map "mpls_lcac:ProtectedS2Ls";
      type uint32;
      description "Number of Protected S2Ls";
    }
    leaf sharing-families {
      xr:xr-xml-map "mpls_lcac:SharingFamilies";
      type uint32;
      description "Number of S2L Sharing Families";
    }
    leaf ab-protection-type {
      xr:xr-xml-map "mpls_lcac:ABProtectionType";
      type Auto-backup-protection;
      description "Protection type";
    }
    leaf is-using-srlg {
      xr:xr-xml-map "mpls_lcac:IsUsingSRLG";
      type boolean;
      description "Indicates whether SRLG Path Option is in use";
    }
    leaf srlg-prot-type {
      xr:xr-xml-map "mpls_lcac:SRLGProtType";
      type Auto-backup-srlg-mode;
      description "SRLG Protection Type";
    }
    leaf ab-protected-interface {
      xr:xr-xml-map "mpls_lcac:ABProtectedInterface";
      type string;
      description "Protected Interface";
    }
    leaf protected-address {
      xr:xr-xml-map "mpls_lcac:ProtectedAddress";
      type inet:ipv4-address;
      description "Protected Address";
    }
    leaf tunnel-attribute-set-name {
      xr:xr-xml-map "mpls_lcac:TunnelAttributeSetName";
      type string;
      description "AttributeSet name";
    }
    leaf is-unused-removal-timer-running {
      xr:xr-xml-map "mpls_lcac:IsUnusedRemovalTimerRunning";
      type boolean;
      description
        "Indicates if the unused removal timer is running";
    }
    leaf unused-removal-remaining-time {
      xr:xr-xml-map "mpls_lcac:UnusedRemovalRemainingTime";
      type uint32;
      units "second";
      description
        "Time Remaining in Unused Removal Time in seconds";
    }

    list iep {
      description
        "List of IEPs for the path options on this tunnel";
      uses MPLS-TE-IEP-BAG;
    }
  }

  grouping TE-PP-SW-LOG-ENTRY-BAG {
    description "Path protection log entry";
    leaf path-protection-switchover-event-index {
      xr:xr-xml-map "mpls_lcac:PathProtectionSwitchoverEventIndex";
      type uint32;
      description
        "The index number of the path protection switch
        over event";
    }
    leaf path-protection-tunnel-id {
      xr:xr-xml-map "mpls_lcac:PathProtectionTunnelID";
      type uint16;
      description
        "The ID of the tunnel that experienced switchover";
    }
    leaf from-lsp-id {
      xr:xr-xml-map "mpls_lcac:FromLSP_ID";
      type uint16;
      description
        "The LSP ID from which the traffic was switched
        over";
    }
    leaf to-lsp-id {
      xr:xr-xml-map "mpls_lcac:ToLSP_ID";
      type uint16;
      description
        "The LSP ID to which the traffic was switched
        over";
    }
    leaf date-of-error-detection {
      xr:xr-xml-map "mpls_lcac:DateOfErrorDetection";
      type uint32;
      units "second";
      description
        "The date when the error that caused the
        switchover was detected. This date is the number
        of seconds since Jan 1st 1970";
    }
    leaf date-of-error-detection-millisec {
      xr:xr-xml-map "mpls_lcac:DateOfErrorDetectionMillisec";
      type uint32;
      units "millisecond";
      description
        "The milliseconds offset of the date when the
        error that caused  the switchover was detected.";
    }
    leaf switchover-duration-millisec {
      xr:xr-xml-map "mpls_lcac:SwitchoverDurationMillisec";
      type uint32;
      units "millisecond";
      description
        "The time in milliseconds between the detection
        of the error and switching the traffic";
    }
    leaf path-protection-switchover-reason {
      xr:xr-xml-map "mpls_lcac:PathProtectionSwitchoverReason";
      type Te-p2mp-s2l-deletion-subcause;
      description
        "The reason that caused the path protection
        switchover";
    }
  }

  grouping MPLS-TE-PP-INFO {
    description "MPLS TE Path Protected Switchover Information";

    container switchover {
      description "Path Protected Switchover Information";
      uses TE-PP-SW-LOG-ENTRY-BAG;
    }
    leaf time-of-switchover-sec {
      xr:xr-xml-map "mpls_lcac:TimeOfSwitchoverSec";
      type uint32;
      units "second";
      description
        "The date when the switchover was completed. This
        date is the number of seconds since Jan 1st 1970";
    }
    leaf switchover-total {
      xr:xr-xml-map "mpls_lcac:SwitchoverTotal";
      type uint16;
      description "Number of times switchover occurred";
    }
    leaf switchover-ready {
      xr:xr-xml-map "mpls_lcac:SwitchoverReady";
      type uint16;
      description "Total times, Standby LSP ready for use";
    }
    leaf standby-reoptimized-number {
      xr:xr-xml-map "mpls_lcac:StandbyReoptimizedNumber";
      type uint16;
      description "Number of times the standby LSP was reoptimized";
    }
    leaf switchover-reason {
      xr:xr-xml-map "mpls_lcac:SwitchoverReason";
      type uint16;
      description "Reason for last switchover";
    }
    leaf diversity-type {
      xr:xr-xml-map "mpls_lcac:DiversityType";
      type Te-pp-diversity;
      description "Standby path diversity type";
    }
    leaf is-path-protect-configured {
      xr:xr-xml-map "mpls_lcac:IsPathProtectConfigured";
      type boolean;
      description "Is Path Protection Configured";
    }
    leaf path-protection-protected-by-id {
      xr:xr-xml-map "mpls_lcac:PathProtectionProtectedByID";
      type uint32;
      description
        "The path option ID (level/index) of the
        configured explicit protecting path";
    }
    leaf valid-path-protection-path-option-exists {
      xr:xr-xml-map "mpls_lcac:ValidPathProtectionPathOptionExists";
      type boolean;
      description
        "Flag to indicate whether tunnel has a
        path-option which is valid for path-protection";
    }
    leaf is-path-protect-switch-over-underway {
      xr:xr-xml-map "mpls_lcac:IsPathProtectSwitchOverUnderway";
      type boolean;
      description "Is Switchover Underway";
    }
    leaf reoptimization-time-remaining {
      xr:xr-xml-map "mpls_lcac:ReoptimizationTimeRemaining";
      type uint32;
      units "second";
      description
        "Remaining time until path protection
        reoptimization (seconds)";
    }
  }

  grouping MPLS-TE-TUNNELS-TUNNEL-LAST-REOPT-FAIL-INFO {
    description
      "Last re-opt failure reason/information if
      applicable";
    leaf re-opt-last-fail-reason {
      xr:xr-xml-map "mpls_lcac:ReOptLastFailReason";
      type Mpls-te-reopt-decision-reason;
      description
        "Reason (if any) for the last re-opt attempt
        failure";
    }
    leaf re-opt-failed-destination {
      xr:xr-xml-map "mpls_lcac:ReOptFailedDestination";
      type inet:ipv4-address;
      description
        "First tunnel destination (if any) in re-opt LSP
        that failed to come up";
    }
    leaf re-opt-failed-timestamp {
      xr:xr-xml-map "mpls_lcac:ReOptFailedTimestamp";
      type uint32;
      units "second";
      description
        "Time stamp of the last re-opt failure. (seconds
        since Jan. 1, 1970)";
    }
  }

  grouping MPLS-TE-TUNNELS-HISTORY-STANDBY-SETUP {
    description "History information for standby setup";
    leaf standby-lsp-uptime {
      xr:xr-xml-map "mpls_lcac:StandbyLSPUptime";
      type uint32;
      units "second";
      description "Time in seconds since the standby LSP was up";
    }
    leaf standby-setup-timer {
      xr:xr-xml-map "mpls_lcac:StandbySetupTimer";
      type uint32;
      units "second";
      description
        "Time in seconds until the next attempt to
        connect this setup";
    }
  }

  grouping MPLS-TE-TUNNELS-HISTORY-OTHER-SETUP {
    description "History information for additional GMPLS setup";
    leaf path-option-index {
      xr:xr-xml-map "mpls_lcac:PathOptionIndex";
      type uint32;
      description "Path option index for the additional setup";
    }
    leaf other-setup-error {
      xr:xr-xml-map "mpls_lcac:OtherSetupError";
      type string;
      description "The last error for the additional setup";
    }
  }

  grouping MPLS-TE-TUNNELS-HISTORY-PREVIOUS-PROTECT {
    description
      "History information for previous protecting GMPLS
      current setup";
    leaf previous-protect-path-option {
      xr:xr-xml-map "mpls_lcac:PreviousProtectPathOption";
      type string;
      description "The previous protect setup path option";
    }
    leaf previous-protect-tunnel-instance {
      xr:xr-xml-map "mpls_lcac:PreviousProtectTunnelInstance";
      type uint32;
      description "The previous protect setup's instance";
    }
    leaf previous-protect-fail-reason {
      xr:xr-xml-map "mpls_lcac:PreviousProtectFailReason";
      type string;
      description "Reason for the previous protect setup's failure";
    }
    leaf previous-protect-setup-last-error {
      xr:xr-xml-map "mpls_lcac:PreviousProtectSetupLastError";
      type string;
      description "The last error for the previous setup";
    }
  }

  grouping MPLS-TE-TUNNELS-HISTORY-PREVIOUS {
    description "History information for previous current setup";
    leaf previous-path-option {
      xr:xr-xml-map "mpls_lcac:PreviousPathOption";
      type string;
      description "The previous setup path option";
    }
    leaf previous-tunnel-instance {
      xr:xr-xml-map "mpls_lcac:PreviousTunnelInstance";
      type uint32;
      description "The previous setup's instance";
    }
    leaf previous-fail-reason {
      xr:xr-xml-map "mpls_lcac:PreviousFailReason";
      type string;
      description "Reason for the previous setup's failure";
    }
    leaf previous-setup-last-error {
      xr:xr-xml-map "mpls_lcac:PreviousSetupLastError";
      type string;
      description "The last error for the previous setup";
    }
  }

  grouping MPLS-TE-TUNNELS-HISTORY-PATH-PROTECT {
    description "History information for protecting setup";
    leaf protecting-setup-uptime {
      xr:xr-xml-map "mpls_lcac:ProtectingSetupUptime";
      type uint32;
      units "second";
      description
        "Time in seconds since the protecting setup came
        up";
    }
    leaf protecting-setup-timer {
      xr:xr-xml-map "mpls_lcac:ProtectingSetupTimer";
      type uint32;
      units "second";
      description
        "Time in seconds until the next attempt to
        connect the protecting setup";
    }
    leaf protecting-setup-last-error {
      xr:xr-xml-map "mpls_lcac:ProtectingSetupLastError";
      type string;
      description
        "The last error for the protecting setup (for
        display purposes only)";
    }
  }

  grouping MPLS-TE-TUNNELS-HISTORY-REOPT {
    description "History information for reoptimized setup";
    leaf reoptimized-setup-uptime {
      xr:xr-xml-map "mpls_lcac:ReoptimizedSetupUptime";
      type uint32;
      units "second";
      description "Time in seconds since the reopt setup came up";
    }
    leaf reoptimized-setup-timer {
      xr:xr-xml-map "mpls_lcac:ReoptimizedSetupTimer";
      type uint32;
      units "second";
      description
        "Time in seconds until the next attempt to
        connect the reopt setup";
    }
    leaf reoptimized-setup-last-error {
      xr:xr-xml-map "mpls_lcac:ReoptimizedSetupLastError";
      type string;
      description "The last error for the reopt setup";
    }
  }

  grouping MPLS-TE-TUNNELS-HISTORY-CURRENT-CONNECTED {
    description "History information for currently connected setup";
    leaf current-lsp-uptime {
      xr:xr-xml-map "mpls_lcac:CurrentLSPUptime";
      type uint32;
      units "second";
      description "Time in seconds since the current LSP was up";
    }
    leaf current-uptime {
      xr:xr-xml-map "mpls_lcac:CurrentUptime";
      type uint32;
      units "second";
      description "Time in seconds since the tunnel was up";
    }
  }

  grouping MPLS-TE-TUNNELS-HISTORY-CURRENT {
    description "History information for current setup";

    container connected-uptimes {
      description "Uptimes for connected setup";
      uses MPLS-TE-TUNNELS-HISTORY-CURRENT-CONNECTED;
    }
    leaf current-setup-timer {
      xr:xr-xml-map "mpls_lcac:CurrentSetupTimer";
      type uint32;
      units "second";
      description
        "Time in seconds until the next attempt to
        connect this setup";
    }
    leaf selection-reason {
      xr:xr-xml-map "mpls_lcac:SelectionReason";
      type string;
      description
        "The reason why this setup is selected. For
        display purposes only.";
    }
    leaf current-setup-last-error {
      xr:xr-xml-map "mpls_lcac:CurrentSetupLastError";
      type string;
      description "The last error for the current setup";
    }
  }

  grouping MPLS-TE-TUNNELS-HISTORY-BAG {
    description "MPLS TE Tunnel History Information";

    container current-setup {
      description "Current setup data";
      uses MPLS-TE-TUNNELS-HISTORY-CURRENT;
    }

    container reopt-setup {
      description "Reoptimized setup data";
      uses MPLS-TE-TUNNELS-HISTORY-REOPT;
    }

    container gmpls-path-protect-setup {
      description "GMPLS protecting setup data";
      uses MPLS-TE-TUNNELS-HISTORY-PATH-PROTECT;
    }

    container previous-setup {
      description "Previous setup data";
      uses MPLS-TE-TUNNELS-HISTORY-PREVIOUS;
    }

    container previous-gmpls-path-protect-setup {
      description "Previous GMPLS protecting setup data";
      uses MPLS-TE-TUNNELS-HISTORY-PREVIOUS-PROTECT;
    }

    container gmpls-other-setup {
      description "GMPLS additional setup data";
      uses MPLS-TE-TUNNELS-HISTORY-OTHER-SETUP;
    }

    container gmpls-other-protect-setup {
      description "GMPLS additional protecting setup data";
      uses MPLS-TE-TUNNELS-HISTORY-OTHER-SETUP;
    }

    container standby-setup {
      description "Standby setup data";
      uses MPLS-TE-TUNNELS-HISTORY-STANDBY-SETUP;
    }

    container standby-reopt-setup {
      description "Standby Reopt setup data";
      uses MPLS-TE-TUNNELS-HISTORY-REOPT;
    }

    container last-re-opt-fail {
      description "Last re-opt attempt failure information";
      uses MPLS-TE-TUNNELS-TUNNEL-LAST-REOPT-FAIL-INFO;
    }

    container last-stdby-re-opt-fail {
      description "Last standby re-opt attempt failure information";
      uses MPLS-TE-TUNNELS-TUNNEL-LAST-REOPT-FAIL-INFO;
    }
  }

  grouping MPLS-TE-TUNNELS-AUTOBW-OPER {
    description
      "MPLS TE Tunnel AutoBandwidth Operational
      Information";
    leaf last-bandwidth-applied {
      xr:xr-xml-map "mpls_lcac:LastBandwidthApplied";
      type uint32;
      description
        "Last bandwidth requested by auto-bw for the
        tunnel";
    }
    leaf bandwidth-pool-type {
      xr:xr-xml-map "mpls_lcac:BandwidthPoolType";
      type Mpls-te-bw-pool;
      description "Bandwidth pool type";
    }
    leaf bandwidth-applications {
      xr:xr-xml-map "mpls_lcac:BandwidthApplications";
      type uint32;
      description
        "Total number of bandwidth applications requested
        by auto-bw";
    }
    leaf last-application-trigger {
      xr:xr-xml-map "mpls_lcac:LastApplicationTrigger";
      type Te-autobw-app-trigger;
      description "The reason causing the last BW application";
    }
    leaf application-jitter {
      xr:xr-xml-map "mpls_lcac:ApplicationJitter";
      type uint32;
      description
        "Amount of time introduced to delay first
        application so that not all tunnels may signal
        BW at the same time";
    }
    leaf time-left-application {
      xr:xr-xml-map "mpls_lcac:TimeLeftApplication";
      type uint32;
      description
        "Time left until next auto-bw application
        algorithm is performed";
    }
    leaf samples-collected {
      xr:xr-xml-map "mpls_lcac:SamplesCollected";
      type uint32;
      description
        "Number of samples collected within current
        application period";
    }
    leaf time-left-collection {
      xr:xr-xml-map "mpls_lcac:TimeLeftCollection";
      type uint32;
      description
        "Time left until next auto-bw data collection is
        performed";
    }
    leaf highest-bandwidth {
      xr:xr-xml-map "mpls_lcac:HighestBandwidth";
      type uint32;
      description
        "Highest bandwidth registered within current
        application period";
    }
    leaf underflow-highest-bandwidth {
      xr:xr-xml-map "mpls_lcac:UnderflowHighestBandwidth";
      type uint32;
      description
        "Highest sample collected during an underflow
        sequence";
    }
    leaf threshold-overflows {
      xr:xr-xml-map "mpls_lcac:ThresholdOverflows";
      type uint32;
      description
        "counter for current consecutive collections
        exceeding threshold";
    }
    leaf overflow-early-bw-applications {
      xr:xr-xml-map "mpls_lcac:OverflowEarlyBWApplications";
      type uint32;
      description
        "tunnel counter for number of bandwidth
        applications due to overflow";
    }
    leaf threshold-underflows {
      xr:xr-xml-map "mpls_lcac:ThresholdUnderflows";
      type uint32;
      description
        "counter for current consecutive collections
        exceeding threshold";
    }
    leaf underflow-early-bw-applications {
      xr:xr-xml-map "mpls_lcac:UnderflowEarlyBWApplications";
      type uint32;
      description
        "tunnel counter for number of bandwidth
        applications due to underflow";
    }
    leaf collect-only-requested-bandwidth {
      xr:xr-xml-map "mpls_lcac:CollectOnlyRequestedBandwidth";
      type uint32;
      description "Collect-only Requested Bandwidth for the tunnel";
    }
    leaf application-reject-reason {
      xr:xr-xml-map "mpls_lcac:ApplicationRejectReason";
      type Te-autobw-app-rej;
      description "Current application reject reason";
    }
  }

  grouping MPLS-TE-TUNNELS-AUTOBW-CONFIG {
    description
      "MPLS TE Tunnel AutoBandwidth Configuration
      Information";
    leaf is-auto-bandwidth-collect-only {
      xr:xr-xml-map "mpls_lcac:IsAutoBandwidthCollectOnly";
      type boolean;
      description "TRUE if auto-bw collection-only is enabled";
    }
    leaf minimum-bandwidth {
      xr:xr-xml-map "mpls_lcac:MinimumBandwidth";
      type uint32;
      description "Minimum bandwith auto-bw can apply";
    }
    leaf maximum-bandwidth {
      xr:xr-xml-map "mpls_lcac:MaximumBandwidth";
      type uint32;
      description "Maximum bandwith auto-bw can apply";
    }
    leaf application-frequency {
      xr:xr-xml-map "mpls_lcac:ApplicationFrequency";
      type uint32;
      units "minute";
      description
        "Auto-bw application frequency for the tunnel
        (mins)";
    }
    leaf collection-frequency {
      xr:xr-xml-map "mpls_lcac:CollectionFrequency";
      type uint32;
      description "Global auto-bw collection frequency";
    }
    leaf adjustment-threshold-percent {
      xr:xr-xml-map "mpls_lcac:AdjustmentThresholdPercent";
      type uint32;
      description
        "Bandwidth change threshold needed to trigger
        bandwidth adjustment";
    }
    leaf adjustment-threshold-value {
      xr:xr-xml-map "mpls_lcac:AdjustmentThresholdValue";
      type uint32;
      units "kbit/s";
      description
        "Bandwidth change value (kbps) needed to trigger
        bandwidth adjustment";
    }
    leaf overflow-threshold-percent {
      xr:xr-xml-map "mpls_lcac:OverflowThresholdPercent";
      type uint32;
      description
        "Bandwidth change threshold needed to count a
        collection towards overflow limit allowed";
    }
    leaf overflow-threshold-value {
      xr:xr-xml-map "mpls_lcac:OverflowThresholdValue";
      type uint32;
      description
        "Bandwidth change value needed to count a
        collection towards overflow limit allowed";
    }
    leaf overflow-threshold-limit {
      xr:xr-xml-map "mpls_lcac:OverflowThresholdLimit";
      type uint32;
      description
        "Limit of consecutive collections exceeding
        threshold to trigger an immediate overflow
        bandwidth adjustment";
    }
    leaf underflow-threshold-percent {
      xr:xr-xml-map "mpls_lcac:UnderflowThresholdPercent";
      type uint32;
      description
        "Bandwidth change threshold needed to count a
        collection towards underflow limit allowed";
    }
    leaf underflow-threshold-value {
      xr:xr-xml-map "mpls_lcac:UnderflowThresholdValue";
      type uint32;
      description
        "Bandwidth change value needed to count a
        collection towards underflow limit allowed";
    }
    leaf underflow-threshold-limit {
      xr:xr-xml-map "mpls_lcac:UnderflowThresholdLimit";
      type uint32;
      description
        "Limit of consecutive collections exceeding
        threshold to trigger an immediate underflow
        bandwidth adjustment";
    }
  }

  grouping MPLS-TE-TUNNELS-AUTOBW-STATUS {
    description "MPLS TE Tunnel AutoBandwidth Status Information";
    leaf is-auto-bandwidth-enabled {
      xr:xr-xml-map "mpls_lcac:IsAutoBandwidthEnabled";
      type boolean;
      description "TRUE if auto-bw is enabled for the tunnel";
    }
    leaf reactivation-time {
      xr:xr-xml-map "mpls_lcac:ReactivationTime";
      type uint32;
      description
        "Time until auto-bw gets activated if activation
        has been delayed due to failover";
    }
  }

  grouping MPLS-TE-P2P-INFO-BAG {
    description "P2P tunnel data";

    container auto-bandwidth-status {
      description "Tunnels's AutoBandwidth Status information";
      uses MPLS-TE-TUNNELS-AUTOBW-STATUS;
    }

    container auto-bandwidth-config {
      description
        "Tunnels's AutoBandwidth Configuration
        information";
      uses MPLS-TE-TUNNELS-AUTOBW-CONFIG;
    }

    container auto-bandwidth-oper {
      description "Tunnels's AutoBandwidth Operational information";
      uses MPLS-TE-TUNNELS-AUTOBW-OPER;
    }
    leaf is-bidirectional {
      xr:xr-xml-map "mpls_lcac:IsBidirectional";
      type boolean;
      description "TRUE if the tunnel is bidirectional";
    }
  }

  grouping MPLS-TE-INTERAREA-REOPT-INFO {
    description
      "Counter and time information for reoptimization
      of interarea tunnels";
    leaf sent-path-queries {
      xr:xr-xml-map "mpls_lcac:SentPathQueries";
      type uint16;
      description "Number of better path queries sent";
    }
    leaf time-since-last-query-sent {
      xr:xr-xml-map "mpls_lcac:TimeSinceLastQuerySent";
      type uint32;
      units "second";
      description
        "Time since the last better path query was sent
        (seconds)";
    }
    leaf received-preferred-path-errors {
      xr:xr-xml-map "mpls_lcac:ReceivedPreferredPathErrors";
      type uint16;
      description "Number of received Preferred Path Exists Error";
    }
    leaf time-since-last-preferred-path-error {
      xr:xr-xml-map "mpls_lcac:TimeSinceLastPreferredPathError";
      type uint32;
      units "second";
      description
        "Time since last Preferred Path Exists error
        received (seconds)";
    }
    leaf received-preferred-tree-errors {
      xr:xr-xml-map "mpls_lcac:ReceivedPreferredTreeErrors";
      type uint16;
      description "Number of received Preferred Tree Exists Error";
    }
    leaf time-since-last-preferred-tree-error {
      xr:xr-xml-map "mpls_lcac:TimeSinceLastPreferredTreeError";
      type uint32;
      units "second";
      description
        "Time since last Preferred Tree Exists error
        received (seconds)";
    }
    leaf preferred-path-error-node {
      xr:xr-xml-map "mpls_lcac:PreferredPathErrorNode";
      type inet:ipv4-address;
      description
        "Address of the preferred path error generating
        node";
    }
    leaf preferred-tree-error-node {
      xr:xr-xml-map "mpls_lcac:PreferredTreeErrorNode";
      type inet:ipv4-address;
      description
        "Address of the preferred tree error generating
        node";
    }
  }

  grouping MPLS-TE-P2MP-DEST {
    description "A P2MP destination";

    container inter-area-reoptimization {
      description
        "The timing and count information of interarea
        reoptimization.";
      uses MPLS-TE-INTERAREA-REOPT-INFO;
    }
    leaf destination-address {
      xr:xr-xml-map "mpls_lcac:DestinationAddress";
      type inet:ipv4-address;
      description "Destination address";
    }
    leaf destination-state {
      xr:xr-xml-map "mpls_lcac:DestinationState";
      type Te-destination-state;
      description "The state of the destination";
    }
    leaf active-path-option-index {
      xr:xr-xml-map "mpls_lcac:ActivePathOptionIndex";
      type uint32;
      description "Index of active path option";
    }
    leaf path-option-exhausted {
      xr:xr-xml-map "mpls_lcac:PathOptionExhausted";
      type boolean;
      description "Path options are exhausted";
    }
    leaf uptime {
      xr:xr-xml-map "mpls_lcac:Uptime";
      type uint32;
      units "second";
      description "Time in seconds since the destination was up";
    }
    leaf path-change-time {
      xr:xr-xml-map "mpls_lcac:PathChangeTime";
      type uint32;
      description "Last path change time";
    }
    leaf total-uptime {
      xr:xr-xml-map "mpls_lcac:TotalUptime";
      type uint32;
      description "Unused";
    }
    leaf s2l-exist {
      xr:xr-xml-map "mpls_lcac:S2LExist";
      type boolean;
      description "Dest state may not be up but S2L may exist";
    }
    leaf destination-deletion-cause {
      xr:xr-xml-map "mpls_lcac:DestinationDeletionCause";
      type Te-p2mp-s2l-deletion-cause;
      description "Destination deletion cause";
    }
    leaf destination-deletion-sub-cause {
      xr:xr-xml-map "mpls_lcac:DestinationDeletionSubCause";
      type Te-p2mp-s2l-deletion-subcause;
      description "Destination deletion subcause";
    }
    leaf destination-deletion-timestamp {
      xr:xr-xml-map "mpls_lcac:DestinationDeletionTimestamp";
      type uint32;
      units "second";
      description "Destination deletion timestamp in seconds";
    }
    leaf is-inter-area {
      xr:xr-xml-map "mpls_lcac:IsInterArea";
      type boolean;
      description
        "Indicates whether this destination is in
        different area";
    }

    list path-option {
      description "Destination's list of path options";
      uses MPLS-TE-P2MP-PATH-OPTION;
    }
  }

  grouping MPLS-TE-AUTOROUTE-DESTINATION-BAG {
    description "An Autoroute destination";
    leaf destination-address {
      xr:xr-xml-map "mpls_lcac:DestinationAddress";
      type inet:ipv4-address;
      description "Destination address";
    }
    leaf prefix-length {
      xr:xr-xml-map "mpls_lcac:PrefixLength";
      type uint16;
      description "Prefix length";
    }
  }

  grouping MPLS-TE-TUNNEL-BFD-CONFIG-INFO {
    description "BFD configuration info for a tunnel";
    leaf bfd-fast-detecting-enabled {
      xr:xr-xml-map "mpls_lcac:BFDFastDetectingEnabled";
      type boolean;
      description "BFD Fast Detecting Enabled";
    }
    leaf min-interval {
      xr:xr-xml-map "mpls_lcac:MinInterval";
      type uint32;
      units "millisecond";
      description "Hello interval in milliseconds";
    }
    leaf min-interval-default {
      xr:xr-xml-map "mpls_lcac:MinIntervalDefault";
      type boolean;
      description "Is default hello interval";
    }
    leaf multiplier {
      xr:xr-xml-map "mpls_lcac:Multiplier";
      type uint8;
      description "Multiplier";
    }
    leaf multiplier-default {
      xr:xr-xml-map "mpls_lcac:MultiplierDefault";
      type boolean;
      description "Is default multiplier";
    }
    leaf bring-up-timeout {
      xr:xr-xml-map "mpls_lcac:BringUpTimeout";
      type uint16;
      description "Bring Up Timeout in second";
    }
    leaf bring-up-timeout-default {
      xr:xr-xml-map "mpls_lcac:BringUpTimeoutDefault";
      type boolean;
      description "Is default bring up timeout";
    }
    leaf dampening-initial-wait {
      xr:xr-xml-map "mpls_lcac:DampeningInitialWait";
      type uint32;
      units "millisecond";
      description "Dampening initial wait time in milliseconds";
    }
    leaf dampening-initial-wait-default {
      xr:xr-xml-map "mpls_lcac:DampeningInitialWaitDefault";
      type boolean;
      description "Is default dampening inital wait time";
    }
    leaf dampening-max-wait {
      xr:xr-xml-map "mpls_lcac:DampeningMaxWait";
      type uint32;
      units "millisecond";
      description "Dampening max wait time in milliseconds";
    }
    leaf dampening-max-wait-default {
      xr:xr-xml-map "mpls_lcac:DampeningMaxWaitDefault";
      type boolean;
      description "Is default dampening max wait time";
    }
    leaf dampening-secondary-wait {
      xr:xr-xml-map "mpls_lcac:DampeningSecondaryWait";
      type uint32;
      units "millisecond";
      description "Dampening secondary wait time in milliseconds";
    }
    leaf dampening-secondary-wait-default {
      xr:xr-xml-map "mpls_lcac:DampeningSecondaryWaitDefault";
      type boolean;
      description "Is default dampening secondary wait time";
    }
    leaf periodic-lsp-ping-disabled {
      xr:xr-xml-map "mpls_lcac:PeriodicLSPPingDisabled";
      type boolean;
      description "Periodic LSP Ping disabled";
    }
    leaf periodic-lsp-ping-interval {
      xr:xr-xml-map "mpls_lcac:PeriodicLSPPingInterval";
      type uint32;
      units "second";
      description "Periodic LSP Ping interval in seconds";
    }
    leaf periodic-lsp-ping-interval-default {
      xr:xr-xml-map "mpls_lcac:PeriodicLSPPingIntervalDefault";
      type boolean;
      description "Is default LSP Ping interval";
    }
    leaf bfd-session-down-action {
      xr:xr-xml-map "mpls_lcac:BFDSessionDownAction";
      type Mpls-te-bfd-session-down-action1;
      description "BFD Session Down Action";
    }
    leaf bfd-session-down-reopt-timeout {
      xr:xr-xml-map "mpls_lcac:BFDSessionDownReoptTimeout";
      type uint32;
      description "BFD Session Down Reopt Timeout";
    }
    leaf bfd-encap-mode {
      xr:xr-xml-map "mpls_lcac:BFDEncapMode";
      type Te-vif-bfd-encap-mode;
      description "BFD Encap Mode";
    }
  }

  grouping MPLS-TE-TUNNEL-BIDIR-CONFIG-INFO {
    description "Bidirectional configuration info for a tunnel";
    leaf association-type {
      xr:xr-xml-map "mpls_lcac:AssociationType";
      type uint16;
      description
        "Association Type
        (draft-ietf-ccamp-mpls-tp-rsvpte-ext-associated-lsp)";
    }
    leaf association-id {
      xr:xr-xml-map "mpls_lcac:AssociationID";
      type uint16;
      description "The association ID";
    }
    leaf association-source {
      xr:xr-xml-map "mpls_lcac:AssociationSource";
      type inet:ipv4-address;
      description "The association source";
    }
    leaf association-global-id {
      xr:xr-xml-map "mpls_lcac:AssociationGlobalID";
      type uint32;
      description "The association global ID";
    }
    leaf association-corouted {
      xr:xr-xml-map "mpls_lcac:AssociationCorouted";
      type boolean;
      description "Is the association co-routed";
    }
  }

  grouping MPLS-TE-P2MP-TUN-CFG-BAG {
    description "Configured P2MP tunnel data";

    container affinity {
      description "Affinity";
      uses MPLS-TE-TUNNELS-AFFINITY-INFO;
    }

    container bidirectional-config {
      description "Bidirectional Configuration Information";
      uses MPLS-TE-TUNNEL-BIDIR-CONFIG-INFO;
    }

    container bfd-config {
      description "BFD Configuration Information";
      uses MPLS-TE-TUNNEL-BFD-CONFIG-INFO;
    }
    leaf tunnel-name {
      xr:xr-xml-map "mpls_lcac:TunnelName";
      type string;
      description "Tunnel name";
    }
    leaf tunnel-id {
      xr:xr-xml-map "mpls_lcac:TunnelID";
      type uint32;
      description "Tunnel id";
    }
    leaf is-p2mp {
      xr:xr-xml-map "mpls_lcac:IsP2MP";
      type boolean;
      description "True if tunnel is a P2MP tunnel";
    }
    leaf signaled-name {
      xr:xr-xml-map "mpls_lcac:SignaledName";
      type string;
      description "Signaled name";
    }
    leaf configured-bandwidth {
      xr:xr-xml-map "mpls_lcac:ConfiguredBandwidth";
      type uint32;
      description "Configured Bandwidth";
    }
    leaf interface-configured-bandwidth {
      xr:xr-xml-map "mpls_lcac:InterfaceConfiguredBandwidth";
      type uint32;
      description "Configured Interface Bandwidth";
    }
    leaf bandwidth-type {
      xr:xr-xml-map "mpls_lcac:BandwidthType";
      type Mpls-te-bw-pool;
      description "The bandwidth type";
    }
    leaf setup-priority {
      xr:xr-xml-map "mpls_lcac:SetupPriority";
      type uint8;
      description "Setup priority";
    }
    leaf hold-priority {
      xr:xr-xml-map "mpls_lcac:HoldPriority";
      type uint8;
      description "Hold priority";
    }
    leaf policy-class {
      xr:xr-xml-map "mpls_lcac:PolicyClass";
      type uint8;
      description "deprecated";
    }
    leaf forward-class {
      xr:xr-xml-map "mpls_lcac:ForwardClass";
      type uint32;
      description "Forward class";
    }
    leaf backup-bandwidth {
      xr:xr-xml-map "mpls_lcac:BackupBandwidth";
      type uint32;
      description "Backup bandwidth";
    }
    leaf backup-bandwidth-flags {
      xr:xr-xml-map "mpls_lcac:BackupBandwidthFlags";
      type uint8;
      description "Backup bandwidth flags";
    }
    leaf config-load-share {
      xr:xr-xml-map "mpls_lcac:ConfigLoadShare";
      type uint32;
      description "Config loadshare";
    }
    leaf payload-type {
      xr:xr-xml-map "mpls_lcac:PayloadType";
      type uint16;
      description "Payload type";
    }
    leaf is-in-config {
      xr:xr-xml-map "mpls_lcac:IsInConfig";
      type boolean;
      description "Is in config";
    }
    leaf explicit-null-imposition {
      xr:xr-xml-map "mpls_lcac:ExplicitNullImposition";
      type boolean;
      description "Imposition of Explicit NULL";
    }
    leaf fast-reroute {
      xr:xr-xml-map "mpls_lcac:FastReroute";
      type boolean;
      description "Fast reroute enabled";
    }
    leaf is-backup-tunnel {
      xr:xr-xml-map "mpls_lcac:IsBackupTunnel";
      type boolean;
      description "TRUE if this is a backup tunnel";
    }
    leaf record-route {
      xr:xr-xml-map "mpls_lcac:RecordRoute";
      type boolean;
      description "Record route";
    }
    leaf srlg-discovery {
      xr:xr-xml-map "mpls_lcac:SRLGDiscovery";
      type boolean;
      description "SRLG-discovery enabled";
    }
    leaf path-protection-enabled {
      xr:xr-xml-map "mpls_lcac:PathProtectionEnabled";
      type boolean;
      description "Path Protection enabled";
    }
    leaf hop-limit {
      xr:xr-xml-map "mpls_lcac:HopLimit";
      type uint8;
      description "Hop Limit";
    }
    leaf cost-limit {
      xr:xr-xml-map "mpls_lcac:CostLimit";
      type uint32;
      description "Cost limit on the tunnel path";
    }
    leaf cost-limit-global {
      xr:xr-xml-map "mpls_lcac:CostLimitGlobal";
      type uint32;
      description "Global Cost Limit";
    }
    leaf path-invalidation-timeout-source {
      xr:xr-xml-map "mpls_lcac:PathInvalidationTimeoutSource";
      type uint32;
      description "Path invalidation timeout configuration source";
    }
    leaf path-invalidation-timeout {
      xr:xr-xml-map "mpls_lcac:PathInvalidationTimeout";
      type uint32;
      description
        "Path invalidation timeout interval on the tunnel
        path";
    }
    leaf path-invalidation-action-source {
      xr:xr-xml-map "mpls_lcac:PathInvalidationActionSource";
      type uint32;
      description "Path invalidation action configuration source";
    }
    leaf path-invalidation-action {
      xr:xr-xml-map "mpls_lcac:PathInvalidationAction";
      type uint32;
      description "Path invalidation action on the tunnel path";
    }
    leaf soft-preempt {
      xr:xr-xml-map "mpls_lcac:SoftPreempt";
      type boolean;
      description "Soft preemption enabled";
    }
    leaf disable-affinity-failure-reopt {
      xr:xr-xml-map "mpls_lcac:DisableAffinityFailureReopt";
      type boolean;
      description "DisableAffinityFailureReopt";
    }
    leaf affinity-failure-reopt-timer {
      xr:xr-xml-map "mpls_lcac:AffinityFailureReoptTimer";
      type uint32;
      description "AffinityFailureReoptTimer";
    }
    leaf segment-routing-path-selection {
      xr:xr-xml-map "mpls_lcac:SegmentRoutingPathSelection";
      type Te-s2l-sr-path-selection;
      description "Segment-Routing path selection type";
    }
    leaf-list policy-class-entry {
      xr:xr-xml-map "mpls_lcac:PolicyClasses";
      type uint8;
      description "PBTS policy classes";
    }

    list autoroute-destination {
      description "Autoroute Destinations list";
      uses MPLS-TE-AUTOROUTE-DESTINATION-BAG;
    }
  }

  grouping MPLS-TE-P2MP-TUNNEL-BAG {
    description "P2MP tunnel data";

    container config {
      description "Configuration data";
      uses MPLS-TE-P2MP-TUN-CFG-BAG;
    }

    container tunnel-current-lsp {
      description "Current LSP";
      uses MPLS-TE-P2MP-LSP;
    }

    container reoptimized-p2mp-lsp {
      description "Reopt LSP";
      uses MPLS-TE-P2MP-LSP;
    }

    container tunnel-standby-lsp {
      description "Standby LSP";
      uses MPLS-TE-P2MP-LSP;
    }

    container reoptimized-standby-p2mp-lsp {
      description "Standby Reopt LSP";
      uses MPLS-TE-P2MP-LSP;
    }

    container tunnel-restoration-lsp {
      description "Restoration LSP";
      uses MPLS-TE-P2MP-LSP;
    }

    container delay-clean-pp-lsp {
      description "Delay Clean PP LSP";
      uses MPLS-TE-P2MP-LSP;
    }

    container cleaned-lsp {
      description "Cleaned LSP";
      uses MPLS-TE-P2MP-LSP;
    }

    container p2p-info {
      description "P2P specific info";
      uses MPLS-TE-P2P-INFO-BAG;
    }

    container history {
      description "Tunnel history";
      uses MPLS-TE-TUNNELS-HISTORY-BAG;
    }

    container path-protection {
      description "Path Protect Info";
      uses MPLS-TE-PP-INFO;
    }

    container auto-backup {
      description "Autobackup Information";
      uses MPLS-TE-AUTOBACKUP-INFO;
    }

    container auto-mesh {
      description "Automesh Information";
      uses MPLS-TE-AUTOMESH-INFO;
    }

    container auto-pcc {
      description "Auto-PCC Information";
      uses MPLS-TE-AUTOPCC-INFO;
    }

    container pce-delegation {
      description "PCE Delegation information";
      uses MPLS-TE-PCE-DELEGATION-INFO;
    }

    container soft-preemption {
      description
        "Tunnel head soft preemption info. This is NULL
        if soft preemption is not configured";
      uses MPLS-TE-SOFT-PREEMPTION-TUNNEL-INFO;
    }

    container wdm-unitunnel {
      description
        "WDM-UNI tunnel data. Only exists for WDM-UNI
        tunnels";
      uses MPLS-TE-MGMT-WDM-UNI-TUNNEL-INFO;
    }

    container transport-tunnel-info {
      description
        "Transport tunnel data. Only exists for Transport
        tunnels";
      uses MPLS-TE-TRANSPORT-TUNNEL-INFO;
    }

    container bfd-info {
      description
        "BFD session info. This is NULL if BFD is not
        configured";
      uses MPLS-TE-TUNNEL-BFD-INFO;
    }

    container otn-bidir {
      description "OTN bidir info";
      uses MPLS-TE-TUNNEL-OTN-BIDIR-INFO;
    }

    container bidir {
      description "Bidir info";
      uses MPLS-TE-TUNNEL-BIDIR-INFO;
    }

    container xro-attribute-set {
      description "XRO attribute-set";
      uses MPLS-TE-ATTRIBUTE-SET;
    }

    container te-tunnel-convergence {
      description "TE tunnel convergence related information";
      uses TE-VIF-CONVERGENCE-INFO;
    }

    container flex-info {
      description "Flex Info";
      uses MPLS-TE-TUNNEL-FLEX-INFO;
    }
    leaf role-standby {
      xr:xr-xml-map "mpls_lcac:RoleStandby";
      type boolean;
      description "TRUE if Role is Standby, Active otherwise";
    }
    leaf tunnel-interface-name {
      xr:xr-xml-map "mpls_lcac:TunnelInterfaceName";
      type xr:Interface-name;
      description "Interface handle of the associated tunnel";
    }
    leaf admin-state {
      xr:xr-xml-map "mpls_lcac:AdminState";
      type Mte-tunnel-admin-state;
      description "Administrative State";
    }
    leaf operational-state {
      xr:xr-xml-map "mpls_lcac:OperationalState";
      type Mte-tunnel-oper-state;
      description "Operational State";
    }
    leaf operational-state-changes {
      xr:xr-xml-map "mpls_lcac:OperationalStateChanges";
      type uint32;
      description "Counters for operational state changes";
    }
    leaf signaled-name {
      xr:xr-xml-map "mpls_lcac:SignaledName";
      type string;
      description "Signaled Name";
    }
    leaf fail-reason {
      xr:xr-xml-map "mpls_lcac:FailReason";
      type Mpls-mte-tunnel-fail-reason;
      description "The reason why failure occurred";
    }
    leaf destination-up-count {
      xr:xr-xml-map "mpls_lcac:DestinationUpCount";
      type uint32;
      description "Count of up destinations";
    }
    leaf destination-disabled-count {
      xr:xr-xml-map "mpls_lcac:DestinationDisabledCount";
      type uint32;
      description "Count of disabled destinations";
    }
    leaf destination-down-count {
      xr:xr-xml-map "mpls_lcac:DestinationDownCount";
      type uint32;
      description "Count of down destinations";
    }
    leaf re-opt-hold-down-timer-remaining {
      xr:xr-xml-map "mpls_lcac:ReOptHoldDownTimerRemaining";
      type uint32;
      units "second";
      description
        "Backup hold-down timer remaining time in seconds";
    }
    leaf bandwidth-requested {
      xr:xr-xml-map "mpls_lcac:BandwidthRequested";
      type uint32;
      description "Bandwidth Requested";
    }
    leaf bandwidth-type {
      xr:xr-xml-map "mpls_lcac:BandwidthType";
      type Mpls-te-bw-pool;
      description "The requested bandwidth type";
    }
    leaf is-node-protected {
      xr:xr-xml-map "mpls_lcac:IsNodeProtected";
      type boolean;
      description "Node Protection Enabled or Disabled";
    }
    leaf is-bandwidth-protect {
      xr:xr-xml-map "mpls_lcac:IsBandwidthProtect";
      type boolean;
      description "BW Protection Enabled or Disabled";
    }
    leaf tunnel-recovering {
      xr:xr-xml-map "mpls_lcac:TunnelRecovering";
      type boolean;
      description "Tunnel recovering";
    }
    leaf reroute-pending {
      xr:xr-xml-map "mpls_lcac:ReroutePending";
      type boolean;
      description "ReroutePending";
    }
    leaf explicit-path-change {
      xr:xr-xml-map "mpls_lcac:ExplicitPathChange";
      type boolean;
      description
        "Explicit-path inuse by the current LSP has been
        modified";
    }
    leaf path-option-change {
      xr:xr-xml-map "mpls_lcac:PathOptionChange";
      type boolean;
      description
        "Path-Option inuse by the current LSP has been
        modified";
    }
    leaf affinity-failure-reopt-disabled {
      xr:xr-xml-map "mpls_lcac:AffinityFailureReoptDisabled";
      type boolean;
      description "AffinityFailureReoptDisabled";
    }
    leaf affinity-failure-reopt-time-remained {
      xr:xr-xml-map "mpls_lcac:AffinityFailureReoptTimeRemained";
      type uint32;
      description "AffinityFailureReoptTimeRemained";
    }
    leaf affinity-failure-delayed-tear-time-remained {
      xr:xr-xml-map "mpls_lcac:AffinityFailureDelayedTearTimeRemain"+
        "ed";
      type uint32;
      description "Affinity Failure LSP tear down time remaining";
    }
    leaf invalidation-time-remained {
      xr:xr-xml-map "mpls_lcac:InvalidationTimeRemained";
      type uint32;
      description "Path invalidation time remaining";
    }
    leaf drop-mode {
      xr:xr-xml-map "mpls_lcac:DropMode";
      type boolean;
      description "True if tunnel is in drop mode";
    }
    leaf auto-route {
      xr:xr-xml-map "mpls_lcac:AutoRoute";
      type boolean;
      description "IGP Auto route announce enabled";
    }
    leaf forwarding-adjacency {
      xr:xr-xml-map "mpls_lcac:ForwardingAdjacency";
      type boolean;
      description "IGP forwarding adjacency enabled";
    }
    leaf load-share-factor {
      xr:xr-xml-map "mpls_lcac:LoadShareFactor";
      type uint32;
      description "The specified loadsharing for the tunnel";
    }
    leaf load-share-type {
      xr:xr-xml-map "mpls_lcac:LoadShareType";
      type Mpls-te-loadshare;
      description "Loadsharing type";
    }
    leaf create-time {
      xr:xr-xml-map "mpls_lcac:CreateTime";
      type uint32;
      description "Time at which the tunnel was created";
    }
    leaf uptime {
      xr:xr-xml-map "mpls_lcac:Uptime";
      type uint32;
      units "second";
      description "Time in seconds since the tunnel was up";
    }
    leaf metric-type {
      xr:xr-xml-map "mpls_lcac:MetricType";
      type Mpls-te-metric;
      description "The path selection metric";
    }
    leaf tiebreaker-type {
      xr:xr-xml-map "mpls_lcac:TiebreakerType";
      type uint32;
      description "The path selection tiebreaker type";
    }
    leaf tiebreaker-qualifier {
      xr:xr-xml-map "mpls_lcac:TiebreakerQualifier";
      type Mpls-te-metric-qualifier;
      description
        "Describes how the path selection tiebreaker was
        specified: default, globally set, or per
        interface";
    }
    leaf metric-qualifier {
      xr:xr-xml-map "mpls_lcac:MetricQualifier";
      type Mpls-te-metric-qualifier;
      description
        "Describe how the metric was specified: default,
        globally set, or per interface";
    }
    leaf is-hop-limit-ignore {
      xr:xr-xml-map "mpls_lcac:IsHopLimitIgnore";
      type boolean;
      description "Is Hop-limit ignored";
    }
    leaf hop-limit-ignored-reason {
      xr:xr-xml-map "mpls_lcac:HopLimitIgnoredReason";
      type Te-hop-limit-ignore;
      description "Hop-limit ignored reason";
    }
    leaf outbound-frr-state {
      xr:xr-xml-map "mpls_lcac:OutboundFRRState";
      type Mpls-te-frr-state;
      description "Indicates outbound FRR state";
    }
    leaf area-id {
      xr:xr-xml-map "mpls_lcac:AreaID";
      type string;
      description
        "Indicates the protocol and area used to find
        Outgoing ERO";
    }
    leaf pce-fail-reason {
      xr:xr-xml-map "mpls_lcac:PCEFailReason";
      type Mpls-te-pce-fail-reasons;
      description "Failure reason for PCE-based tunnels";
    }
    leaf snmp-index {
      xr:xr-xml-map "mpls_lcac:SNMPIndex";
      type uint32;
      description "SNMP index for interface";
    }
    leaf is-inter-area-tunnel {
      xr:xr-xml-map "mpls_lcac:IsInterAreaTunnel";
      type boolean;
      description
        "Indicates whether this tunnel spans multiple
        areas.";
    }
    leaf is-auto-backup {
      xr:xr-xml-map "mpls_lcac:IsAutoBackup";
      type boolean;
      description
        "Indicates whether this is an automatically
        generated backup tunnel";
    }
    leaf is-auto-pcc {
      xr:xr-xml-map "mpls_lcac:IsAutoPCC";
      type boolean;
      description
        "Indicates whether this is an automatic PCC
        tunnel";
    }
    leaf is-pce-delegated {
      xr:xr-xml-map "mpls_lcac:IsPCEDelegated";
      type boolean;
      description
        "Indicates whether this tunnel is delegated to a
        PCE server or not";
    }
    leaf tunnel-attribute-set-name {
      xr:xr-xml-map "mpls_lcac:TunnelAttributeSetName";
      type string;
      description "AttributeSet name";
    }
    leaf tunnel-attribute-set-type {
      xr:xr-xml-map "mpls_lcac:TunnelAttributeSetType";
      type Tunnel-attribute-set;
      description "AttributeSet type";
    }
    leaf xro-attribute-set-name {
      xr:xr-xml-map "mpls_lcac:XROAttributeSetName";
      type string;
      description "Configured XRO attribute-set name";
    }
    leaf is-passive {
      xr:xr-xml-map "mpls_lcac:IsPassive";
      type boolean;
      description "True for passive tunnel";
    }
    leaf passive-tunnel-name {
      xr:xr-xml-map "mpls_lcac:PassiveTunnelName";
      type string;
      description "Passive tunnel name";
    }
    leaf binding-label-exists {
      xr:xr-xml-map "mpls_lcac:BindingLabelExists";
      type boolean;
      description "True, if binding label exists";
    }
    leaf binding-label {
      xr:xr-xml-map "mpls_lcac:BindingLabel";
      type uint32;
      description "Binding Label";
    }
    leaf last-hop-ifindex {
      xr:xr-xml-map "mpls_lcac:LastHopIfindex";
      type uint32;
      description "Termination destination ifindex";
    }
    leaf is-named {
      xr:xr-xml-map "mpls_lcac:IsNamed";
      type boolean;
      description "Indicates whether this tunnel is named";
    }
    leaf lsp-wrap-protection-enabled {
      xr:xr-xml-map "mpls_lcac:LSPWrapProtectionEnabled";
      type boolean;
      description "Lsp-wrap Protection enabled";
    }
    leaf lsp-wrap-label {
      xr:xr-xml-map "mpls_lcac:LSPWrapLabel";
      type uint32;
      description "Lsp-wrap label value";
    }

    list destination {
      description "Destinations array";
      uses MPLS-TE-P2MP-DEST;
    }
  }

  grouping MPLS-TE-S2L-DIVERSITY-INFO {
    description "S2l Diversity info";
    leaf diversity-type {
      xr:xr-xml-map "mpls_lcac:DiversityType";
      type Te-pp-diversity;
      description "S2L path diversity type";
    }
  }

  grouping TUNNEL-MIDPOINT-LSP-WRAP-INFO-BAG {
    description "Midpoint LSP Wrap Protection LSP Info";
    leaf lsp-wrap-protection-enable {
      xr:xr-xml-map "mpls_lcac:LSPWrapProtectionEnable";
      type boolean;
      description "LSP Wrap protection enabled";
    }
    leaf lsp-wrap-protection-label {
      xr:xr-xml-map "mpls_lcac:LSPWrapProtectionLabel";
      type uint32;
      description "LSP Wrap Merge Point Label";
    }
    leaf reverse-egress-interface {
      xr:xr-xml-map "mpls_lcac:ReverseEgressInterface";
      type string;
      description "Reverse Egress Interface";
    }
    leaf reverse-lsp-label {
      xr:xr-xml-map "mpls_lcac:ReverseLspLabel";
      type uint32;
      description "Reverse LSP label";
    }
    leaf lsp-wrap-protection-state {
      xr:xr-xml-map "mpls_lcac:LSPWrapProtectionState";
      type Mpls-te-lsp-wrap-state;
      description "LSP wrap protection state";
    }
  }

  grouping TE-S2L-SR-PATH-HOP {
    description "TE Segment-Routing S2L path hop";
    leaf sid-type {
      xr:xr-xml-map "mpls_lcac:SIDType";
      type Te-sr-sid;
      description "Type of the SID";
    }
    leaf has-ip-addresses {
      xr:xr-xml-map "mpls_lcac:HasIPAddresses";
      type boolean;
      description "Node has IP addresses specified";
    }
    leaf local-addr {
      xr:xr-xml-map "mpls_lcac:LocalAddr";
      type inet:ipv4-address;
      description "Local IP address of adjacency or Node ID";
    }
    leaf remote-addr {
      xr:xr-xml-map "mpls_lcac:RemoteAddr";
      type inet:ipv4-address;
      description "Remote IP address of adjacency";
    }
    leaf has-mpls-label {
      xr:xr-xml-map "mpls_lcac:HasMPLSLabel";
      type boolean;
      description "Hop has MPLS label specified";
    }
    leaf mpls-label-value {
      xr:xr-xml-map "mpls_lcac:MPLSLabelValue";
      type uint32;
      description "The MPLS label value";
    }
    leaf has-entropy-label {
      xr:xr-xml-map "mpls_lcac:HasEntropyLabel";
      type boolean;
      description "Hop has EL specified";
    }
  }

  grouping FLEX-LOCKOUT {
    description
      "Information about flex LSP lockout info for the
      link";
    leaf is-lockout {
      xr:xr-xml-map "mpls_lcac:IsLockout";
      type boolean;
      description "True if s2l is locked out";
    }
    leaf origination {
      xr:xr-xml-map "mpls_lcac:Origination";
      type Flex-lsp-lockout-origination;
      description "Flex LSP Lockout Origination Source";
    }
    leaf lockout-timestamp {
      xr:xr-xml-map "mpls_lcac:LockoutTimestamp";
      type uint32;
      description "The timestamp when the lockout is set";
    }
  }

  grouping MPLS-TE-S2L-FLEX-INFO {
    description "TE Per-S2L FlexLSP Information";

    container flex-fec {
      description "FEC for the FlexLSP Entry";
      uses TE-S2L-FEC;
    }

    container lockout {
      description "Flex LSP Lockout Info";
      uses FLEX-LOCKOUT;
    }
    leaf entry-exists {
      xr:xr-xml-map "mpls_lcac:EntryExists";
      type boolean;
      description "FlexLSP Entry Exists";
    }
    leaf in-label {
      xr:xr-xml-map "mpls_lcac:InLabel";
      type uint32;
      description "In Label";
    }
    leaf bfd-created {
      xr:xr-xml-map "mpls_lcac:BfdCreated";
      type boolean;
      description "GAL BFD Session Created";
    }
    leaf bfd-up {
      xr:xr-xml-map "mpls_lcac:BfdUp";
      type boolean;
      description "GAL BFD Session Up";
    }
    leaf oam-created {
      xr:xr-xml-map "mpls_lcac:OamCreated";
      type boolean;
      description "OAM Entry Created";
    }
    leaf bfd-next-hop {
      xr:xr-xml-map "mpls_lcac:BfdNextHop";
      type inet:ipv4-address;
      description "BFD Next Hop";
    }
    leaf bfd-tun-ifh {
      xr:xr-xml-map "mpls_lcac:BfdTunIfh";
      type xr:Interface-name;
      description "BFD Tunnel Interface Handle";
    }
    leaf bfd-out-ifh {
      xr:xr-xml-map "mpls_lcac:BfdOutIfh";
      type xr:Interface-name;
      description "BFD Out Interface Handle";
    }
    leaf bfd-int-label {
      xr:xr-xml-map "mpls_lcac:BfdIntLabel";
      type uint32;
      description "BFD Internal Label";
    }
    leaf bfd-egress-label {
      xr:xr-xml-map "mpls_lcac:BfdEgressLabel";
      type uint32;
      description "BFD Egress Label";
    }
    leaf fault-ldi-lockout {
      xr:xr-xml-map "mpls_lcac:FaultLdiLockout";
      type boolean;
      description "Fault LDI Lockout";
    }
    leaf fault-ldi {
      xr:xr-xml-map "mpls_lcac:FaultLdi";
      type boolean;
      description "Fault LDI";
    }
    leaf fault-lkr {
      xr:xr-xml-map "mpls_lcac:FaultLkr";
      type boolean;
      description "Fault LKR";
    }
    leaf fault-ais {
      xr:xr-xml-map "mpls_lcac:FaultAis";
      type boolean;
      description "Fault AIS";
    }
    leaf fault-time {
      xr:xr-xml-map "mpls_lcac:FaultTime";
      type uint32;
      description "Fault Time";
    }
  }

  grouping MPLS-TE-S2L-PROTECTION-OBJECT {
    description "TE Protection Object";
    leaf s2l-secondary {
      xr:xr-xml-map "mpls_lcac:S2LSecondary";
      type boolean;
      description " S2L Protection Secondary Bit";
    }
    leaf s2l-protecting {
      xr:xr-xml-map "mpls_lcac:S2LProtecting";
      type boolean;
      description " S2L Protection Protecting Bit";
    }
    leaf s2l-notification {
      xr:xr-xml-map "mpls_lcac:S2LNotification";
      type boolean;
      description " S2L Protection Notification Bit";
    }
    leaf s2l-operational {
      xr:xr-xml-map "mpls_lcac:S2LOperational";
      type boolean;
      description " S2L Protection Operational Bit";
    }
    leaf enhanced {
      xr:xr-xml-map "mpls_lcac:Enhanced";
      type boolean;
      description "Indicates Enhanced Protection Scheme";
    }
    leaf ded1-plus1 {
      xr:xr-xml-map "mpls_lcac:Ded1Plus1";
      type boolean;
      description "Dedicated 1+1 Protection";
    }
    leaf ded1-to1 {
      xr:xr-xml-map "mpls_lcac:Ded1To1";
      type boolean;
      description "Dedicated 1:1 Protection";
    }
    leaf shared {
      xr:xr-xml-map "mpls_lcac:Shared";
      type boolean;
      description "Shared Link Layer Protection";
    }
    leaf link-unprotected {
      xr:xr-xml-map "mpls_lcac:LinkUnprotected";
      type boolean;
      description "LSP should not use any Link Layer Protection";
    }
    leaf extra-traffic {
      xr:xr-xml-map "mpls_lcac:ExtraTraffic";
      type boolean;
      description
        "LSP should use Links that are protecting other
        (primary) traffic";
    }
    leaf any {
      xr:xr-xml-map "mpls_lcac:Any";
      type boolean;
      description "Any";
    }
    leaf rerouting {
      xr:xr-xml-map "mpls_lcac:Rerouting";
      type boolean;
      description "Full Rerouting";
    }
    leaf rerouting-no-et {
      xr:xr-xml-map "mpls_lcac:ReroutingNoET";
      type boolean;
      description "Rerouting Without Extra-Traffic";
    }
    leaf one-to-n-protection-et {
      xr:xr-xml-map "mpls_lcac:OneToNProtectionET";
      type boolean;
      description "1:N Protection with Extra-Traffic";
    }
    leaf one-plus-one-uni {
      xr:xr-xml-map "mpls_lcac:OnePlusOneUni";
      type boolean;
      description "1+1 Unidirectional Protection";
    }
    leaf one-plus-one-bi {
      xr:xr-xml-map "mpls_lcac:OnePlusOneBi";
      type boolean;
      description "1+1 Bidirectional Protection";
    }
    leaf lsp-unprotected {
      xr:xr-xml-map "mpls_lcac:LSPUnprotected";
      type boolean;
      description "LSP Flags Unprotected";
    }
  }

  grouping MPLS-TE-S2L-ASSOCIATION-OBJECT {
    description "TE Association Object";
    leaf s2l-association-type {
      xr:xr-xml-map "mpls_lcac:S2LAssociationType";
      type uint16;
      description
        "S2L Association Type                         
        (draft-ietf-ccamp-mpls-tp-rsvpte-ext-associated-lsp)";
    }
    leaf s2l-association-tie-role {
      xr:xr-xml-map "mpls_lcac:S2LAssociationTieRole";
      type Te-association-tie-role;
      description "S2L Association Tie Role";
    }
    leaf s2l-association-id {
      xr:xr-xml-map "mpls_lcac:S2LAssociationID";
      type uint16;
      description "S2L Association ID";
    }
    leaf s2l-association-source {
      xr:xr-xml-map "mpls_lcac:S2LAssociationSource";
      type inet:ipv4-address;
      description "S2L Association Source";
    }
    leaf s2l-global-source {
      xr:xr-xml-map "mpls_lcac:S2LGlobalSource";
      type uint32;
      description "S2L Global Source";
    }
    leaf-list s2l-extended-id {
      xr:xr-xml-map "mpls_lcac:S2LExtendedID";
      type uint32;
      description "S2L Extended ID Array";
    }
  }

  grouping TE-S2L-SRLG-COLLECT-INFO {
    description "SRLG-collection information";
    leaf srlg-collect-type {
      xr:xr-xml-map "mpls_lcac:SRLGCollectType";
      type Te-srlg-collect-request;
      description "SRLG-collection mechanism";
    }
    leaf-list discovered-srlg {
      xr:xr-xml-map "mpls_lcac:DiscoveredSRLGs";
      type uint32;
      description "Discovered SRLGs";
    }
  }

  grouping MPLS-TE-TAIL-BFD-INFO {
    description "TE Tail-end BFD information";

    container session-info {
      description "BFD Session Info";
      uses MPLS-TE-BFD-SESSION-INFO;
    }
    leaf failure-diagnostic-code {
      xr:xr-xml-map "mpls_lcac:FailureDiagnosticCode";
      type uint32;
      description "BFD session failure diagnostic code";
    }
    leaf failure-reason {
      xr:xr-xml-map "mpls_lcac:FailureReason";
      type string;
      description "BFD session failure reason";
    }
    leaf local-discriminator {
      xr:xr-xml-map "mpls_lcac:LocalDiscriminator";
      type uint32;
      description "BFD Local Discriminator";
    }
    leaf remote-discriminator {
      xr:xr-xml-map "mpls_lcac:RemoteDiscriminator";
      type uint32;
      description "BFD Remote Discrminator";
    }
    leaf min-interval {
      xr:xr-xml-map "mpls_lcac:MinInterval";
      type uint32;
      description "Hello interval in mini second";
    }
    leaf min-interval-default {
      xr:xr-xml-map "mpls_lcac:MinIntervalDefault";
      type boolean;
      description "Is default hello interval";
    }
    leaf multiplier {
      xr:xr-xml-map "mpls_lcac:Multiplier";
      type uint8;
      description "Multiplier";
    }
    leaf multiplier-default {
      xr:xr-xml-map "mpls_lcac:MultiplierDefault";
      type boolean;
      description "Is default multiplier";
    }
  }

  grouping MPLS-TE-BFD-DELETION-HISTORY {
    description "TE Tunnel BFD Session Deletion History";
    leaf lsp-id {
      xr:xr-xml-map "mpls_lcac:LspID";
      type uint16;
      description "LSP ID of the BFD session get deleted";
    }
    leaf deletion-time {
      xr:xr-xml-map "mpls_lcac:DeletionTime";
      type uint32;
      description "Time stamp of the BFD session get deleted";
    }
    leaf deletion-reason {
      xr:xr-xml-map "mpls_lcac:DeletionReason";
      type string;
      description "Reason for the BFD session get deleted";
    }
    leaf deletion-diagnostic-code {
      xr:xr-xml-map "mpls_lcac:DeletionDiagnosticCode";
      type uint32;
      description "Diagnostic Code for the BFD session get deleted";
    }
  }

  grouping MPLS-TE-BFD-SESSION-INFO {
    description "TE BFD Session Info";
    leaf state {
      xr:xr-xml-map "mpls_lcac:State";
      type Te-bfd-lsp-session-state;
      description "BFD session state";
    }
    leaf state-change-time {
      xr:xr-xml-map "mpls_lcac:StateChangeTime";
      type uint32;
      units "second";
      description
        "Time in seconds since the last session state
        change";
    }
  }

  grouping MPLS-TE-HEAD-BFD-INFO {
    description "TE Head-end BFD information";

    container session-info {
      description "BFD Session Info";
      uses MPLS-TE-BFD-SESSION-INFO;
    }

    container deletion-history {
      description "BFD Session Deletion History";
      uses MPLS-TE-BFD-DELETION-HISTORY;
    }
    leaf creation-time {
      xr:xr-xml-map "mpls_lcac:CreationTime";
      type uint32;
      units "second";
      description "Time in seconds since the BFD session created";
    }
  }

  grouping TE-PVT-PROT-OBJ {
    description "Private Protection information signaled";
    leaf sbit {
      xr:xr-xml-map "mpls_lcac:sBit";
      type boolean;
      description "Secondary bit";
    }
    leaf pbit {
      xr:xr-xml-map "mpls_lcac:pBit";
      type boolean;
      description "Protecting bit";
    }
    leaf nbit {
      xr:xr-xml-map "mpls_lcac:nBit";
      type boolean;
      description "Notification bit ";
    }
    leaf obit {
      xr:xr-xml-map "mpls_lcac:oBit";
      type boolean;
      description "Operational bit";
    }
    leaf protect-type {
      xr:xr-xml-map "mpls_lcac:ProtectType";
      type Te-protect;
      description "LSP Protect Type";
    }
    leaf is-wtr-present {
      xr:xr-xml-map "mpls_lcac:IsWTRPresent";
      type boolean;
      description "Is Wait-to-Restore timeout present";
    }
    leaf wtr-timeout {
      xr:xr-xml-map "mpls_lcac:WTRTimeout";
      type uint32;
      description "Wait-to-Restore timeout";
    }
    leaf is-hopresent {
      xr:xr-xml-map "mpls_lcac:IsHOPresent";
      type boolean;
      description "Is Hold-Off timeout present";
    }
    leaf ho-timeout {
      xr:xr-xml-map "mpls_lcac:HOTimeout";
      type uint32;
      description "Hold-Off timeout";
    }
    leaf is-snc-mode-present {
      xr:xr-xml-map "mpls_lcac:IsSNCModePresent";
      type boolean;
      description "Is SNC mode present";
    }
    leaf snc-mode {
      xr:xr-xml-map "mpls_lcac:snc_mode";
      type Te-aps-snc-mode;
      description "SNC mode";
    }
    leaf tcm-id {
      xr:xr-xml-map "mpls_lcac:tcm_id";
      type uint32;
      description "TCM ID";
    }
    leaf path-prot-profile-type {
      xr:xr-xml-map "mpls_lcac:path_prot_profile_type";
      type Te-path-prot-profile;
      description "Path protection profile type";
    }
  }

  grouping MPLS-TE-S2L-APS-INFO {
    description "APS Protection Info of S2L";

    container protection-info {
      description "Protection Info";
      uses TE-PVT-PROT-OBJ;
    }
  }

  grouping TE-ODU-FLEX-GFP-F-NON-RES-INFO {
    description
      "ODU flex info for non-resizable GFP-F framing
      type";
    leaf bit-rate {
      xr:xr-xml-map "mpls_lcac:BitRate";
      type uint32;
      description "Bit rate in kbit/s";
    }
  }

  grouping TE-ODU-FLEX-GFP-F-RES-INFO {
    description "ODU flex info for resizable GFP-F framing type";
    leaf bit-rate {
      xr:xr-xml-map "mpls_lcac:BitRate";
      type uint32;
      description "Bit rate in kbit/s";
    }
  }

  grouping TE-ODU-FLEX-CBR-INFO {
    description "ODU flex info for CBR framing type";
    leaf bit-rate {
      xr:xr-xml-map "mpls_lcac:BitRate";
      type uint32;
      description "Bit rate in kbit/s";
    }
    leaf tolerance {
      xr:xr-xml-map "mpls_lcac:Tolerance";
      type uint16;
      description "Tolerance";
    }
  }

  grouping TE-ODU-V3-BW {
    description "ODU bandwidth union";

    container odu-flex-cbr {
      when "../odu-level = 'te-odu-level-flex-cbr'" {
        description "../ODULevel = 'TE_ODULevelFlexCBR'";
      }
      description "Odu flex CBR info";
      uses TE-ODU-FLEX-CBR-INFO;
    }

    container odu-flex-gfp-f-res {
      when "../odu-level = 'te-odu-level-flex-gfpf-resizeable'" {
        description "../ODULevel = 'TE_ODULevelFlexGFPFResizeable'";
      }
      description "Odu flex GFP-F resizable info";
      uses TE-ODU-FLEX-GFP-F-RES-INFO;
    }

    container odu-flex-gfp-f-non-res {
      when "../odu-level = 'te-odu-level-flex-gfpf-non-resizable'" {
        description
          "../ODULevel = 'TE_ODULevelFlexGFPFNonResizable'";
      }
      description "Odu flex GFP-F non-resizable info";
      uses TE-ODU-FLEX-GFP-F-NON-RES-INFO;
    }
    leaf odu-level {
      xr:xr-xml-map "mpls_lcac:ODULevel";
      type Te-odu-level;
      description "ODULevel";
    }
  }

  grouping MPLS-TE-S2L-OTN-INFO {
    description "OTN S2L's Controllers' information";

    container bandwidth {
      description "OTN Bandwidth for s2l";
      uses TE-ODU-V3-BW;
    }

    container labels {
      description "Labels";
      uses MPLS-TE-MGMT-GMPLS-LABELS;
    }
    leaf incoming-controller {
      xr:xr-xml-map "mpls_lcac:IncomingController";
      type string;
      description "Incoming Controller";
    }
    leaf incoming-controller-state {
      xr:xr-xml-map "mpls_lcac:IncomingControllerState";
      type Te-controller-state;
      description "State of Incoming Controller";
    }
    leaf incoming-sub-controller {
      xr:xr-xml-map "mpls_lcac:IncomingSubController";
      type string;
      description "Incoming Sub Controller";
    }
    leaf incoming-sub-controller-state {
      xr:xr-xml-map "mpls_lcac:IncomingSubControllerState";
      type Te-controller-state;
      description "State of Incoming Sub Controller";
    }
    leaf outgoing-controller {
      xr:xr-xml-map "mpls_lcac:OutgoingController";
      type string;
      description "Outgoing Controller";
    }
    leaf outgoing-controller-state {
      xr:xr-xml-map "mpls_lcac:OutgoingControllerState";
      type Te-controller-state;
      description "State of Outgoing Controller";
    }
    leaf outgoing-sub-controller {
      xr:xr-xml-map "mpls_lcac:OutgoingSubController";
      type string;
      description "Outgoing Sub Controller";
    }
    leaf outgoing-sub-controller-state {
      xr:xr-xml-map "mpls_lcac:OutgoingSubControllerState";
      type Te-controller-state;
      description "State of Outgoing Sub Controller";
    }
    leaf cross-connect-id {
      xr:xr-xml-map "mpls_lcac:CrossConnectID";
      type uint32;
      description "Cross connect id";
    }
    leaf is-connected {
      xr:xr-xml-map "mpls_lcac:IsConnected";
      type boolean;
      description "True if subcontrollers are connected";
    }
    leaf uptime {
      xr:xr-xml-map "mpls_lcac:Uptime";
      type uint32;
      description "XC Uptime";
    }
    leaf outgoing-controller-ifhandle {
      xr:xr-xml-map "mpls_lcac:OutgoingControllerIfhandle";
      type xr:Interface-name;
      description "Outgoing Controller Ifhandle";
    }
    leaf outgoing-sub-controller-ifhandle {
      xr:xr-xml-map "mpls_lcac:OutgoingSubControllerIfhandle";
      type xr:Interface-name;
      description "Outgoing Sub Controller Ifhandle";
    }
    leaf incoming-controller-ifhandle {
      xr:xr-xml-map "mpls_lcac:IncomingControllerIfhandle";
      type xr:Interface-name;
      description "Incoming Controller Ifhandle";
    }
    leaf incoming-sub-controller-ifhandle {
      xr:xr-xml-map "mpls_lcac:IncomingSubControllerIfhandle";
      type xr:Interface-name;
      description "Incoming Sub Controller Ifhandle";
    }
    leaf gpid {
      xr:xr-xml-map "mpls_lcac:GPID";
      type uint16;
      description "Gpid Payload";
    }
  }

  grouping MPLS-TE-OTN-S2L-INFO {
    description "OTN S2l information";

    container otn {
      description "Info Related to OTN technology in S2L";
      uses MPLS-TE-S2L-OTN-INFO;
    }

    container aps {
      description "APS Info for OTN S2L";
      uses MPLS-TE-S2L-APS-INFO;
    }
  }

  grouping MPLS-TE-MGMT-G709-OTN-FIXED-SIZE-LABEL {
    description "GMPLS G709 OTN fixed-size Label";
    leaf tpn {
      xr:xr-xml-map "mpls_lcac:TPN";
      type uint16;
      description "Tributary time slot";
    }
    leaf bit-map-length {
      xr:xr-xml-map "mpls_lcac:BitMapLength";
      type uint16;
      description "Bit map length";
    }
    leaf-list bit-map {
      xr:xr-xml-map "mpls_lcac:BitMap";
      type uint8;
      description "Bit Map";
    }
  }

  grouping MPLS-TE-MGMT-WDM-FIXED-GRID-LABEL {
    description "GMPLS WDM fixed-grid Label";
    leaf label-set {
      xr:xr-xml-map "mpls_lcac:LabelSet";
      type boolean;
      description "Flag to indicate whether label is set";
    }
    leaf grid {
      xr:xr-xml-map "mpls_lcac:Grid";
      type Gmpls-uni-mgmt-wdm-grid;
      description "Grid";
    }
    leaf channel-spacing {
      xr:xr-xml-map "mpls_lcac:ChannelSpacing";
      type Gmpls-uni-mgmt-dwdm-cs;
      description "Channel spacing";
    }
    leaf identifier {
      xr:xr-xml-map "mpls_lcac:Identifier";
      type uint16;
      description "Identifier";
    }
    leaf channel {
      xr:xr-xml-map "mpls_lcac:Channel";
      type int16;
      description "Channel Number";
    }
  }

  grouping MPLS-TE-MGMT-GMPLS-LABEL {
    description "A GMPLS label";

    container wdm {
      when "../label-type = 'fixed-wdm'" {
        description "../LabelType = 'FixedWDM'";
      }
      description "Fixed-grid WDM label";
      uses MPLS-TE-MGMT-WDM-FIXED-GRID-LABEL;
    }

    container otn {
      when "../label-type = 'fixed-g709otn'" {
        description "../LabelType = 'FixedG709OTN'";
      }
      description "Fixed-size G09 OTN label";
      uses MPLS-TE-MGMT-G709-OTN-FIXED-SIZE-LABEL;
    }
    leaf label-type {
      xr:xr-xml-map "mpls_lcac:LabelType";
      type Mpls-te-mgmt-gmpls-label;
      description "LabelType";
    }
  }

  grouping MPLS-TE-MGMT-GMPLS-LABELS {
    description "GMPLS Labels";

    container path-ingress-label {
      description "Path message (upstream) ingress label";
      uses MPLS-TE-MGMT-GMPLS-LABEL;
    }

    container path-egress-label {
      description "Path message (upstream) egress label";
      uses MPLS-TE-MGMT-GMPLS-LABEL;
    }

    container resv-ingress-label {
      description "Resv message (downstream) ingress label";
      uses MPLS-TE-MGMT-GMPLS-LABEL;
    }

    container resv-egress-label {
      description "Resv message (downstream) egress label";
      uses MPLS-TE-MGMT-GMPLS-LABEL;
    }
  }

  grouping MPLS-TE-SOFT-PREEMPTION-LSP-INFO {
    description "Midpoint Soft Preemption LSP Info";
    leaf status {
      xr:xr-xml-map "mpls_lcac:Status";
      type Mpls-te-soft-preemption-state;
      description
        "The current state of the soft preemption
        operation";
    }
    leaf soft-preemption-timestamp {
      xr:xr-xml-map "mpls_lcac:SoftPreemptionTimestamp";
      type uint32;
      description
        "The POSIX timestamp when the soft preemption
        occurred";
    }
    leaf soft-preemption-link {
      xr:xr-xml-map "mpls_lcac:SoftPreemptionLink";
      type string;
      description
        "Name of the link where the soft preemption
        occurred";
    }
    leaf preempting-link-address {
      xr:xr-xml-map "mpls_lcac:PreemptingLinkAddress";
      type inet:ipv4-address;
      description
        "The address of the link where the preemption
        happened";
    }
    leaf time-to-hard-preemption {
      xr:xr-xml-map "mpls_lcac:TimeToHardPreemption";
      type uint16;
      units "second";
      description
        "The number of seconds until hard preemption is
        triggered";
    }
    leaf fr-rrewrite {
      xr:xr-xml-map "mpls_lcac:FRRrewrite";
      type boolean;
      description "FRR-rewrite during soft preemption";
    }
    leaf fr-rrewrite-tunnel-name {
      xr:xr-xml-map "mpls_lcac:FRRrewriteTunnelName";
      type string;
      description "The tunnel name of the backup";
    }
  }

  grouping TE-LSP-CONVERGENCE-INFO {
    description "TE LSP convergence related information";
    leaf path-in {
      xr:xr-xml-map "mpls_lcac:PathIn";
      type uint64;
      units "nanosecond";
      description "LSP RSVP Path-in timestamp (clocktime in nsecs)";
    }
    leaf path-out {
      xr:xr-xml-map "mpls_lcac:PathOut";
      type uint64;
      units "nanosecond";
      description "LSP RSVP Path-in timestamp (clocktime in nsecs)";
    }
    leaf resv-in {
      xr:xr-xml-map "mpls_lcac:ResvIn";
      type uint64;
      units "nanosecond";
      description "LSP RSVP Resv-in timestamp (clocktime in nsecs)";
    }
    leaf resv-out {
      xr:xr-xml-map "mpls_lcac:ResvOut";
      type uint64;
      units "nanosecond";
      description
        "LSP RSVP Resv-out timestamp (clocktime in nsecs)";
    }
    leaf label-rewrite {
      xr:xr-xml-map "mpls_lcac:LabelRewrite";
      type uint64;
      units "nanosecond";
      description
        "LSP Label rewrite timestamp (clocktime in nsecs)";
    }
    leaf tunnel-rewrite {
      xr:xr-xml-map "mpls_lcac:TunnelRewrite";
      type uint64;
      units "nanosecond";
      description "Tunnel rewrite timestamp (clocktime in nsecs)";
    }
  }

  grouping TE-MGMT-G709-OTN-FSPEC {
    description "TE G709 OTN FSpec";
    leaf signal-type {
      xr:xr-xml-map "mpls_lcac:SignalType";
      type uint8;
      description "Signal Type";
    }
    leaf nmc-or-tolerance {
      xr:xr-xml-map "mpls_lcac:NMCOrTolerance";
      type uint16;
      description "NMC or Tolerance";
    }
    leaf nvc {
      xr:xr-xml-map "mpls_lcac:NVC";
      type uint16;
      description "Number of Virtual Components";
    }
    leaf multiplier {
      xr:xr-xml-map "mpls_lcac:Multiplier";
      type uint16;
      description "Multiplier";
    }
    leaf bit-rate {
      xr:xr-xml-map "mpls_lcac:BitRate";
      type uint32;
      units "kbit/s";
      description "Bit Rate in kbps";
    }
  }

  grouping TE-MGMT-GENERIC-FSPEC {
    description "Union of different TE generic FSpec types";

    container otnfspec {
      when "../fspec-type = 'te-generic-fspec-type-g709otn'" {
        description "../FSpecType = 'TEGenericFSpecTypeG709OTN'";
      }
      description "TE FSpec for G709 OTN";
      uses TE-MGMT-G709-OTN-FSPEC;
    }
    leaf fspec-type {
      xr:xr-xml-map "mpls_lcac:FSpecType";
      type Te-mgmt-generic-fspec;
      description "FSpecType";
    }
  }

  grouping TE-MGMT-G709-OTN-TSPEC {
    description "TE G709 OTN TSpec";
    leaf signal-type {
      xr:xr-xml-map "mpls_lcac:SignalType";
      type uint8;
      description "Signal Type";
    }
    leaf nmc-or-tolerance {
      xr:xr-xml-map "mpls_lcac:NMCOrTolerance";
      type uint16;
      description "NMC or Tolerance";
    }
    leaf nvc {
      xr:xr-xml-map "mpls_lcac:NVC";
      type uint16;
      description "Number of Virtual Components";
    }
    leaf multiplier {
      xr:xr-xml-map "mpls_lcac:Multiplier";
      type uint16;
      description "Multiplier";
    }
    leaf bit-rate {
      xr:xr-xml-map "mpls_lcac:BitRate";
      type uint32;
      units "kbit/s";
      description "Bit Rate in kbps";
    }
  }

  grouping TE-MGMT-GENERIC-TSPEC {
    description "Union of different TE generic TSpec types";

    container otntspec {
      when "../tspec-type = 'te-generic-tspec-type-g709otn'" {
        description "../TSpecType = 'TEGenericTSpecTypeG709OTN'";
      }
      description "TE TSpec for G709 OTN";
      uses TE-MGMT-G709-OTN-TSPEC;
    }
    leaf tspec-type {
      xr:xr-xml-map "mpls_lcac:TSpecType";
      type Te-mgmt-generic-tspec;
      description "TSpecType";
    }
  }

  grouping BANDWIDTH-SPEC-BAG {
    description "Bandwidth information of a flow";
    leaf average-rate {
      xr:xr-xml-map "mpls_lcac:AverageRate";
      type uint64;
      units "kbit/s";
      description "Average bandwidth in  kbps";
    }
    leaf maximum-burst {
      xr:xr-xml-map "mpls_lcac:MaximumBurst";
      type uint64;
      units "byte";
      description "Maximum burst of data in bytes";
    }
    leaf peak-rate {
      xr:xr-xml-map "mpls_lcac:PeakRate";
      type uint64;
      units "kbit/s";
      description "Peak rate in  kbps";
    }
  }

  grouping TUNNEL-HOP-INFO {
    description "Hop information";
    leaf hop-address {
      xr:xr-xml-map "mpls_lcac:HopAddress";
      type inet:ipv4-address;
      description "Hop address";
    }
    leaf hop-affinity {
      xr:xr-xml-map "mpls_lcac:HopAffinity";
      type uint32;
      description "Deprecated";
    }
    leaf-list hop-extended-affinity {
      xr:xr-xml-map "mpls_lcac:HopExtendedAffinity";
      type uint32;
      description "Hop affinity";
    }
  }

  grouping RSVP-MGMT-RRO-SRLG-SUBOBJ {
    description "RSVP RRO SRLG subobject";
    leaf-list srl-gs {
      xr:xr-xml-map "mpls_lcac:SRLGs";
      type uint32;
      description "The RRO Subobject SRLGs";
    }
  }

  grouping RSVP-MGMT-RRO-UNNUMBERED-SUBOBJ-FLAGS {
    description "RSVP RRO UNNUMBERED Subobject Flags";
    leaf is-protection-available {
      xr:xr-xml-map "mpls_lcac:IsProtectionAvailable";
      type boolean;
      description "Local Protection Available";
    }
    leaf is-protection-in-use {
      xr:xr-xml-map "mpls_lcac:IsProtectionInUse";
      type boolean;
      description "Local Protection In Use";
    }
    leaf is-bandwidth-protected {
      xr:xr-xml-map "mpls_lcac:IsBandwidthProtected";
      type boolean;
      description "Bandwidth Protection Available";
    }
    leaf is-node-protection-available {
      xr:xr-xml-map "mpls_lcac:IsNodeProtectionAvailable";
      type boolean;
      description "Node Protection Available";
    }
    leaf is-node-id {
      xr:xr-xml-map "mpls_lcac:IsNodeID";
      type boolean;
      description "Node ID In Use";
    }
  }

  grouping RSVP-MGMT-RRO-UNNUMBERED-SUBOBJ {
    description "RSVP RRO Unnumbered subobject";

    container flags {
      description "The RRO Subobject Unnumbered Flags";
      uses RSVP-MGMT-RRO-UNNUMBERED-SUBOBJ-FLAGS;
    }
    leaf interface-address {
      xr:xr-xml-map "mpls_lcac:InterfaceAddress";
      type inet:ipv4-address;
      description "The RRO Interface Address";
    }
    leaf interface-id {
      xr:xr-xml-map "mpls_lcac:InterfaceID";
      type uint32;
      description "The RRO Interface ID";
    }
  }

  grouping RSVP-MGMT-RRO-LABEL-SUBOBJ-FLAGS {
    description "RSVP RRO Label Subobject Flags";
    leaf is-global-label {
      xr:xr-xml-map "mpls_lcac:IsGlobalLabel";
      type boolean;
      description "Label is Global across all interfaces";
    }
  }

  grouping RSVP-MGMT-RRO-LABEL-SUBOBJ {
    description "RSVP RRO Label subobject";

    container flags {
      description "The RRO Subobject Label Flags";
      uses RSVP-MGMT-RRO-LABEL-SUBOBJ-FLAGS;
    }
    leaf label {
      xr:xr-xml-map "mpls_lcac:Label";
      type uint32;
      description "The RRO Subobject Label Value";
    }
    leaf is-label-variable-length {
      xr:xr-xml-map "mpls_lcac:IsLabelVariableLength";
      type boolean;
      description "Is the RRO Subobject Label Variable Length";
    }
    leaf-list variable-length-label {
      xr:xr-xml-map "mpls_lcac:VariableLengthLabel";
      type uint32;
      description "The RRO Subobject Variable Length Label";
    }
  }

  grouping RSVP-MGMT-RRO-IPV4-SUBOBJ-FLAGS {
    description "RSVP RRO IPV4 Subobject Flags";
    leaf is-protection-available {
      xr:xr-xml-map "mpls_lcac:IsProtectionAvailable";
      type boolean;
      description "Local Protection Available";
    }
    leaf is-protection-in-use {
      xr:xr-xml-map "mpls_lcac:IsProtectionInUse";
      type boolean;
      description "Local Protection In Use";
    }
    leaf is-bandwidth-protected {
      xr:xr-xml-map "mpls_lcac:IsBandwidthProtected";
      type boolean;
      description "Bandwidth Protection Available";
    }
    leaf is-node-protection-available {
      xr:xr-xml-map "mpls_lcac:IsNodeProtectionAvailable";
      type boolean;
      description "Node Protection Available";
    }
    leaf is-node-id {
      xr:xr-xml-map "mpls_lcac:IsNodeID";
      type boolean;
      description "Node ID In Use";
    }
  }

  grouping RSVP-MGMT-RRO-IPV4-SUBOBJ {
    description "RSVP RRO IPV4 subobject";

    container flags {
      description "The RRO IPV4 Subobject Flags";
      uses RSVP-MGMT-RRO-IPV4-SUBOBJ-FLAGS;
    }
    leaf rro-address {
      xr:xr-xml-map "mpls_lcac:RROAddress";
      type inet:ipv4-address;
      description "The RRO IPV4 Address";
    }
  }

  grouping RSVP-MGMT-RRO-SUBOBJ {
    description "Union of the different RSVP RRO types";

    container ipv4rro-sub-object {
      when "../rro-type = 'ipv4rro-type'" {
        description "../RROType = 'IPv4RROType'";
      }
      description "IPV4 RRO Sub Object";
      uses RSVP-MGMT-RRO-IPV4-SUBOBJ;
    }

    container label-rro-sub-object {
      when "../rro-type = 'label-rro-type'" {
        description "../RROType = 'LabelRROType'";
      }
      description "Label RRO Sub Object";
      uses RSVP-MGMT-RRO-LABEL-SUBOBJ;
    }

    container unnumbered-rro-sub-object {
      when "../rro-type = 'unnumbered-rro-type'" {
        description "../RROType = 'UnnumberedRROType'";
      }
      description "Unnumbered RRO Sub Object";
      uses RSVP-MGMT-RRO-UNNUMBERED-SUBOBJ;
    }

    container srlg-rro-sub-object {
      when "../rro-type = 'srlg-rro-type'" {
        description "../RROType = 'SRLG_RROType'";
      }
      description "SRLG RRO Sub Object";
      uses RSVP-MGMT-RRO-SRLG-SUBOBJ;
    }
    leaf rro-type {
      xr:xr-xml-map "mpls_lcac:RROType";
      type Rsvp-mgmt-rro-subobj;
      description "RROType";
    }
  }

  grouping RSVP-MGMT-ERO-UNNUM-SUBOBJ {
    description "RSVP ERO UNNUM subobject";
    leaf is-strict-route {
      xr:xr-xml-map "mpls_lcac:IsStrictRoute";
      type boolean;
      description "ERO Entry Is Strict";
    }
    leaf ero-interface-id {
      xr:xr-xml-map "mpls_lcac:EROInterfaceID";
      type uint32;
      description "The Interface ID in ERO";
    }
    leaf ero-router-id {
      xr:xr-xml-map "mpls_lcac:ERORouterID";
      type inet:ipv4-address;
      description "The Router ID in ERO";
    }
    leaf status {
      xr:xr-xml-map "mpls_lcac:Status";
      type Rsvp-mgmt-ero-subobj-status;
      description "Status of ERO";
    }
  }

  grouping RSVP-MGMT-ERO-IPV4-SUBOBJ {
    description "RSVP ERO IPV4 subobject";
    leaf is-strict-route {
      xr:xr-xml-map "mpls_lcac:IsStrictRoute";
      type boolean;
      description "ERO Entry Is Strict";
    }
    leaf ero-address {
      xr:xr-xml-map "mpls_lcac:EROAddress";
      type inet:ipv4-address;
      description "The ERO IPV4 Address";
    }
    leaf prefix-length {
      xr:xr-xml-map "mpls_lcac:PrefixLength";
      type uint8;
      description "ERO Prefix Length";
    }
  }

  grouping RSVP-MGMT-ERO-SUBOBJ {
    description "Union of the different RSVP ERO types";

    container ipv4ero-sub-object {
      when "../ero-type = 'rsvp-mgmt-ero-type-ipv4'" {
        description "../EROType = 'RSVP_MGMT_ERO_TYPE_IPv4'";
      }
      description "IPV4 ERO Sub Object";
      uses RSVP-MGMT-ERO-IPV4-SUBOBJ;
    }

    container unnumbered-ero-sub-object {
      when "../ero-type = 'rsvp-mgmt-ero-type-un-num'" {
        description "../EROType = 'RSVP_MGMT_ERO_TYPE_UNNUM'";
      }
      description "Unnumbered ERO Sub Object";
      uses RSVP-MGMT-ERO-UNNUM-SUBOBJ;
    }
    leaf ero-type {
      xr:xr-xml-map "mpls_lcac:EROType";
      type Rsvp-mgmt-ero-subobj;
      description "EROType";
    }
  }

  grouping MPLS-TE-P2MP-SIG-ERROR {
    description "P2MP signalling error";
    leaf error-node {
      xr:xr-xml-map "mpls_lcac:ErrorNode";
      type uint32;
      description "Source address of the error generating node";
    }
    leaf error {
      xr:xr-xml-map "mpls_lcac:Error";
      type uint8;
      description "Path Error code";
    }
    leaf sub-code {
      xr:xr-xml-map "mpls_lcac:SubCode";
      type uint16;
      description "Path Error subcode";
    }
    leaf lsp-mode {
      xr:xr-xml-map "mpls_lcac:LSPMode";
      type Mpls-te-lsp-mode;
      description "LSPMode";
    }
    leaf log-time {
      xr:xr-xml-map "mpls_lcac:LogTime";
      type uint32;
      units "second";
      description
        "Time in seconds when the error message is logged";
    }
    leaf signalling-lsp-id {
      xr:xr-xml-map "mpls_lcac:SignallingLSP_ID";
      type uint16;
      description "LSP-id for which the error was received";
    }
    leaf error-message {
      xr:xr-xml-map "mpls_lcac:ErrorMessage";
      type string;
      description "Error message (for display purposes only)";
    }
    leaf reverse-lsp {
      xr:xr-xml-map "mpls_lcac:ReverseLSP";
      type boolean;
      description "Indicates if error is on the reverse LSP";
    }
  }

  grouping MPLS-TE-P2MP-PCALC-ERROR {
    description "Path computation error information";
    leaf error-message {
      xr:xr-xml-map "mpls_lcac:ErrorMessage";
      type string;
      description "Error message (for display purposes only)";
    }
    leaf lsp-mode {
      xr:xr-xml-map "mpls_lcac:LSPMode";
      type Mpls-te-lsp-mode;
      description "LSP Mode";
    }
    leaf log-time {
      xr:xr-xml-map "mpls_lcac:LogTime";
      type uint32;
      units "second";
      description
        "Time in seconds seconds (since Jan. 1, 1970)
        when the error message is logged";
    }
  }

  grouping MPLS-TE-ATTRIBUTE-SET-SR-PREPEND-ENTRY {
    description "TE segment routing prepend entry";
    leaf type {
      xr:xr-xml-map "mpls_lcac:Type";
      type Te-attribute-set-sr-prepend;
      description "Prepend Type";
    }
    leaf index {
      xr:xr-xml-map "mpls_lcac:Index";
      type uint32;
      description "Prepend index";
    }
    leaf next-label {
      xr:xr-xml-map "mpls_lcac:NextLabel";
      type uint32;
      description "Prepend next label";
    }
  }

  grouping MPLS-TE-ATTRIBUTE-SET-SR-PREPEND-LIST {
    description "TE segment routing prepend list";

    list prepend-entry {
      description "List of prepend entries";
      uses MPLS-TE-ATTRIBUTE-SET-SR-PREPEND-ENTRY;
    }
  }

  grouping MPLS-TE-ATTRIBUTE-SET-P2P-TE {
    description "TE P2P-TE Attribute Set";

    container affinity {
      description "Affinity";
      uses MPLS-TE-TUNNELS-AFFINITY-INFO;
    }

    container logging {
      description "Logging attributes";
      uses MPLS-TE-LOGGING-ATTRIBUTES;
    }

    container prepend-list {
      description "SR prepend list";
      uses MPLS-TE-ATTRIBUTE-SET-SR-PREPEND-LIST;
    }
    leaf is-affinity-configured {
      xr:xr-xml-map "mpls_lcac:IsAffinityConfigured";
      type boolean;
      description "Is affinity configured";
    }
    leaf path-selection-segment-routing-adjacency-protection {
      xr:xr-xml-map "mpls_lcac:PathSelectionSegmentRoutingAdjacency"+
        "Protection";
      type Te-s2l-sr-path-selection;
      description "Path selection segment-routing type";
    }
    leaf is-path-selection-segment-routing-adjacency-protection-configured {
      xr:xr-xml-map "mpls_lcac:IsPathSelectionSegmentRoutingAdjacen"+
        "cyProtectionConfigured";
      type boolean;
      description "Is path selection segment routing configured";
    }
    leaf path-invalidation-timeout {
      xr:xr-xml-map "mpls_lcac:PathInvalidationTimeout";
      type uint32;
      description "Path invalidation timeout on the tunnel path";
    }
    leaf path-selection-invalidation-action {
      xr:xr-xml-map "mpls_lcac:PathSelectionInvalidationAction";
      type Te-path-inval-action;
      description "Path invalidation action";
    }
    leaf is-path-invalidation-timeout-configured {
      xr:xr-xml-map "mpls_lcac:IsPathInvalidationTimeoutConfigured";
      type boolean;
      description "Is Path Invalidation timeout configured";
    }
    leaf is-path-invalidation-action-configured {
      xr:xr-xml-map "mpls_lcac:IsPathInvalidationActionConfigured";
      type boolean;
      description "Is Path Invalidation action configured";
    }
    leaf path-selection-metric {
      xr:xr-xml-map "mpls_lcac:PathSelectionMetric";
      type Mpls-te-metric;
      description "Path selection metric type";
    }
    leaf is-path-selection-metric-configured {
      xr:xr-xml-map "mpls_lcac:IsPathSelectionMetricConfigured";
      type boolean;
      description "Is path selection metric configured";
    }
    leaf path-selection-segment-routing-margin {
      xr:xr-xml-map "mpls_lcac:PathSelectionSegmentRoutingMargin";
      type uint32;
      description "Path selection margin";
    }
    leaf is-path-selection-segment-routing-margin-relative {
      xr:xr-xml-map "mpls_lcac:IsPathSelectionSegmentRoutingMarginR"+
        "elative";
      type boolean;
      description "Path selection margin is_relative";
    }
    leaf is-path-selection-segment-routing-margin-configured {
      xr:xr-xml-map "mpls_lcac:IsPathSelectionSegmentRoutingMarginC"+
        "onfigured";
      type boolean;
      description "Is path selection margin configured";
    }
    leaf path-selection-segment-routing-segment-limit {
      xr:xr-xml-map "mpls_lcac:PathSelectionSegmentRoutingSegmentLi"+
        "mit";
      type uint32;
      description "Is path selection segment limit configured";
    }
    leaf is-path-selection-segment-routing-segment-limit-configured {
      xr:xr-xml-map "mpls_lcac:IsPathSelectionSegmentRoutingSegment"+
        "LimitConfigured";
      type boolean;
      description "Is path selection segment limit configured";
    }
    leaf is-path-select-configured {
      xr:xr-xml-map "mpls_lcac:IsPathSelectConfigured";
      type boolean;
      description
        "Is any of the path selection parameters
        configured";
    }
    leaf is-prepend-list-configured {
      xr:xr-xml-map "mpls_lcac:IsPrependListConfigured";
      type boolean;
      description "Is SR prepend list configured";
    }
    leaf-list tunnel-id {
      xr:xr-xml-map "mpls_lcac:TunnelID";
      type uint16;
      description "Tunnel ID";
    }
  }

  grouping MPLS-TE-ATTRIBUTE-SET-APS-PP {
    description "TE OTN path protection attribute set";

    container revert-schedule {
      description "Revert Schedule";
      uses TE-REVERT-SCH;
    }
    leaf snc-mode {
      xr:xr-xml-map "mpls_lcac:SNCMode";
      type Te-aps-snc-mode;
      description "Sub-network Connection Mode";
    }
    leaf tcm-id {
      xr:xr-xml-map "mpls_lcac:TCMId";
      type uint32;
      description "Sub-network Connection Monitoring Mode";
    }
    leaf protection-type {
      xr:xr-xml-map "mpls_lcac:ProtectionType";
      type Te-protect;
      description "Protection Type";
    }
    leaf protection-mode {
      xr:xr-xml-map "mpls_lcac:ProtectionMode";
      type Te-pnr-revert-options;
      description "Protection Restoration Mode";
    }
    leaf wait-to-restore-time {
      xr:xr-xml-map "mpls_lcac:WaitToRestoreTime";
      type uint32;
      description "Wait to restore time";
    }
    leaf hold-off-time {
      xr:xr-xml-map "mpls_lcac:HoldOffTime";
      type uint32;
      description "Hold-off time";
    }
    leaf path-prot-profile-type {
      xr:xr-xml-map "mpls_lcac:PathProtProfileType";
      type Te-path-prot-profile;
      description "Path Protection Profile Type";
    }
    leaf restoration-style {
      xr:xr-xml-map "mpls_lcac:RestorationStyle";
      type Te-restoration-style;
      description "Restoration Style";
    }
  }

  grouping MPLS-TE-ATTRIBUTE-SET-P2MP-TE {
    description "TE P2MP-TE Attribute Set";

    container affinity {
      description "Affinity";
      uses MPLS-TE-TUNNELS-AFFINITY-INFO;
    }
    leaf fast-reroute {
      xr:xr-xml-map "mpls_lcac:FastReroute";
      type boolean;
      description "Fast reroute";
    }
    leaf frr-bandwidth-protection {
      xr:xr-xml-map "mpls_lcac:FRRBandwidthProtection";
      type boolean;
      description "FRR bandwidth protection";
    }
    leaf setup-priority {
      xr:xr-xml-map "mpls_lcac:SetupPriority";
      type uint8;
      description "Setup priority";
    }
    leaf hold-priority {
      xr:xr-xml-map "mpls_lcac:HoldPriority";
      type uint8;
      description "Hold priority";
    }
    leaf is-priority-configured {
      xr:xr-xml-map "mpls_lcac:IsPriorityConfigured";
      type boolean;
      description "Is priority configured";
    }
    leaf configured-bandwidth {
      xr:xr-xml-map "mpls_lcac:ConfiguredBandwidth";
      type uint32;
      units "kbit/s";
      description "Bandwidth value in kbps";
    }
    leaf dste-class-type {
      xr:xr-xml-map "mpls_lcac:DSTEClassType";
      type uint8;
      description "DSTE Class";
    }
    leaf is-bandwidth-configured {
      xr:xr-xml-map "mpls_lcac:IsBandwidthConfigured";
      type boolean;
      description "Is bandwidth configured";
    }
    leaf is-affinity-configured {
      xr:xr-xml-map "mpls_lcac:IsAffinityConfigured";
      type boolean;
      description "Is affinity configured";
    }
    leaf-list tunnel-id {
      xr:xr-xml-map "mpls_lcac:TunnelID";
      type uint16;
      description "Tunnel ID";
    }
  }

  grouping MPLS-TE-ATTRIBUTE-SET-XRO {
    description "TE XRO attribute set";

    container xro {
      description "The XRO specified by this attribute-set";
      uses TE-XRO;
    }
  }

  grouping MPLS-TE-ATTRIBUTE-SET-AUTO-MESH {
    description "TE Auto-mesh Attribute Set";

    container affinity {
      description "Affinity";
      uses MPLS-TE-TUNNELS-AFFINITY-INFO;
    }

    container logging {
      description "Logging attributes";
      uses MPLS-TE-LOGGING-ATTRIBUTES;
    }
    leaf configured-bandwidth {
      xr:xr-xml-map "mpls_lcac:ConfiguredBandwidth";
      type uint32;
      units "kbit/s";
      description "Bandwidth value in kbps";
    }
    leaf dste-class-type {
      xr:xr-xml-map "mpls_lcac:DSTEClassType";
      type uint8;
      description "DSTE Class";
    }
    leaf is-bandwidth-configured {
      xr:xr-xml-map "mpls_lcac:IsBandwidthConfigured";
      type boolean;
      description "Is bandwidth configured";
    }
    leaf setup-priority {
      xr:xr-xml-map "mpls_lcac:SetupPriority";
      type uint8;
      description "Setup priority";
    }
    leaf hold-priority {
      xr:xr-xml-map "mpls_lcac:HoldPriority";
      type uint8;
      description "Hold priority";
    }
    leaf is-priority-configured {
      xr:xr-xml-map "mpls_lcac:IsPriorityConfigured";
      type boolean;
      description "Is priority configured";
    }
    leaf policy-class {
      xr:xr-xml-map "mpls_lcac:PolicyClass";
      type uint8;
      description "deprecated";
    }
    leaf is-policyclass-configured {
      xr:xr-xml-map "mpls_lcac:IsPolicyclassConfigured";
      type boolean;
      description "Is policy class configured";
    }
    leaf forward-class {
      xr:xr-xml-map "mpls_lcac:ForwardClass";
      type uint32;
      description "Forward class";
    }
    leaf is-affinity-configured {
      xr:xr-xml-map "mpls_lcac:IsAffinityConfigured";
      type boolean;
      description "Is affinity configured";
    }
    leaf fast-reroute {
      xr:xr-xml-map "mpls_lcac:FastReroute";
      type boolean;
      description "Fast reroute";
    }
    leaf frr-node-protection {
      xr:xr-xml-map "mpls_lcac:FRRNodeProtection";
      type boolean;
      description "FRR Node protection";
    }
    leaf frr-bandwidth-protection {
      xr:xr-xml-map "mpls_lcac:FRRBandwidthProtection";
      type boolean;
      description "FRR bandwidth protection";
    }
    leaf record-route {
      xr:xr-xml-map "mpls_lcac:RecordRoute";
      type boolean;
      description "Record route";
    }
    leaf auto-bandwidth-collect {
      xr:xr-xml-map "mpls_lcac:AutoBandwidthCollect";
      type boolean;
      description "Auto bandwidth collect only";
    }
    leaf auto-route-announce {
      xr:xr-xml-map "mpls_lcac:AutoRouteAnnounce";
      type boolean;
      description "Announce auto route to IGP";
    }
    leaf soft-preemption-configured {
      xr:xr-xml-map "mpls_lcac:SoftPreemptionConfigured";
      type boolean;
      description "Soft preemption is configured";
    }
    leaf bandwidth {
      xr:xr-xml-map "mpls_lcac:bandwidth";
      type uint32;
      description "IM bandwidth";
    }
    leaf load-share {
      xr:xr-xml-map "mpls_lcac:LoadShare";
      type uint32;
      description "Load Share";
    }
    leaf is-interface-bw-configured {
      xr:xr-xml-map "mpls_lcac:IsInterfaceBWConfigured";
      type boolean;
      description "Is Interface BW configured";
    }
    leaf-list policy-class-entry {
      xr:xr-xml-map "mpls_lcac:PolicyClasses";
      type uint8;
      description "PBTS policy classes";
    }
    leaf-list mesh-group-id {
      xr:xr-xml-map "mpls_lcac:MeshGroupID";
      type uint32;
      description "Meshgroup ID";
    }
    leaf-list tunnel-id {
      xr:xr-xml-map "mpls_lcac:TunnelID";
      type uint16;
      description "Tunnel ID";
    }
  }

  grouping MPLS-TE-PROTECTED-IF-NAME-STR {
    description "TE Protected Interface Name String";
    leaf protected-interface {
      xr:xr-xml-map "mpls_lcac:ProtectedInterface";
      type string;
      description "Protected Interface Name";
    }
  }

  grouping MPLS-TE-LOGGING-ATTRIBUTES {
    description "TE Logging Attributes";
    leaf lsp-state {
      xr:xr-xml-map "mpls_lcac:LSPState";
      type boolean;
      description
        "LSP State logging: TRUE - enabled, FALSE -
        disabled";
    }
    leaf s2l-state {
      xr:xr-xml-map "mpls_lcac:S2LState";
      type boolean;
      description
        "S2L State logging: TRUE - enabled, FALSE -
        disabled";
    }
    leaf lsp-re-route {
      xr:xr-xml-map "mpls_lcac:LSPReRoute";
      type boolean;
      description
        "LSP re-route logging: TRUE - enabled, FALSE -
        disabled";
    }
    leaf lsp-re-opt {
      xr:xr-xml-map "mpls_lcac:LSPReOpt";
      type boolean;
      description
        "LSP re-optimization logging: TRUE - enabled,
        FALSE - disabled";
    }
    leaf lsp-insufficient-bw {
      xr:xr-xml-map "mpls_lcac:LSPInsufficientBW";
      type boolean;
      description
        "LSP insufficient bandwidth logging: TRUE -
        enabled, FALSE - disabled";
    }
    leaf lsp-bandwidth-change {
      xr:xr-xml-map "mpls_lcac:LSPBandwidthChange";
      type boolean;
      description
        "LSP bandwidth change logging: TRUE - enabled,
        FALSE - disabled";
    }
    leaf lsp-pcalc-failure-logging-enabled {
      xr:xr-xml-map "mpls_lcac:LSP_PCALCFailureLoggingEnabled";
      type boolean;
      description
        "LSP pcalc failure logging: TRUE - enabled, FALSE
        - disabled";
    }
    leaf all-logging-enabled {
      xr:xr-xml-map "mpls_lcac:AllLoggingEnabled";
      type boolean;
      description
        "All logging option: TRUE - enabled, FALSE -
        disabled";
    }
  }

  grouping MPLS-TE-ATTRIBUTE-SET-SIG-NAME {
    description "Attribute set signalled name";
    leaf name {
      xr:xr-xml-map "mpls_lcac:Name";
      type string;
      description "Signalled name";
    }
    leaf source-type {
      xr:xr-xml-map "mpls_lcac:SourceType";
      type Te-sig-name-append;
      description "Source address or name";
    }
    leaf protected-interface-type {
      xr:xr-xml-map "mpls_lcac:ProtectedInterfaceType";
      type Te-sig-name-append;
      description "Protected interface address or name";
    }
    leaf is-mp-addresses {
      xr:xr-xml-map "mpls_lcac:IsMPAddresses";
      type boolean;
      description "MP address appended";
    }
  }

  grouping MPLS-TE-ATTRIBUTE-SET-AUTO-BACKUP {
    description "TE Auto-backup Attribute Set";

    container signalled-name {
      description "Signalled name";
      uses MPLS-TE-ATTRIBUTE-SET-SIG-NAME;
    }

    container affinity {
      description "Affinity";
      uses MPLS-TE-TUNNELS-AFFINITY-INFO;
    }

    container logging {
      description "Logging attributes";
      uses MPLS-TE-LOGGING-ATTRIBUTES;
    }
    leaf is-signalled-name-configured {
      xr:xr-xml-map "mpls_lcac:IsSignalledNameConfigured";
      type boolean;
      description "Is signalled name configured";
    }
    leaf setup-priority {
      xr:xr-xml-map "mpls_lcac:SetupPriority";
      type uint8;
      description "Setup priority";
    }
    leaf hold-priority {
      xr:xr-xml-map "mpls_lcac:HoldPriority";
      type uint8;
      description "Hold priority";
    }
    leaf is-priority-configured {
      xr:xr-xml-map "mpls_lcac:IsPriorityConfigured";
      type boolean;
      description "Is priority configured";
    }
    leaf policy-class {
      xr:xr-xml-map "mpls_lcac:PolicyClass";
      type uint8;
      description "deprecated";
    }
    leaf is-policyclass-configured {
      xr:xr-xml-map "mpls_lcac:IsPolicyclassConfigured";
      type boolean;
      description "Is policy class configured";
    }
    leaf is-affinity-configured {
      xr:xr-xml-map "mpls_lcac:IsAffinityConfigured";
      type boolean;
      description "Is affinity configured";
    }
    leaf record-route {
      xr:xr-xml-map "mpls_lcac:RecordRoute";
      type boolean;
      description "Record route";
    }
    leaf-list policy-class-entry {
      xr:xr-xml-map "mpls_lcac:PolicyClasses";
      type uint8;
      description "PBTS policy classes";
    }
    leaf-list tunnel-id {
      xr:xr-xml-map "mpls_lcac:TunnelID";
      type uint16;
      description "Tunnel ID";
    }

    list protected-interface {
      description "Array of Protected Interface Names";
      uses MPLS-TE-PROTECTED-IF-NAME-STR;
    }
  }

  grouping MPLS-TE-ATTRIBUTE-SET-VERSION {
    description "TE attribute set versioning info";
    leaf attribute-type {
      xr:xr-xml-map "mpls_lcac:AttributeType";
      type string;
      description "Attribute Type";
    }
    leaf generation {
      xr:xr-xml-map "mpls_lcac:Generation";
      type uint32;
      description "Generation";
    }
    leaf is-default {
      xr:xr-xml-map "mpls_lcac:IsDefault";
      type boolean;
      description "Is default";
    }
  }

  grouping MPLS-TE-ATTRIBUTE-SET-PATH-OPTION {
    description "TE Path Option Attribute Set";

    container affinity {
      description "Affinity";
      uses MPLS-TE-TUNNELS-AFFINITY-INFO;
    }
    leaf configured-bandwidth {
      xr:xr-xml-map "mpls_lcac:ConfiguredBandwidth";
      type uint32;
      units "kbit/s";
      description "Bandwidth value in kbps";
    }
    leaf cost-limit {
      xr:xr-xml-map "mpls_lcac:CostLimit";
      type uint32;
      description "Cost limit on the tunnel path";
    }
    leaf dste-class-type {
      xr:xr-xml-map "mpls_lcac:DSTEClassType";
      type uint8;
      description "DSTE Class";
    }
    leaf bandwidth-type {
      xr:xr-xml-map "mpls_lcac:BandwidthType";
      type Mpls-te-bw-pool;
      description "The bandwidth type";
    }
    leaf is-bandwidth-configured {
      xr:xr-xml-map "mpls_lcac:IsBandwidthConfigured";
      type boolean;
      description "Is bandwidth configured";
    }
    leaf is-cost-limit-configured {
      xr:xr-xml-map "mpls_lcac:IsCostLimitConfigured";
      type boolean;
      description "Is Cost Limit configured";
    }
    leaf is-affinity-configured {
      xr:xr-xml-map "mpls_lcac:IsAffinityConfigured";
      type boolean;
      description "Is affinity configured";
    }
    leaf generation {
      xr:xr-xml-map "mpls_lcac:Generation";
      type uint32;
      description "Generation";
    }
    leaf path-invalidation-timeout {
      xr:xr-xml-map "mpls_lcac:PathInvalidationTimeout";
      type uint32;
      description "Path invalidation interval on the tunnel path";
    }
    leaf path-invalidation-action {
      xr:xr-xml-map "mpls_lcac:PathInvalidationAction";
      type uint32;
      description "Path invalidation action";
    }
    leaf is-path-invalidation-timeout-configured {
      xr:xr-xml-map "mpls_lcac:IsPathInvalidationTimeoutConfigured";
      type boolean;
      description "Is path invalidation timeout configured";
    }
    leaf is-path-invalidation-action-configured {
      xr:xr-xml-map "mpls_lcac:IsPathInvalidationActionConfigured";
      type boolean;
      description "Is path invalidation action configured";
    }
    leaf exclude-list-name {
      xr:xr-xml-map "mpls_lcac:ExcludeListName";
      type string;
      description "Exclude list name";
    }
    leaf is-exclude-list-name-configured {
      xr:xr-xml-map "mpls_lcac:IsExcludeListNameConfigured";
      type boolean;
      description "Is exclude list name configured";
    }
    leaf-list tunnel-id {
      xr:xr-xml-map "mpls_lcac:TunnelID";
      type uint16;
      description "Tunnel ID";
    }

    list version-info {
      description "Version Info";
      uses MPLS-TE-ATTRIBUTE-SET-VERSION;
    }
  }

  grouping MPLS-TE-ATTRIBUTE-SET-UNION {
    description "TE Attribute Set Union";

    container attribute-set-path-option {
      when "../tunnel-attribute-set-type ="+
        " 'tunnel-attribute-set-path-option'" {
          description
            "../TunnelAttributeSetType =
            'TunnelAttributeSetPathOption'";
      }
      description "MPLS TE Path Option Attribute Set";
      uses MPLS-TE-ATTRIBUTE-SET-PATH-OPTION;
    }

    container attribute-set-autobackup {
      when "../tunnel-attribute-set-type ="+
        " 'tunnel-attribute-set-auto-backup'" {
          description
            "../TunnelAttributeSetType =
            'TunnelAttributeSetAutoBackup'";
      }
      description "MPLS TE Auto-backup Attribute Set";
      uses MPLS-TE-ATTRIBUTE-SET-AUTO-BACKUP;
    }

    container attribute-set-automesh {
      when "../tunnel-attribute-set-type ="+
        " 'tunnel-attribute-set-auto-mesh'" {
          description
            "../TunnelAttributeSetType =
            'TunnelAttributeSetAutoMesh'";
      }
      description "MPLS TE Auto-mesh Attribute Set";
      uses MPLS-TE-ATTRIBUTE-SET-AUTO-MESH;
    }

    container attribute-set-xro {
      when "../tunnel-attribute-set-type ="+
        " 'tunnel-attribute-set-xro'" {
          description
            "../TunnelAttributeSetType =
            'TunnelAttributeSetXRO'";
      }
      description "Attribute Set XRO";
      uses MPLS-TE-ATTRIBUTE-SET-XRO;
    }

    container attribute-set-p2mpte {
      when "../tunnel-attribute-set-type ="+
        " 'tunnel-attribute-set-p2mpte'" {
          description
            "../TunnelAttributeSetType =
            'TunnelAttributeSetP2MPTE'";
      }
      description "MPLS TE P2MP-TE Attribute Set";
      uses MPLS-TE-ATTRIBUTE-SET-P2MP-TE;
    }

    container attribute-set-aps-pp {
      when "../tunnel-attribute-set-type ="+
        " 'tunnel-attribute-aps-pp'" {
          description
            "../TunnelAttributeSetType =
            'TunnelAttributeAPS_PP'";
      }
      description "Attribute Set OTN APS Path Protection";
      uses MPLS-TE-ATTRIBUTE-SET-APS-PP;
    }

    container attribute-set-p2p-te {
      when "../tunnel-attribute-set-type ="+
        " 'tunnel-attribute-set-p2p-te'" {
          description
            "../TunnelAttributeSetType =
            'TunnelAttributeSetP2P_TE'";
      }
      description "MPLS TE P2P-TE Attribute Set";
      uses MPLS-TE-ATTRIBUTE-SET-P2P-TE;
    }
    leaf tunnel-attribute-set-type {
      xr:xr-xml-map "mpls_lcac:TunnelAttributeSetType";
      type Tunnel-attribute-set;
      description "TunnelAttributeSetType";
    }
  }

  grouping MPLS-TE-ATTRIBUTE-SET {
    description "TE Attribute Set";

    container attribute-set-union {
      description "Union of Attribute Sets";
      uses MPLS-TE-ATTRIBUTE-SET-UNION;
    }
    leaf tunnel-attribute-set-name {
      xr:xr-xml-map "mpls_lcac:TunnelAttributeSetName";
      type string;
      description "Attribute Set Name";
    }
    leaf tunnel-attribute-set-name-crc32 {
      xr:xr-xml-map "mpls_lcac:TunnelAttributeSetNameCRC32";
      type uint32;
      description "Attribute Set name CRC32 value";
    }
  }

  grouping MPLS-TE-P2MP-PATH-OPTION {
    description "P2MP path-option";

    container attribute-set {
      description "The path option attribute set used by this path";
      uses MPLS-TE-ATTRIBUTE-SET;
    }

    container xro-attribute-set {
      description "The XRO attribute set used by this path-option";
      uses MPLS-TE-ATTRIBUTE-SET;
    }
    leaf option-index-is-valid {
      xr:xr-xml-map "mpls_lcac:OptionIndexIsValid";
      type boolean;
      description "The path option index is valid";
    }
    leaf option-index {
      xr:xr-xml-map "mpls_lcac:OptionIndex";
      type uint32;
      description "Path option index";
    }
    leaf path-option-name {
      xr:xr-xml-map "mpls_lcac:PathOptionName";
      type string;
      description "Path option name";
    }
    leaf path-option-type {
      xr:xr-xml-map "mpls_lcac:PathOptionType";
      type Mpls-te-pathoption;
      description "Path option type";
    }
    leaf explicit-path-name {
      xr:xr-xml-map "mpls_lcac:ExplicitPathName";
      type string;
      description "Explicit Path Name";
    }
    leaf explicit-path-id {
      xr:xr-xml-map "mpls_lcac:ExplicitPathID";
      type uint16;
      description "Explicit Path ID";
    }
    leaf holddown-duration {
      xr:xr-xml-map "mpls_lcac:HolddownDuration";
      type uint16;
      units "second";
      description "Holddown Duration (seconds)";
    }
    leaf pce-address {
      xr:xr-xml-map "mpls_lcac:PCEAddress";
      type inet:ipv4-address;
      description "PCE server address";
    }
    leaf path-option-area-id {
      xr:xr-xml-map "mpls_lcac:PathOptionAreaID";
      type string;
      description "The path-option area constraint";
    }
    leaf is-strict-explicit-path {
      xr:xr-xml-map "mpls_lcac:IsStrictExplicitPath";
      type boolean;
      description "TRUE if explicit path is strict";
    }
    leaf is-helddown {
      xr:xr-xml-map "mpls_lcac:IsHelddown";
      type boolean;
      description "TRUE if path is helddown";
    }
    leaf is-lockdown {
      xr:xr-xml-map "mpls_lcac:IsLockdown";
      type boolean;
      description "TRUE if the path is locked down";
    }
    leaf is-verbatim {
      xr:xr-xml-map "mpls_lcac:IsVerbatim";
      type boolean;
      description "TRUE if the path is verbatim";
    }
    leaf is-disabled {
      xr:xr-xml-map "mpls_lcac:IsDisabled";
      type boolean;
      description "TRUE if the path option is disabled";
    }
    leaf has-attribute-set {
      xr:xr-xml-map "mpls_lcac:HasAttributeSet";
      type boolean;
      description "TRUE if the path has an attribute set defined";
    }
    leaf attribute-set-found {
      xr:xr-xml-map "mpls_lcac:AttributeSetFound";
      type boolean;
      description
        "TRUE if the path has found the defined attribute
        set";
    }
    leaf has-xro-attribute-set {
      xr:xr-xml-map "mpls_lcac:HasXROAttributeSet";
      type boolean;
      description
        "TRUE if the path has an XRO attribute set
        configured";
    }
    leaf xro-attribute-set-found {
      xr:xr-xml-map "mpls_lcac:XROAttributeSetFound";
      type boolean;
      description "TRUE if the path's XRO attribute set is known";
    }
    leaf is-segment-routing {
      xr:xr-xml-map "mpls_lcac:IsSegmentRouting";
      type boolean;
      description "TRUE if the path is Segment-Routing";
    }
    leaf protected-by-path-option-index {
      xr:xr-xml-map "mpls_lcac:ProtectedByPathOptionIndex";
      type uint32;
      description "Path option index for Protect path options";
    }
    leaf restored-from-path-option-index {
      xr:xr-xml-map "mpls_lcac:RestoredFromPathOptionIndex";
      type uint32;
      description "Path option index for Restore path options";
    }

    list path-calculation-error {
      description "Path computation information";
      uses MPLS-TE-P2MP-PCALC-ERROR;
    }

    list remerge-error {
      description "Path computation remerge resolve info";
      uses MPLS-TE-P2MP-PCALC-ERROR;
    }

    list signalling-error {
      description "Signalling information";
      uses MPLS-TE-P2MP-SIG-ERROR;
    }
  }

  grouping MPLS-TE-P2MP-S2L {
    description "A P2MP S2L";

    container s2l-fec {
      description "FEC for the S2L";
      uses TE-S2L-FEC;
    }

    container active-path-option {
      description
        "The path option used to find the path for this
        S2L";
      uses MPLS-TE-P2MP-PATH-OPTION;
    }

    container out-xro {
      description "Outgoing XRO for this S2L";
      uses TE-XRO;
    }

    container in-xro {
      description "Incoming XRO for this S2L";
      uses TE-XRO;
    }

    container tspec {
      description "The T spec info";
      uses BANDWIDTH-SPEC-BAG;
    }

    container generic-tspec {
      description "Generic TSpec";
      uses TE-MGMT-GENERIC-TSPEC;
    }

    container fspec {
      description "The F spec info";
      uses BANDWIDTH-SPEC-BAG;
    }

    container generic-fspec {
      description "Generic FSpec";
      uses TE-MGMT-GENERIC-FSPEC;
    }

    container next-hop-address-generic {
      description "Next hop address";
      uses TE-ADDR;
    }

    container previous-hop-address-generic {
      description "Previous hop address";
      uses TE-ADDR;
    }

    container incoming-address-generic {
      description "Incoming interface address";
      uses TE-ADDR;
    }

    container s2l-convergence {
      description "TE LSP convergence related information";
      uses TE-LSP-CONVERGENCE-INFO;
    }

    container soft-preemption {
      description "The soft preemption info for this LSP.";
      uses MPLS-TE-SOFT-PREEMPTION-LSP-INFO;
    }

    container gmpls-labels {
      description "GMPLS labels";
      uses MPLS-TE-MGMT-GMPLS-LABELS;
    }

    container otn-s2l {
      description "Otn S2L Information";
      uses MPLS-TE-OTN-S2L-INFO;
    }

    container head-end-bfd-info {
      description "The Head-end BFD info";
      uses MPLS-TE-HEAD-BFD-INFO;
    }

    container tail-end-bfd-info {
      description "The Tail-end BFD info";
      uses MPLS-TE-TAIL-BFD-INFO;
    }

    container srlg-collection {
      description "SRLG-collection data";
      uses TE-S2L-SRLG-COLLECT-INFO;
    }

    container association {
      description "Association Object";
      uses MPLS-TE-S2L-ASSOCIATION-OBJECT;
    }

    container protection {
      description "Protection Object";
      uses MPLS-TE-S2L-PROTECTION-OBJECT;
    }

    container reverse-lsp-fec {
      description "Reverse Associated Bidir LSP FEC";
      uses TE-LSP-FEC;
    }

    container reverse-tspec {
      description "The Reverse T spec info";
      uses BANDWIDTH-SPEC-BAG;
    }

    container flex-info {
      description "FlexLSP S2L Information";
      uses MPLS-TE-S2L-FLEX-INFO;
    }

    container lsp-wrap-info {
      description "Lsp Wrap  Related information";
      uses TUNNEL-MIDPOINT-LSP-WRAP-INFO-BAG;
    }

    container diversity-info {
      description "S2L Diversity Information";
      uses MPLS-TE-S2L-DIVERSITY-INFO;
    }
    leaf pcalc-area {
      xr:xr-xml-map "mpls_lcac:PCALCArea";
      type string;
      description "IGP-area in which the S2L path was calculated";
    }
    leaf is-expanded-ero {
      xr:xr-xml-map "mpls_lcac:IsExpandedERO";
      type boolean;
      description "TRUE if this LSR expanded a loose path";
    }
    leaf path-reeval-query-mid {
      xr:xr-xml-map "mpls_lcac:PathReevalQueryMid";
      type uint32;
      description
        "Loose path reevaluation query received at
        mid-point";
    }
    leaf time-since-last-query-received-mid {
      xr:xr-xml-map "mpls_lcac:TimeSinceLastQueryReceivedMid";
      type uint32;
      description
        "Time since last reevaluation query received at
        mid-point";
    }
    leaf time-since-last-preferred-path-exists-send-mid {
      xr:xr-xml-map "mpls_lcac:TimeSinceLastPreferredPathExistsSend"+
        "Mid";
      type uint32;
      description
        "Time since last preferred path exists msg send
        from mid-point";
    }
    leaf time-since-last-preferred-tree-exists-send-mid {
      xr:xr-xml-map "mpls_lcac:TimeSinceLastPreferredTreeExistsSend"+
        "Mid";
      type uint32;
      description
        "Time since last preferred tree exists msg send
        from mid-point";
    }
    leaf expanded-ero-area-id {
      xr:xr-xml-map "mpls_lcac:ExpandedEROAreaID";
      type string;
      description
        "Indicates the protocol and area used to find
        Outgoing ERO";
    }
    leaf expanded-ero-affinity-bits {
      xr:xr-xml-map "mpls_lcac:ExpandedEROAffinityBits";
      type uint32;
      description "The Outgoing ERO's affinity bits (colors)";
    }
    leaf expanded-ero-affinity-mask {
      xr:xr-xml-map "mpls_lcac:ExpandedEROAffinityMask";
      type uint32;
      description "The Outgoing ERO's affinity mask (colors)";
    }
    leaf expanded-ero-metric-type {
      xr:xr-xml-map "mpls_lcac:ExpandedEROMetricType";
      type Mpls-te-metric;
      description "The Outgoing ERO's selection metric";
    }
    leaf expanded-ero-metric {
      xr:xr-xml-map "mpls_lcac:ExpandedEROMetric";
      type uint32;
      description "The metric value of the expanded path";
    }
    leaf abr-auto-discovered {
      xr:xr-xml-map "mpls_lcac:ABRAutoDiscovered";
      type inet:ipv4-address;
      description "Next ABR auto discovered";
    }
    leaf is-frr-enabled {
      xr:xr-xml-map "mpls_lcac:IsFRREnabled";
      type boolean;
      description "FRR Enabled or Disabled";
    }
    leaf is-node-protected {
      xr:xr-xml-map "mpls_lcac:IsNodeProtected";
      type boolean;
      description "Node Protection Enabled or Disabled";
    }
    leaf is-bandwidth-protect {
      xr:xr-xml-map "mpls_lcac:IsBandwidthProtect";
      type boolean;
      description "BW Protection Enabled or Disabled";
    }
    leaf path-rro-enabled {
      xr:xr-xml-map "mpls_lcac:PathRROEnabled";
      type boolean;
      description "Path RRO Enabled or Disabled";
    }
    leaf weight {
      xr:xr-xml-map "mpls_lcac:Weight";
      type uint64;
      description "The path's weight";
    }
    leaf reverse-weight {
      xr:xr-xml-map "mpls_lcac:ReverseWeight";
      type uint64;
      description "The reverse path weight";
    }
    leaf uptime {
      xr:xr-xml-map "mpls_lcac:Uptime";
      type uint32;
      units "second";
      description "Time in seconds since the tunnel was up";
    }
    leaf egress-interface {
      xr:xr-xml-map "mpls_lcac:EgressInterface";
      type string;
      description "Egress Interface";
    }
    leaf egress-interface-state {
      xr:xr-xml-map "mpls_lcac:EgressInterfaceState";
      type Te-controller-state;
      description "State of Outgoing Interface";
    }
    leaf egress-interface-brief {
      xr:xr-xml-map "mpls_lcac:EgressInterfaceBrief";
      type string;
      description "Egress Interface in brief format";
    }
    leaf ingress-interface {
      xr:xr-xml-map "mpls_lcac:IngressInterface";
      type string;
      description "Ingress Interface";
    }
    leaf ingress-interface-state {
      xr:xr-xml-map "mpls_lcac:IngressInterfaceState";
      type Te-controller-state;
      description "State of Incoming Interface";
    }
    leaf ingress-interface-brief {
      xr:xr-xml-map "mpls_lcac:IngressInterfaceBrief";
      type string;
      description "Ingress Interface in brief format";
    }
    leaf s2l-local-label {
      xr:xr-xml-map "mpls_lcac:S2LLocalLabel";
      type uint32;
      description "Local label";
    }
    leaf s2l-out-label {
      xr:xr-xml-map "mpls_lcac:S2LOutLabel";
      type uint32;
      description "Outgoing label";
    }
    leaf outbound-frr-state {
      xr:xr-xml-map "mpls_lcac:OutboundFRRState";
      type Mpls-te-frr-state;
      description "Indicates outbound FRR state";
    }
    leaf frr-out-tunnel-interface {
      xr:xr-xml-map "mpls_lcac:FRROutTunnelInterface";
      type string;
      description "FRR out tunnel intface";
    }
    leaf role {
      xr:xr-xml-map "mpls_lcac:Role";
      type Mpls-te-tunnel-role;
      description "Role of S2L";
    }
    leaf signalling-status {
      xr:xr-xml-map "mpls_lcac:SignallingStatus";
      type Mpls-te-tunnels-signaling-status;
      description "Signaling status";
    }
    leaf local-router-id {
      xr:xr-xml-map "mpls_lcac:LocalRouterID";
      type inet:ipv4-address;
      description "Local router id";
    }
    leaf upstream-router-id {
      xr:xr-xml-map "mpls_lcac:UpstreamRouterID";
      type inet:ipv4-address;
      description "Upstream router id";
    }
    leaf downstream-router-id {
      xr:xr-xml-map "mpls_lcac:DownstreamRouterID";
      type inet:ipv4-address;
      description "Downstream router id";
    }
    leaf next-hop-address {
      xr:xr-xml-map "mpls_lcac:NextHopAddress";
      type inet:ipv4-address;
      description "Next hop address";
    }
    leaf previous-hop-address {
      xr:xr-xml-map "mpls_lcac:PreviousHopAddress";
      type inet:ipv4-address;
      description "Previous hop address";
    }
    leaf incoming-address {
      xr:xr-xml-map "mpls_lcac:IncomingAddress";
      type inet:ipv4-address;
      description "Incoming interface address";
    }
    leaf backup-tunnel-interface {
      xr:xr-xml-map "mpls_lcac:BackupTunnelInterface";
      type xr:Interface-name;
      description "Interface handle of the backup tunnel";
    }
    leaf node-hop-count {
      xr:xr-xml-map "mpls_lcac:NodeHopCount";
      type uint8;
      description "Hop count";
    }
    leaf is-optical {
      xr:xr-xml-map "mpls_lcac:IsOptical";
      type boolean;
      description "Is Optical";
    }
    leaf s2l-reverse-ero-obj-present {
      xr:xr-xml-map "mpls_lcac:S2LReverseEROObjPresent";
      type boolean;
      description " S2l Reverse ERO Object Present";
    }
    leaf reverse-lsp-present {
      xr:xr-xml-map "mpls_lcac:ReverseLSPPresent";
      type boolean;
      description "Reverse Associated Bidir LSP Present";
    }
    leaf reverse-lsp-connected {
      xr:xr-xml-map "mpls_lcac:ReverseLSPConnected";
      type boolean;
      description "Reverse Associated Bidir LSP Connected";
    }
    leaf reverse-lsp-name {
      xr:xr-xml-map "mpls_lcac:ReverseLSPName";
      type string;
      description "Reverse Associated Bidir LSP Name";
    }
    leaf s2l-reverse-tspec-obj-present {
      xr:xr-xml-map "mpls_lcac:S2LReverseTSpecObjPresent";
      type boolean;
      description " S2L Reverse TSpec Object Present";
    }
    leaf-list s2l-reverse-lsp-sub-obj {
      xr:xr-xml-map "mpls_lcac:S2LReverseLspSubObjs";
      type uint8;
      description "Reverse LSP Sub Objects";
    }

    list shared-risk-link-group {
      description "The S2L's excluded srlg groups";
      uses MPLS-SRLG-INFO;
    }

    list out-ero {
      description "Outgoing ERO for this S2L";
      uses RSVP-MGMT-ERO-SUBOBJ;
    }

    list in-ero {
      description "Incoming ERO for this S2L";
      uses RSVP-MGMT-ERO-SUBOBJ;
    }

    list path-rro {
      description "Path RRO for this S2L";
      uses RSVP-MGMT-RRO-SUBOBJ;
    }

    list resv-rro {
      description "Resv RRO for this S2L";
      uses RSVP-MGMT-RRO-SUBOBJ;
    }

    list path-affinity-array {
      description "Tunnel's Path hops with affinity";
      uses TUNNEL-HOP-INFO;
    }

    list reverse-ero-in {
      description " Reverse Incoming ERO for this S2L";
      uses RSVP-MGMT-ERO-SUBOBJ;
    }

    list s2l-segment-routing-path {
      description "Segment-Routing S2L path info";
      uses TE-S2L-SR-PATH-HOP;
    }
  }

  grouping MPLS-TE-P2MP-LSP {
    description "A P2MP LSP";

    container lsp-fec {
      description "FEC for the LSP";
      uses TE-LSP-FEC;
    }
    leaf signaled-name {
      xr:xr-xml-map "mpls_lcac:SignaledName";
      type string;
      description "Signaled Name";
    }
    leaf is-frr-failed {
      xr:xr-xml-map "mpls_lcac:IsFRRFailed";
      type boolean;
      description "P2MP LSP has FRR Failed";
    }
    leaf frr-active-reason {
      xr:xr-xml-map "mpls_lcac:FRRActiveReason";
      type uint32;
      description "P2MP LSP FRR active reason";
    }
    leaf lsp-bandwidth {
      xr:xr-xml-map "mpls_lcac:LSPBandwidth";
      type uint32;
      description "P2MP LSP Bandwidth";
    }
    leaf lsp-setup-priority {
      xr:xr-xml-map "mpls_lcac:LSPSetupPriority";
      type uint8;
      description "LSP setup priority";
    }
    leaf lsp-hold-priority {
      xr:xr-xml-map "mpls_lcac:LSPHoldPriority";
      type uint8;
      description "LSP hold priority";
    }
    leaf lsp-bandwidth-type {
      xr:xr-xml-map "mpls_lcac:LSPBandwidthType";
      type Mpls-te-bw-pool;
      description "The LSP bandwidth type";
    }
    leaf dste-class-match {
      xr:xr-xml-map "mpls_lcac:DSTEClassMatch";
      type boolean;
      description
        "Do the class type and priority match a DSTE
        class";
    }
    leaf dste-class-index {
      xr:xr-xml-map "mpls_lcac:DSTEClassIndex";
      type uint8;
      description "Matching DSTE class index";
    }
    leaf type {
      xr:xr-xml-map "mpls_lcac:Type";
      type Mpls-te-lsp;
      description "The type of this LSP";
    }
    leaf uptime {
      xr:xr-xml-map "mpls_lcac:Uptime";
      type uint32;
      units "second";
      description "Time in seconds since the tunnel was up";
    }
    leaf s2-ls-up {
      xr:xr-xml-map "mpls_lcac:S2LsUp";
      type uint32;
      description "Number of connected S2Ls";
    }
    leaf s2-ls-proceeding {
      xr:xr-xml-map "mpls_lcac:S2LsProceeding";
      type uint32;
      description "Number of proceeding S2Ls";
    }
    leaf s2-ls-down {
      xr:xr-xml-map "mpls_lcac:S2LsDown";
      type uint32;
      description "Number of down S2Ls";
    }
    leaf reoptimize-reason {
      xr:xr-xml-map "mpls_lcac:ReoptimizeReason";
      type Mpls-te-reopt-decision-reason;
      description "Reason for re-optimization";
    }
    leaf reoptimize-trigger {
      xr:xr-xml-map "mpls_lcac:ReoptimizeTrigger";
      type Mte-reopt-trigger;
      description "Re-optimize trigger";
    }
    leaf timer-left {
      xr:xr-xml-map "mpls_lcac:TimerLeft";
      type uint32;
      units "second";
      description "Time in seconds left to take next action if any";
    }
    leaf is-passive {
      xr:xr-xml-map "mpls_lcac:IsPassive";
      type boolean;
      description "True for passive tunnel";
    }

    list s2l {
      description "array of S2L structures";
      uses MPLS-TE-P2MP-S2L;
    }
  }

  grouping MPLS-TE-P2MP-S2L-BRIEF {
    description "A P2MP S2L";

    container s2l-fec {
      description "FEC for the S2L";
      uses TE-S2L-FEC;
    }
    leaf uptime {
      xr:xr-xml-map "mpls_lcac:Uptime";
      type uint32;
      units "second";
      description "Time in seconds since the S2L was up";
    }
    leaf egress-interface {
      xr:xr-xml-map "mpls_lcac:EgressInterface";
      type string;
      description "Egress Interface";
    }
    leaf ingress-interface {
      xr:xr-xml-map "mpls_lcac:IngressInterface";
      type string;
      description "Ingress Interface";
    }
    leaf role {
      xr:xr-xml-map "mpls_lcac:Role";
      type Mpls-te-tunnel-role;
      description "Role of S2L";
    }
    leaf oper-state {
      xr:xr-xml-map "mpls_lcac:OperState";
      type boolean;
      description "Oper state of S2L";
    }
  }

  grouping MPLS-TE-P2MP-LSP-BRIEF {
    description "A P2MP LSP";

    container lsp-fec {
      description "FEC for the LSP";
      uses TE-LSP-FEC;
    }
    leaf signaled-name {
      xr:xr-xml-map "mpls_lcac:SignaledName";
      type string;
      description "Signaled Name";
    }
    leaf uptime {
      xr:xr-xml-map "mpls_lcac:Uptime";
      type uint32;
      units "second";
      description "Time in seconds since the LSP was up";
    }

    list s2l {
      description "array of S2L structures";
      uses MPLS-TE-P2MP-S2L-BRIEF;
    }
  }
}
