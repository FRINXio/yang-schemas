module Cisco-IOS-XR-ip-ntp-admin-oper {

  /*** NAMESPACE / PREFIX DEFINITION ***/

  namespace "http://cisco.com/ns"+
    "/yang/Cisco-IOS-XR-ip-ntp-admin-oper";


  prefix "ip-ntp-admin-oper";

  /*** LINKAGE (IMPORTS / INCLUDES) ***/

  import Cisco-IOS-XR-types { prefix "xr"; }

  include Cisco-IOS-XR-ip-ntp-admin-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-ntp package
     admin-plane operational data.

     This module contains definitions
     for the following management objects:
       ntp: NTP admin operational data

     Copyright (c) 2013-2015 by Cisco Systems, Inc.
     All rights reserved.";

  revision "2015-11-09" {
    description
      "IOS XR 6.0 revision.";
  }


  container ntp {
    xr:xr-xml-map "ip_ntp_admin_oper:NTP";
    config false;
    description "NTP admin operational data";

    container racks {
      xr:xr-xml-map "ip_ntp_admin_oper:RackTable";
      description "Rack-specific NTP operational data";

      list rack {
        xr:xr-xml-map "ip_ntp_admin_oper:Rack";
        key "number";
        description "NTP operational data for a particular rack";

        container slots {
          xr:xr-xml-map "ip_ntp_admin_oper:SlotTable";
          description "Node-specific NTP operational data";

          list slot {
            xr:xr-xml-map "ip_ntp_admin_oper:Slot";
            key "number";
            description
              "NTP operational data for a particular slot";

            container instances {
              xr:xr-xml-map "ip_ntp_admin_oper:InstanceTable";
              description "Instance-specific NTP operational data";

              list instance {
                xr:xr-xml-map "ip_ntp_admin_oper:Instance";
                key "number";
                description
                  "NTP operational data for a particular
                  instance";

                container status {
                  xr:xr-xml-map "ip_ntp_admin_oper:Status";
                  description "Status of NTP peer(s)";
                  uses NTP-EDM-STATUS-RESULT;
                }

                container associations {
                  xr:xr-xml-map "ip_ntp_admin_oper:Associations";
                  description "NTP Associations information";
                  uses NTP-EDM-ASSOC-SUMMARY-RESULT;
                }

                container associations-detail {
                  xr:xr-xml-map "ip_ntp_admin_oper:AssociationsDeta"+
                    "il";
                  description "NTP Associations Detail information";
                  uses NTP-EDM-ASSOC-DETAIL-RESULT;
                }
                leaf number {
                  xr:xr-xml-map "ip_ntp_admin_oper:Number";
                  type int32;
                  description "The instance number";
                }
              }
            }
            leaf number {
              xr:xr-xml-map "ip_ntp_admin_oper:Number";
              type int32;
              description "The slot number";
            }
          }
        }
        leaf number {
          xr:xr-xml-map "ip_ntp_admin_oper:Number";
          type int32;
          description "The rack number";
        }
      }
    }
  }
}
