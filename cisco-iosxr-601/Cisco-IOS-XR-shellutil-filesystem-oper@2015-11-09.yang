module Cisco-IOS-XR-shellutil-filesystem-oper {

  /*** NAMESPACE / PREFIX DEFINITION ***/

  namespace "http://cisco.com/ns/yang"+
    "/Cisco-IOS-XR-shellutil-filesystem-oper";


  prefix "shellutil-filesystem-oper";

  /*** LINKAGE (IMPORTS / INCLUDES) ***/

  import Cisco-IOS-XR-types { prefix "xr"; }

  include Cisco-IOS-XR-shellutil-filesystem-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR shellutil-filesystem package operational data.

     This module contains definitions
     for the following management objects:
       file-system: List of filesystems

     Copyright (c) 2013-2015 by Cisco Systems, Inc.
     All rights reserved.";

  revision "2015-11-09" {
    description
      "IOS XR 6.0 revision.";
  }


  container file-system {
    xr:xr-xml-map "shellutil_filesystem_oper:FileSystem";
    config false;
    description "List of filesystems";

    list node {
      xr:xr-xml-map "shellutil_filesystem_oper:Node";
      key "node-name";
      description "Node ID";
      leaf node-name {
        xr:xr-xml-map "shellutil_filesystem_oper:NodeName";
        type xr:Node-id;
        description "Node name";
      }
      uses FILESYSTEM;
    }
  }
}
