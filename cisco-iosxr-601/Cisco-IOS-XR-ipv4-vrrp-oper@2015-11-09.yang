module Cisco-IOS-XR-ipv4-vrrp-oper {

  /*** NAMESPACE / PREFIX DEFINITION ***/

  namespace "http://cisco.com/ns/yang/Cisco-IOS-XR-ipv4-vrrp-oper";


  prefix "ipv4-vrrp-oper";

  /*** LINKAGE (IMPORTS / INCLUDES) ***/

  import Cisco-IOS-XR-types { prefix "xr"; }

  include Cisco-IOS-XR-ipv4-vrrp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-vrrp package operational data.

     This module contains definitions
     for the following management objects:
       vrrp: VRRP operational data

     Copyright (c) 2013-2015 by Cisco Systems, Inc.
     All rights reserved.";

  revision "2015-11-09" {
    description
      "IOS XR 6.0 revision.";
  }


  container vrrp {
    xr:xr-xml-map "vrrp_oper:VRRP";
    config false;
    description "VRRP operational data";

    container summary {
      xr:xr-xml-map "vrrp_oper:Summary";
      description "VRRP summary statistics";
      uses VRRP-SUMMARY-INFO;
    }

    container ipv6 {
      xr:xr-xml-map "vrrp_ipv6_oper:IPv6";
      description "IPv6 VRRP configuration";

      container track-items {
        xr:xr-xml-map "vrrp_ipv6_oper:TrackItemTable";
        description "The VRRP tracked item table";

        list track-item {
          xr:xr-xml-map "vrrp_ipv6_oper:TrackItem";
          key "interface-name virtual-router-id"+
            " tracked-interface-name";
          description "A configured VRRP IP address entry";
          leaf interface-name {
            xr:xr-xml-map "vrrp_ipv6_oper:InterfaceName";
            type xr:Interface-name;
            description "The interface name to track";
          }
          leaf virtual-router-id {
            xr:xr-xml-map "vrrp_ipv6_oper:VirtualRouterID";
            type int32;
            description "The VRRP virtual router id";
          }
          leaf tracked-interface-name {
            xr:xr-xml-map "vrrp_ipv6_oper:TrackedInterfaceName";
            type xr:Interface-name;
            description "The name of the tracked interface";
          }
          uses VRRP-TRACKITEM-INFO;
        }
      }

      container virtual-routers {
        xr:xr-xml-map "vrrp_ipv6_oper:VirtualRouterTable";
        description "The VRRP virtual router table";

        list virtual-router {
          xr:xr-xml-map "vrrp_ipv6_oper:VirtualRouter";
          key "interface-name virtual-router-id";
          description "A VRRP virtual router";
          leaf interface-name {
            xr:xr-xml-map "vrrp_ipv6_oper:InterfaceName";
            type xr:Interface-name;
            description "The name of the interface";
          }
          leaf virtual-router-id {
            xr:xr-xml-map "vrrp_ipv6_oper:VirtualRouterID";
            type int32;
            description "The VRRP virtual router id";
          }
          uses VRRP-VROUTER-INFO;
        }
      }

      container interfaces {
        xr:xr-xml-map "vrrp_ipv6_oper:InterfaceTable";
        description "The VRRP interface table";

        list interface {
          xr:xr-xml-map "vrrp_ipv6_oper:Interface";
          key "interface-name";
          description "A VRRP interface entry";
          leaf interface-name {
            xr:xr-xml-map "vrrp_ipv6_oper:InterfaceName";
            type xr:Interface-name;
            description "The name of the interface";
          }
          uses VRRP-INTERFACE-INFO;
        }
      }
    }

    container ipv4 {
      xr:xr-xml-map "vrrp_oper:IPv4";
      description "IPv4 VRRP configuration";

      container interfaces {
        xr:xr-xml-map "vrrp_oper:InterfaceTable";
        description "The VRRP interface table";

        list interface {
          xr:xr-xml-map "vrrp_oper:Interface";
          key "interface-name";
          description "A VRRP interface entry";
          leaf interface-name {
            xr:xr-xml-map "vrrp_oper:InterfaceName";
            type xr:Interface-name;
            description "The name of the interface";
          }
          uses VRRP-INTERFACE-INFO;
        }
      }

      container track-items {
        xr:xr-xml-map "vrrp_oper:TrackItemTable";
        description "The VRRP tracked item table";

        list track-item {
          xr:xr-xml-map "vrrp_oper:TrackItem";
          key "interface-name virtual-router-id"+
            " tracked-interface-name";
          description "A configured VRRP IP address entry";
          leaf interface-name {
            xr:xr-xml-map "vrrp_oper:InterfaceName";
            type xr:Interface-name;
            description "The interface name to track";
          }
          leaf virtual-router-id {
            xr:xr-xml-map "vrrp_oper:VirtualRouterID";
            type int32;
            description "The VRRP virtual router id";
          }
          leaf tracked-interface-name {
            xr:xr-xml-map "vrrp_oper:TrackedInterfaceName";
            type xr:Interface-name;
            description "The name of the tracked interface";
          }
          uses VRRP-TRACKITEM-INFO;
        }
      }

      container virtual-routers {
        xr:xr-xml-map "vrrp_oper:VirtualRouterTable";
        description "The VRRP virtual router table";

        list virtual-router {
          xr:xr-xml-map "vrrp_oper:VirtualRouter";
          key "interface-name virtual-router-id";
          description "A VRRP virtual router";
          leaf interface-name {
            xr:xr-xml-map "vrrp_oper:InterfaceName";
            type xr:Interface-name;
            description "The name of the interface";
          }
          leaf virtual-router-id {
            xr:xr-xml-map "vrrp_oper:VirtualRouterID";
            type int32;
            description "The VRRP virtual router id";
          }
          uses VRRP-VROUTER-INFO;
        }
      }
    }

    container mgo-sessions {
      xr:xr-xml-map "vrrp_oper:MGOSessionTable";
      description "VRRP MGO Session information";

      list mgo-session {
        xr:xr-xml-map "vrrp_oper:MGOSession";
        key "session-name";
        description "A VRRP MGO Session";
        leaf session-name {
          xr:xr-xml-map "vrrp_oper:SessionName";
          type xr:Cisco-ios-xr-string;
          description "The name of the session";
        }
        uses VRRP-MGO-INFO;
      }
    }
  }
}
