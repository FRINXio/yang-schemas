module Cisco-IOS-XR-infra-ceredundancymib-cfg {

  /*** NAMESPACE / PREFIX DEFINITION ***/

  namespace "http://cisco.com/ns/yang"+
    "/Cisco-IOS-XR-infra-ceredundancymib-cfg";


  prefix "infra-ceredundancymib-cfg";

  /*** LINKAGE (IMPORTS / INCLUDES) ***/

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-ceredundancymib package configuration.

     This YANG module augments the
       Cisco-IOS-XR-snmp-agent-cfg
     module with configuration data.

     Copyright (c) 2013-2015 by Cisco Systems, Inc.
     All rights reserved.";

  revision "2015-01-07" {
    description
      "IOS XR 5.3.1 revision.";
  }


  augment "/a1:snmp/a1:notification" {

    container entity-redundancy {
      xr:xr-xml-map "ceredundancymib_cfg:EntityRedundancy";
      description
        "CISCO-ENTITY-REDUNDANCY-MIB notification
        configuration";
      leaf switchover {
        xr:xr-xml-map "ceredundancymib_cfg:Switchover";
        type empty;
        description "Enable switchover notification";
      }
      leaf enable {
        xr:xr-xml-map "ceredundancymib_cfg:Enable";
        type empty;
        description
          "Enable CISCO-ENTITY-REDUNDANCY-MIB notification";
      }
      leaf status {
        xr:xr-xml-map "ceredundancymib_cfg:Status";
        type empty;
        description "Enable status change notification";
      }
    }
    description
      "This augment extends the configuration data of
      'Cisco-IOS-XR-snmp-agent-cfg'";
  }
}
