module Cisco-IOS-XR-fib-common-oper {

  /*** NAMESPACE / PREFIX DEFINITION ***/

  namespace "http://cisco.com/ns/yang/Cisco-IOS-XR-fib-common-oper";


  prefix "fib-common-oper";

  /*** LINKAGE (IMPORTS / INCLUDES) ***/

  import ietf-inet-types { prefix "inet"; }

  import Cisco-IOS-XR-types { prefix "xr"; }

  include Cisco-IOS-XR-fib-common-oper-sub4 {
    revision-date 2015-11-09;
  }

  include Cisco-IOS-XR-fib-common-oper-sub3 {
    revision-date 2015-11-09;
  }

  include Cisco-IOS-XR-fib-common-oper-sub2 {
    revision-date 2015-11-09;
  }

  include Cisco-IOS-XR-fib-common-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fib-common package operational data.

     This module contains definitions
     for the following management objects:
       fib-statistics: cef interface drops operational data
       fib: fib
       mpls-forwarding: mpls forwarding
       fib-mpls: fib mpls

     Copyright (c) 2013-2015 by Cisco Systems, Inc.
     All rights reserved.";

  revision "2015-11-09" {
    description
      "IOS XR 6.0 revision.";
  }

  typedef Fib-route-source {
    type enumeration {
      enum lsd {
        value 5;
        description "LSD";
      }
      enum rib {
        value 7;
        description "RIB";
      }
      enum mrib {
        value 13;
        description "MRIB";
      }
    }
    description "Fib route source";
  }
  typedef Fib-protocol {
    type enumeration {
      enum ipv4 {
        value 0;
        description "ipv4 protocol";
      }
      enum ipv6 {
        value 1;
        description "ipv6 protocol";
      }
      enum mpls {
        value 2;
        description "MPLS protocol";
      }
    }
    description "Fib protocol";
  }
  typedef Eos {
    type enumeration {
      enum eos0 {
        value 0;
        description "EOS Disable";
      }
      enum eos1 {
        value 1;
        description "EOS Enable";
      }
    }
    description "Eos";
  }
  typedef Fib-label {
    type uint32 {
      range "16..1048575";
    }
    description "Fib label";
  }
  typedef Fibllc-entry {
    type enumeration {
      enum xc {
        value 1;
        description "LabelXconnect";
      }
      enum pfx {
        value 2;
        description "IPPrefix";
      }
    }
    description "Fibllc entry";
  }
  typedef Fib-link {
    type enumeration {
      enum link-ipv4 {
        value 0;
        description "IPv4 link protocol";
      }
      enum link-ipv6 {
        value 1;
        description "IPv6 link protocol";
      }
      enum link-mpls {
        value 2;
        description "MPLS link protocol";
      }
    }
    description "Fib link";
  }
  typedef Mplseos {
    type enumeration {
      enum eos0 {
        value 0;
        description "EOS Disable";
      }
      enum eos1 {
        value 1;
        description "EOS Enable";
      }
    }
    description "Mplseos";
  }

  container fib-statistics {
    xr:xr-xml-map "fib_common_statistics_oper:FIBStatistics";
    config false;
    description "cef interface drops operational data";

    container nodes {
      xr:xr-xml-map "fib_common_statistics_oper:NodeTable";
      description "List of nodes";

      list node {
        xr:xr-xml-map "fib_common_statistics_oper:Node";
        key "node-name";
        description "Specific node operational data";

        container drops {
          xr:xr-xml-map "fib_common_statistics_oper:Drops";
          description "Specific node drops";
          uses FIB-STATISTICS-BAG-DROPS;
        }
        leaf node-name {
          xr:xr-xml-map "fib_common_statistics_oper:NodeName";
          type xr:Node-id;
          description "Node name";
        }
      }
    }
  }

  container fib {
    xr:xr-xml-map "fib_common_oper:FIB";
    config false;
    description "fib";

    container nodes {
      xr:xr-xml-map "fib_common_oper:NodeTable";
      description "Table of nodes";

      list node {
        xr:xr-xml-map "fib_common_oper:Node";
        key "node-name";
        description "Operational data for a specific Node";

        container protocols {
          xr:xr-xml-map "fib_common_oper:ProtocolTable";
          description "Protocol table";

          list protocol {
            xr:xr-xml-map "fib_common_oper:Protocol";
            key "protocol-name";
            description "Protocol table entry";

            container issu-state {
              xr:xr-xml-map "fib_common_oper:IssuState";
              description "CEF ISSU State";
              uses FIB-ISSU-STATE;
            }

            container external-summary-all {
              xr:xr-xml-map "fib_common_oper:ExternalSummaryAll";
              description "Summary for all external clients";
              uses FIB-SH-TBL-EXT-SUM-ALL;
            }

            container frr-log {
              xr:xr-xml-map "fib_common_oper:FRRLog";
              description "Table of Fast Reroute activation logs";

              container frr-interfaces {
                xr:xr-xml-map "fib_common_oper:FRRInterfaceTable";
                description "FRR Interface Table";

                list frr-interface {
                  xr:xr-xml-map "fib_common_oper:FRRInterface";
                  key "frr-interface-name";
                  description "Specify FRR Interface Name";

                  container logs {
                    xr:xr-xml-map "fib_common_oper:LogTable";
                    description "FRR log table";

                    list log {
                      xr:xr-xml-map "fib_common_oper:Log";
                      key "log-index";
                      description
                        "Specify index into frr log table";
                      leaf log-index {
                        xr:xr-xml-map "fib_common_oper:LogIndex";
                        type int32;
                        description "FRR Log Index";
                      }
                      uses FIB-SH-FRR-LOG;
                    }
                  }
                  leaf frr-interface-name {
                    xr:xr-xml-map "fib_common_oper:FRRInterfaceName";
                    type xr:Interface-name;
                    description "Interface Name";
                  }
                }
              }
            }

            container vrfs {
              xr:xr-xml-map "fib_common_oper:VRFTable";
              description "VRF table";

              list vrf {
                xr:xr-xml-map "fib_common_oper:VRF";
                key "vrf-name";
                description "VRF table entry";

                container ip-prefix-details {
                  xr:xr-xml-map "fib_common_oper:IPPrefixDetailTabl"+
                    "e";
                  description "IP FIB prefix detail table";

                  list ip-prefix-detail {
                    xr:xr-xml-map "fib_common_oper:IPPrefixDetail";
                    description "IP FIB prefix detail table entry";
                    leaf prefix {
                      xr:xr-xml-map "fib_common_oper:Prefix";
                      type inet:ip-address-no-zone;
                      description "Destination IP address";
                    }
                    leaf prefix-length {
                      xr:xr-xml-map "fib_common_oper:PrefixLength";
                      type xr:Ipv6-prefix-length;
                      description "IP prefix length";
                    }
                    uses FIB-SH-TBL-FIB;
                  }
                }

                container summary {
                  xr:xr-xml-map "fib_common_oper:Summary";
                  description "Operational data for FIB Tablee";
                  uses FIB-SH-SUM;
                }

                container interface-infos {
                  xr:xr-xml-map "fib_common_oper:InterfaceInfoTable";
                  description "Table of InterfaceInfo";

                  list interface-info {
                    xr:xr-xml-map "fib_common_oper:InterfaceInfo";
                    key "link-type";
                    description "Specify link type";

                    container interfaces {
                      xr:xr-xml-map "fib_common_oper:InterfaceTable";
                      description "Table of interfaces";

                      list interface {
                        xr:xr-xml-map "fib_common_oper:Interface";
                        key "interface-name";
                        description "Specify Interface name";
                        leaf interface-name {
                          xr:xr-xml-map "fib_common_oper:InterfaceN"+
                            "ame";
                          type xr:Interface-name;
                          description "Interface Name";
                        }
                        uses FIB-SH-INT;
                      }
                    }
                    leaf link-type {
                      xr:xr-xml-map "fib_common_oper:LinkType";
                      type Fib-link;
                      description "Link type";
                    }
                  }
                }

                container ip-prefix-briefs {
                  xr:xr-xml-map "fib_common_oper:IPPrefixBriefTable";
                  description "IP FIB prefix brief table";

                  list ip-prefix-brief {
                    xr:xr-xml-map "fib_common_oper:IPPrefixBrief";
                    description "IP FIB prefix brief table entry";
                    leaf prefix {
                      xr:xr-xml-map "fib_common_oper:Prefix";
                      type inet:ip-address-no-zone;
                      description "Destination IP address";
                    }
                    leaf prefix-length {
                      xr:xr-xml-map "fib_common_oper:PrefixLength";
                      type xr:Ipv6-prefix-length;
                      description "IP prefix length";
                    }
                    uses FIB-SH-TBL-FIB;
                  }
                }
                leaf vrf-name {
                  xr:xr-xml-map "fib_common_oper:VRFName";
                  type xr:Cisco-ios-xr-string;
                  description "VRF Name";
                }
              }
            }

            container external-client-summaries {
              xr:xr-xml-map "fib_common_oper:ExternalClientSummaryT"+
                "able";
              description "External Client Summary Table";

              list external-client-summary {
                xr:xr-xml-map "fib_common_oper:ExternalClientSummar"+
                  "y";
                description "Summary of the external clients";
                leaf ecd-ver {
                  xr:xr-xml-map "fib_common_oper:EcdVer";
                  type int32;
                  description "Ecd Version";
                }
                leaf id {
                  xr:xr-xml-map "fib_common_oper:ID";
                  type int32;
                  description
                    "ID of the client: ECDv1 is component id,
                    ECDv2 is client id";
                }
                uses FIB-SH-TBL-EXT-CLIENT-SUM;
              }
            }

            container misc {
              xr:xr-xml-map "fib_common_oper:Misc";
              description "CEF misc hidden data";
              uses FIB-SH-MISC;
            }

            container local-label {
              xr:xr-xml-map "fib_common_oper:LocalLabel";
              description "Local label";

              container conflicts {
                xr:xr-xml-map "fib_common_oper:ConflictsTable";
                description "FIB Local-label conflicts database";

                list conflict {
                  xr:xr-xml-map "fib_common_oper:Conflict";
                  description "CEF Local-label conflicts entry";
                  leaf label {
                    xr:xr-xml-map "fib_common_oper:Label";
                    type Fib-label;
                    description "Local label";
                  }
                  leaf source {
                    xr:xr-xml-map "fib_common_oper:Source";
                    type Fib-route-source;
                    description "Route source";
                  }
                  leaf ll-ctype {
                    xr:xr-xml-map "fib_common_oper:LLCType";
                    type Fibllc-entry;
                    description "Type of entry";
                  }
                  leaf pfx-tbl-id {
                    xr:xr-xml-map "fib_common_oper:PfxTblId";
                    type int32;
                    description "Table ID of IP prefix";
                  }
                  leaf prefix {
                    xr:xr-xml-map "fib_common_oper:Prefix";
                    type xr:Cisco-ios-xr-string;
                    description "IP Prefix";
                  }
                  leaf prefix-len {
                    xr:xr-xml-map "fib_common_oper:PrefixLen";
                    type int32;
                    description "Length of IP Prefix";
                  }
                  uses FIB-MPLS-LLC;
                }
              }
            }
            leaf protocol-name {
              xr:xr-xml-map "fib_common_oper:ProtocolName";
              type Fib-protocol;
              description "Protocol Name ";
            }
          }
        }
        leaf node-name {
          xr:xr-xml-map "fib_common_oper:NodeName";
          type xr:Node-id;
          description "Node name";
        }
      }
    }
  }

  container mpls-forwarding {
    xr:xr-xml-map "mpls_fwd_oper:MPLSForwarding";
    config false;
    description "mpls forwarding";

    container nodes {
      xr:xr-xml-map "mpls_fwd_oper:NodeTable";
      description "Table of Nodes";

      list node {
        xr:xr-xml-map "mpls_fwd_oper:Node";
        key "node-name";
        description "Operational data for a specific Node";

        container forwarding-summary {
          xr:xr-xml-map "mpls_fwd_oper:ForwardingSummary";
          description "FIB MPLS forwarding summary";
          uses MPLS-FWDING-SUMMARY;
        }

        container label-fib {
          xr:xr-xml-map "mpls_fwd_oper:LabelFIB";
          description "Labels For FIB";

          container forwarding-details {
            xr:xr-xml-map "mpls_fwd_oper:ForwardingDetailTable";
            description "MPLS Forwarding Detail table";

            list forwarding-detail {
              xr:xr-xml-map "mpls_fwd_oper:ForwardingDetail";
              description "FIB MPLS forwarding details";
              leaf label-value {
                xr:xr-xml-map "mpls_fwd_oper:LabelValue";
                type int32;
                description "Local label value";
              }
              leaf eos {
                xr:xr-xml-map "mpls_fwd_oper:EOS";
                type Mplseos;
                description "End of stack flag";
              }
              uses MPLS-SH-LEAF;
            }
          }

          container informations {
            xr:xr-xml-map "mpls_fwd_oper:Forwarding";
            description "Forwarding filtering details";

            list information {
              xr:xr-xml-map "mpls_fwd_oper:Information";
              description "FIB MPLS forwarding information";
              leaf label-value {
                xr:xr-xml-map "mpls_fwd_oper:LabelValue";
                type int32;
                description "Local label value";
              }
              leaf eos {
                xr:xr-xml-map "mpls_fwd_oper:EOS";
                type Mplseos;
                description "End of stack flag";
              }
              uses MPLS-SH-LEAF;
            }
          }

          container label-security {
            xr:xr-xml-map "mpls_fwd_oper:LabelSecurity";
            description "MPLS label security";

            container interfaces {
              xr:xr-xml-map "mpls_fwd_oper:InterfaceTable";
              description "MPLS label security interface table";

              list interface {
                xr:xr-xml-map "mpls_fwd_oper:Interface";
                key "interface-name";
                description "Specify interface Name";
                leaf interface-name {
                  xr:xr-xml-map "mpls_fwd_oper:InterfaceName";
                  type xr:Interface-name;
                  description "Interface Name";
                }
                uses MPLS-LABEL-SECURITY-INTF;
              }
            }

            container summary {
              xr:xr-xml-map "mpls_fwd_oper:Summary";
              description "MPLS label security summary";
              uses MPLS-LABEL-SECURITY-SUMMARY;
            }
          }
        }
        leaf node-name {
          xr:xr-xml-map "mpls_fwd_oper:NodeName";
          type xr:Node-id;
          description "Node ID";
        }
      }
    }
  }

  container fib-mpls {
    xr:xr-xml-map "fib_mpls_oper:FIB_MPLS";
    config false;
    description "fib mpls";

    container nodes {
      xr:xr-xml-map "fib_mpls_oper:NodeTable";
      description "Table of Nodes";

      list node {
        xr:xr-xml-map "fib_mpls_oper:Node";
        key "node-name";
        description "Operational data for a specific Node";

        container label-fib {
          xr:xr-xml-map "fib_mpls_oper:LabelFIB";
          description "Labels For FIB";

          container forwardings {
            xr:xr-xml-map "fib_mpls_oper:ForwardingTable";
            description "Forwarding filtering details";

            list forwarding {
              xr:xr-xml-map "fib_mpls_oper:Forwarding";
              description "FIB MPLS forwarding information";
              leaf local-label {
                xr:xr-xml-map "fib_mpls_oper:LocalLabel";
                type int32;
                description "Local label value";
              }
              leaf eos {
                xr:xr-xml-map "fib_mpls_oper:EOS";
                type Eos;
                description "End of stack flag";
              }
              uses FIB-MPLS-SH-LEAF;
            }
          }

          container forwarding-details {
            xr:xr-xml-map "fib_mpls_oper:ForwardingDetailTable";
            description "MPLS Forwarding Detail table";

            list forwarding-detail {
              xr:xr-xml-map "fib_mpls_oper:ForwardingDetail";
              description "FIB MPLS forwarding details";
              leaf local-label {
                xr:xr-xml-map "fib_mpls_oper:LocalLabel";
                type int32;
                description "Local label value";
              }
              leaf eos {
                xr:xr-xml-map "fib_mpls_oper:EOS";
                type Eos;
                description "End of stack flag";
              }
              uses FIB-MPLS-SH-LEAF;
            }
          }
        }

        container tunnel {
          xr:xr-xml-map "fib_mpls_oper:Tunnel";
          description "Tunnels Operations";

          container forwarding-tunnels {
            xr:xr-xml-map "fib_mpls_oper:ForwardingTunnelTable";
            description "Forwarding details";

            list forwarding-tunnel {
              xr:xr-xml-map "fib_mpls_oper:ForwardingTunnel";
              key "interface-name";
              description "FIB MPLS Tunnels Interfaces operation";
              leaf interface-name {
                xr:xr-xml-map "fib_mpls_oper:InterfaceName";
                type xr:Interface-name;
                description "Interface Name";
              }
              uses FIB-MPLS-SH-TEHEAD;
            }
          }
        }

        container frr-database {
          xr:xr-xml-map "fib_mpls_oper:FRRDatabase";
          description "FIB MPLS FRR Database";

          container frrdb-tunnel-head-summary {
            xr:xr-xml-map "fib_mpls_oper:FRRDBTunnelHeadSummary";
            description "FIB MPLS FRR Database Tunnel Head Summary";
            uses FIB-MPLS-FRR-DB-SUM;
          }

          container frrdb-backup-interface-summaries {
            xr:xr-xml-map "fib_mpls_oper:FRRDBBackupInterfaceSummar"+
              "yTable";
            description
              "FIB MPLS FRR Database Backup Interface
              Summary Table";

            list frrdb-backup-interface-summary {
              xr:xr-xml-map "fib_mpls_oper:FRRDBBackupInterfaceSumm"+
                "ary";
              key "interface-name";
              description
                "FIB MPLS FRR Database Backup Interface
                Summary";
              leaf interface-name {
                xr:xr-xml-map "fib_mpls_oper:InterfaceName";
                type xr:Interface-name;
                description "Interface Name";
              }
              uses FIB-MPLS-FRR-DB-SUM;
            }
          }

          container frrdb-summary {
            xr:xr-xml-map "fib_mpls_oper:FRRDBSummary";
            description "FIB MPLS FRR Database Summary";
            uses FIB-MPLS-FRR-DB-SUM;
          }

          container frrdb-protected-interface-table-summaries {
            xr:xr-xml-map "fib_mpls_oper:FRRDBProtectedInterfaceSum"+
              "maryTable";
            description
              "FIB MPLS FRR Database Protected Interface
              Summary Table";

            list frrdb-protected-interface-table-summary {
              xr:xr-xml-map "fib_mpls_oper:FRRDBProtectedInterfaceT"+
                "ableSummary";
              key "interface-name";
              description
                "FIB MPLS FRR Database Protected Interface
                Summary";
              leaf interface-name {
                xr:xr-xml-map "fib_mpls_oper:InterfaceName";
                type xr:Interface-name;
                description "Interface Name";
              }
              uses FIB-MPLS-FRR-DB-SUM;
            }
          }

          container frrdb-tunnel-midpoint-summary {
            xr:xr-xml-map "fib_mpls_oper:FRRDBTunnelMidpointSummary";
            description
              "FIB MPLS FRR Database Tunnel Midpoint Summary";
            uses FIB-MPLS-FRR-DB-SUM;
          }

          container frrdb-tunnel-midpoints {
            xr:xr-xml-map "fib_mpls_oper:FRRDBTunnelMidpointTable";
            description
              "FIB MPLS FRR Database Tunnel Midpoint Table";

            list frrdb-tunnel-midpoint {
              xr:xr-xml-map "fib_mpls_oper:FRRDBTunnelMidpoint";
              key "local-label";
              description
                "FIB MPLS FRR Database Tunnel Midpoint Entry";
              leaf local-label {
                xr:xr-xml-map "fib_mpls_oper:LocalLabel";
                type int32;
                description "Local label value";
              }
              uses FIB-MPLS-FRR-DB-ENTRY;
            }
          }

          container frrdb-tunnel-heads {
            xr:xr-xml-map "fib_mpls_oper:FRRDBTunnelHeadTable";
            description "FIB MPLS FRR Database Tunnel Head Table";

            list frrdb-tunnel-head {
              xr:xr-xml-map "fib_mpls_oper:FRRDBTunnelHead";
              key "interface-name";
              description "FIB MPLS FRR Database Tunnel Head Entry";
              leaf interface-name {
                xr:xr-xml-map "fib_mpls_oper:InterfaceName";
                type xr:Interface-name;
                description "Interface Name";
              }
              uses FIB-MPLS-FRR-DB-ENTRY;
            }
          }
        }

        container forwarding-summary {
          xr:xr-xml-map "fib_mpls_oper:ForwardingSummary";
          description "FIB MPLS forwarding summary";
          uses FIB-MPLS-FWDING-SUMMARY;
        }

        container frr-logs {
          xr:xr-xml-map "fib_mpls_oper:FRRLogTable";
          description "FRR Log Table";

          list frr-log {
            xr:xr-xml-map "fib_mpls_oper:FRRLog";
            key "event-id";
            description "FRR Log information";
            leaf event-id {
              xr:xr-xml-map "fib_mpls_oper:EventID";
              type int32;
              description "Event ID";
            }
            uses FIB-MPLS-FRR-EVENT;
          }
        }
        leaf node-name {
          xr:xr-xml-map "fib_mpls_oper:NodeName";
          type xr:Node-id;
          description "Node name";
        }
      }
    }
  }
}
