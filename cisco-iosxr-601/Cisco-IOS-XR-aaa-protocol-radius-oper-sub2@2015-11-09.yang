submodule Cisco-IOS-XR-aaa-protocol-radius-oper-sub2 {

  belongs-to Cisco-IOS-XR-aaa-protocol-radius-oper {
    prefix Cisco-IOS-XR-aaa-protocol-radius-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR aaa-protocol-radius package operational data.

     Copyright (c) 2013-2015 by Cisco Systems, Inc.
     All rights reserved.";

  revision "2015-11-09" {
    description
      "IOS XR 6.0 revision.";
  }


  grouping RADIUS-DYNAMIC-SERVER {
    description "RADIUS dynamic author server";
    leaf disconnected-invalid-requests {
      xr:xr-xml-map "radius:DisconnectedInvalidRequests";
      type uint32;
      description "Invalid disconnected requests";
    }
    leaf invalid-coa-requests {
      xr:xr-xml-map "radius:InvalidCOARequests";
      type uint32;
      description "Invalid change of authorization requests";
    }
  }

  grouping RADIUS-AUTHORIZATION-DATA {
    description "RADIUS authorization data";
    leaf author-requests {
      xr:xr-xml-map "radius:AuthorRequests";
      type uint32;
      description "Number of access requests";
    }
    leaf author-request-timeouts {
      xr:xr-xml-map "radius:AuthorRequestTimeouts";
      type uint32;
      description "Number of access packets timed out";
    }
    leaf author-unexpected-responses {
      xr:xr-xml-map "radius:AuthorUnexpectedResponses";
      type uint32;
      description "Number of unexpected authorization responses";
    }
    leaf author-server-error-responses {
      xr:xr-xml-map "radius:AuthorServerErrorResponses";
      type uint32;
      description "Number of server error authorization responses";
    }
    leaf author-incorrect-responses {
      xr:xr-xml-map "radius:AuthorIncorrectResponses";
      type uint32;
      description "Number of incorrect authorization responses";
    }
    leaf author-response-time {
      xr:xr-xml-map "radius:AuthorResponseTime";
      type uint32;
      description
        "Average response time for authorization requests";
    }
    leaf author-transaction-successess {
      xr:xr-xml-map "radius:AuthorTransactionSuccessess";
      type uint32;
      description "Number of succeeded authorization transactions";
    }
    leaf author-transaction-failure {
      xr:xr-xml-map "radius:AuthorTransactionFailure";
      type uint32;
      description "Number of failed authorization transactions";
    }
  }

  grouping RADIUS-SERVER-GROUP-DATA {
    description "RADIUS server group data";

    container accounting {
      description "Accounting data";
      uses RADIUS-ACCOUNTING-DATA;
    }

    container authentication {
      description "Authentication data";
      uses RADIUS-AUTHENTICATION-DATA;
    }

    container authorization {
      description "Authorization data";
      uses RADIUS-AUTHORIZATION-DATA;
    }
    leaf server-address {
      xr:xr-xml-map "radius:ServerAddress";
      type inet:ipv4-address;
      description "Server address";
    }
    leaf authentication-port {
      xr:xr-xml-map "radius:AuthenticationPort";
      type uint32;
      description "Authentication port";
    }
    leaf accounting-port {
      xr:xr-xml-map "radius:AccountingPort";
      type uint32;
      description "Accounting port";
    }
    leaf is-private {
      xr:xr-xml-map "radius:IsPrivate";
      type boolean;
      description "True if private";
    }
    leaf ip-address {
      xr:xr-xml-map "radius:IP_Address";
      type string;
      description "IP address buffer";
    }
    leaf family {
      xr:xr-xml-map "radius:Family";
      type string;
      description "IP address Family";
    }
  }

  grouping RADIUS-GROUPS-SERVERS {
    description "RADIUS server groups";
    leaf groups {
      xr:xr-xml-map "radius:Groups";
      type uint32;
      description "Number of groups";
    }
    leaf vrf-name {
      xr:xr-xml-map "radius:VRFName";
      type string;
      description "VRF name";
    }
    leaf dead-time {
      xr:xr-xml-map "radius:DeadTime";
      type uint32;
      units "minute";
      description "Dead time in minutes";
    }
    leaf servers {
      xr:xr-xml-map "radius:Servers";
      type uint32;
      description "Number of servers";
    }

    list server-group {
      description "Server groups";
      uses RADIUS-SERVER-GROUP-DATA;
    }
  }

  grouping RADIUS-ACCOUNTING-DATA {
    description "RADIUS accounting data";
    leaf requests {
      xr:xr-xml-map "radius:Requests";
      type uint32;
      description "Number of accounting requests";
    }
    leaf pending-requests {
      xr:xr-xml-map "radius:PendingRequests";
      type uint32;
      description "Number of pending accounting requests";
    }
    leaf retransmits {
      xr:xr-xml-map "radius:Retransmits";
      type uint32;
      description "Number of retransmitted accounting requests";
    }
    leaf responses {
      xr:xr-xml-map "radius:Responses";
      type uint32;
      description "Number of accounting responses";
    }
    leaf timeouts {
      xr:xr-xml-map "radius:Timeouts";
      type uint32;
      description "Number of accounting packets timed-out";
    }
    leaf bad-responses {
      xr:xr-xml-map "radius:BadResponses";
      type uint32;
      description "Number of bad accounting responses";
    }
    leaf bad-authenticators {
      xr:xr-xml-map "radius:BadAuthenticators";
      type uint32;
      description "Number of bad accounting authenticators";
    }
    leaf unknown-packet-types {
      xr:xr-xml-map "radius:UnknownPacketTypes";
      type uint32;
      description
        "Number of packets received with unknown type
        from accounting server";
    }
    leaf dropped-responses {
      xr:xr-xml-map "radius:DroppedResponses";
      type uint32;
      description "Number of accounting responses dropped";
    }
    leaf rtt {
      xr:xr-xml-map "radius:RTT";
      type uint32;
      units "millisecond";
      description "Round trip time for accounting in milliseconds";
    }
    leaf acct-unexpected-responses {
      xr:xr-xml-map "radius:AcctUnexpectedResponses";
      type uint32;
      description "Number of unexpected accounting responses";
    }
    leaf acct-server-error-responses {
      xr:xr-xml-map "radius:AcctServerErrorResponses";
      type uint32;
      description "Number of server error accounting responses";
    }
    leaf acct-incorrect-responses {
      xr:xr-xml-map "radius:AcctIncorrectResponses";
      type uint32;
      description "Number of incorrect accounting responses";
    }
    leaf acct-response-time {
      xr:xr-xml-map "radius:AcctResponseTime";
      type uint32;
      description
        "Average response time for authentication
        requests";
    }
    leaf acct-transaction-successess {
      xr:xr-xml-map "radius:AcctTransactionSuccessess";
      type uint32;
      description "Number of succeeded authentication transactions";
    }
    leaf acct-transaction-failure {
      xr:xr-xml-map "radius:AcctTransactionFailure";
      type uint32;
      description "Number of failed authentication transactions";
    }
  }

  grouping RADIUS-ACCOUNTING {
    description "RADIUS accounting";

    container accounting {
      description "Accounting data";
      uses RADIUS-ACCOUNTING-DATA;
    }
    leaf server-address {
      xr:xr-xml-map "radius:ServerAddress";
      type inet:ipv4-address;
      description "IP address of RADIUS server";
    }
    leaf port {
      xr:xr-xml-map "radius:Port";
      type uint32;
      description "Accounting port number";
    }
    leaf ip-address {
      xr:xr-xml-map "radius:IP_Address";
      type string;
      description "IP address buffer";
    }
    leaf family {
      xr:xr-xml-map "radius:Family";
      type string;
      description "IP address Family";
    }
  }

  grouping RADIUS-SERVER-ACCOUNTING {
    description "RADIUS accounting information of all servers";

    list accounting-group {
      description "List of accounting groups";
      uses RADIUS-ACCOUNTING;
    }
  }

  grouping RADIUS-AUTHENTICATION-DATA {
    description "RADIUS authentication data";
    leaf access-requests {
      xr:xr-xml-map "radius:AccessRequests";
      type uint32;
      description "Number of access requests";
    }
    leaf pending-access-requests {
      xr:xr-xml-map "radius:PendingAccessRequests";
      type uint32;
      description "Number of pending access requests";
    }
    leaf access-request-retransmits {
      xr:xr-xml-map "radius:AccessRequestRetransmits";
      type uint32;
      description "Number of retransmitted access requests";
    }
    leaf access-accepts {
      xr:xr-xml-map "radius:AccessAccepts";
      type uint32;
      description "Number of access accepts";
    }
    leaf access-rejects {
      xr:xr-xml-map "radius:AccessRejects";
      type uint32;
      description "Number of access rejects";
    }
    leaf access-challenges {
      xr:xr-xml-map "radius:AccessChallenges";
      type uint32;
      description "Number of access challenges";
    }
    leaf access-timeouts {
      xr:xr-xml-map "radius:AccessTimeouts";
      type uint32;
      description "Number of access packets timed out";
    }
    leaf bad-access-responses {
      xr:xr-xml-map "radius:BadAccessResponses";
      type uint32;
      description "Number of bad access responses";
    }
    leaf bad-access-authenticators {
      xr:xr-xml-map "radius:BadAccessAuthenticators";
      type uint32;
      description "Number of bad access authenticators";
    }
    leaf unknown-access-types {
      xr:xr-xml-map "radius:UnknownAccessTypes";
      type uint32;
      description
        "Number of packets received with unknown type
        from authentication server";
    }
    leaf dropped-access-responses {
      xr:xr-xml-map "radius:DroppedAccessResponses";
      type uint32;
      description "Number of access responses dropped";
    }
    leaf rtt {
      xr:xr-xml-map "radius:RTT";
      type uint32;
      units "millisecond";
      description
        "Round trip time for authentication in
        milliseconds";
    }
    leaf authen-response-time {
      xr:xr-xml-map "radius:AuthenResponseTime";
      type uint32;
      description
        "Average response time for authentication
        requests";
    }
    leaf authen-transaction-successess {
      xr:xr-xml-map "radius:AuthenTransactionSuccessess";
      type uint32;
      description "Number of succeeded authentication transactions";
    }
    leaf authen-transaction-failure {
      xr:xr-xml-map "radius:AuthenTransactionFailure";
      type uint32;
      description "Number of failed authentication transactions";
    }
    leaf authen-unexpected-responses {
      xr:xr-xml-map "radius:AuthenUnexpectedResponses";
      type uint32;
      description "Number of unexpected authentication responses";
    }
    leaf authen-server-error-responses {
      xr:xr-xml-map "radius:AuthenServerErrorResponses";
      type uint32;
      description "Number of server error authentication responses";
    }
    leaf authen-incorrect-responses {
      xr:xr-xml-map "radius:AuthenIncorrectResponses";
      type uint32;
      description "Number of incorrect authentication responses";
    }
  }

  grouping RADIUS-AUTHENTICATION {
    description "RADIUS authentication";

    container authentication {
      description "Authentication data";
      uses RADIUS-AUTHENTICATION-DATA;
    }
    leaf server-address {
      xr:xr-xml-map "radius:ServerAddress";
      type inet:ipv4-address;
      description "IP address of RADIUS server";
    }
    leaf port {
      xr:xr-xml-map "radius:Port";
      type uint32;
      description "Authentication port number";
    }
    leaf ip-address {
      xr:xr-xml-map "radius:IP_Address";
      type string;
      description "IP address buffer";
    }
    leaf family {
      xr:xr-xml-map "radius:Family";
      type string;
      description "IP address Family";
    }
  }

  grouping RADIUS-SERVER-AUTHENTICATION {
    description "RADIUS authentication data of all servers";

    list authentication-group {
      description "List of authentication groups";
      uses RADIUS-AUTHENTICATION;
    }
  }

  grouping RADIUS-TIME-TRIES-DATA {
    description "Time and tries information";
    leaf value {
      xr:xr-xml-map "radius:Value";
      type uint32;
      description "Value for time or tries";
    }
    leaf is-computed {
      xr:xr-xml-map "radius:IsComputed";
      type boolean;
      description "True if computed; false if not";
    }
  }

  grouping RADIUS-DEAD-CRITERIA {
    description "Dead criteria information";

    container time {
      description "Time in seconds";
      uses RADIUS-TIME-TRIES-DATA;
    }

    container tries {
      description "Number of tries";
      uses RADIUS-TIME-TRIES-DATA;
    }
  }

  grouping RADIUS-CLIENT-XML {
    description "RADIUS client data";
    leaf unknown-authentication-responses {
      xr:xr-xml-map "radius:UnknownAuthenticationResponses";
      type uint32;
      description
        "Number of RADIUS access responses packets
        received from unknown addresses";
    }
    leaf authentication-nas-id {
      xr:xr-xml-map "radius:AuthenticationNAS_ID";
      type string;
      description
        "NAS-Identifier of the RADIUS authentication
        client";
    }
    leaf unknown-accounting-responses {
      xr:xr-xml-map "radius:UnknownAccountingResponses";
      type uint32;
      description
        "Number of RADIUS accounting responses packets
        received from unknown addresses";
    }
  }
}
