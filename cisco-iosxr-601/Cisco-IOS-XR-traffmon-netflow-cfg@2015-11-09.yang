module Cisco-IOS-XR-traffmon-netflow-cfg {

  /*** NAMESPACE / PREFIX DEFINITION ***/

  namespace "http://cisco.com/ns/yang"+
    "/Cisco-IOS-XR-traffmon-netflow-cfg";


  prefix "traffmon-netflow-cfg";

  /*** LINKAGE (IMPORTS / INCLUDES) ***/

  import ietf-inet-types { prefix "inet"; }

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR traffmon-netflow package configuration.

     This module contains definitions
     for the following management objects:
       net-flow: NetFlow Configuration

     This YANG module augments the
       Cisco-IOS-XR-ifmgr-cfg
     module with configuration data.

     Copyright (c) 2013-2015 by Cisco Systems, Inc.
     All rights reserved.";

  revision "2015-11-09" {
    description
      "IOS XR 6.0 revision.";
  }

  typedef Nf-export-timeout {
    type uint32 {
      range "0..604800";
    }
    description "Nf export timeout";
  }
  typedef Nf-active-cache-aging-timeout {
    type uint32 {
      range "1..604800";
    }
    description "Nf active cache aging timeout";
  }
  typedef Nf-inactive-cache-aging-timeout {
    type uint32 {
      range "0..604800";
    }
    description "Nf inactive cache aging timeout";
  }
  typedef Nf-sample-interval {
    type uint32 {
      range "1..65535";
    }
    description "Nf sample interval";
  }
  typedef Nf-sample-number {
    type uint32;
    description "Nf sample number";
  }
  typedef Nf-template-timeout {
    type uint32 {
      range "1..604800";
    }
    description "Nf template timeout";
  }
  typedef Nf-map-name {
    type xr:Cisco-ios-xr-string {
      length "0..32";
    }
    description "Nf map name";
  }
  typedef Nf-cache-aging-mode {
    type enumeration {
      enum normal {
        value 0;
        description "Normal, caches age";
      }
      enum permanent {
        value 1;
        description "Permanent, caches never age";
      }
    }
    description "Nf cache aging mode";
  }
  typedef Nf-cache-entry {
    type uint32 {
      range "4096..1000000";
    }
    description "Nf cache entry";
  }
  typedef Nf-update-cache-aging-timeout {
    type uint32 {
      range "1..604800";
    }
    description "Nf update cache aging timeout";
  }
  typedef Nf-sampling-mode {
    type enumeration {
      enum random {
        value 2;
        description "Random sampling";
      }
    }
    description "Nf sampling mode";
  }
  typedef Nf-export-version {
    type uint32 {
      range "9..10";
    }
    description "Nf export version";
  }
  typedef Nf-cache-timeout-rate-limit {
    type uint32 {
      range "1..1000000";
    }
    description "Nf cache timeout rate limit";
  }

  grouping FLOW-MONITOR-NAME {
    description "Common node of ingress, egress";

    list flow-monitor-name {
      xr:xr-xml-map "netflow_interface_cfg:FlowMonitorName";
      key "monitor-map-name";
      description "Specify a sampler for a flow monitor";
      leaf monitor-map-name {
        xr:xr-xml-map "netflow_interface_cfg:MonitorMapName";
        type xr:Cisco-ios-xr-string;
        description "Flow monitor map name";
      }
      leaf sampler-map-name {
        xr:xr-xml-map "netflow_interface_cfg:SamplerMapName";
        type string;
        mandatory true;
        description "Sampler map name";
      }
    }
  }

  grouping FLOW-MONITOR-MAP {
    description "Common node of mpls, ipv4, ipv6";

    container flow-monitor-map {
      xr:xr-xml-map "netflow_interface_cfg:FlowMonitorMap";
      description "Configure a flow monitor map";

      container ingress {
        xr:xr-xml-map "netflow_interface_cfg:Ingress";
        description "Configure ingress monitoring direction";
        uses FLOW-MONITOR-NAME;
      }

      container egress {
        xr:xr-xml-map "netflow_interface_cfg:Egress";
        description "Configure egress monitoring direction";
        uses FLOW-MONITOR-NAME;
      }
    }
  }

  grouping NETFLOW-CFG-FLOW-MONITOR-MAP {
    description
      "Common node of flow-monitor-map-table,
      flow-monitor-map-performance-table";

    list flow-monitor-map {
      xr:xr-xml-map "netflow_cfg:FlowMonitorMap";
      key "monitor-map-name";
      description "Monitor map name";

      container option {
        xr:xr-xml-map "netflow_cfg:Option";
        description "Specify an option for the flow cache";
        leaf filtered {
          xr:xr-xml-map "netflow_cfg:Filtered";
          type empty;
          description "Specify whether data should be filtered";
        }
        leaf out-phys-int {
          xr:xr-xml-map "netflow_cfg:OutPhysInt";
          type empty;
          description
            "Specify whether it exports the physical output
            interface";
        }
      }

      container exporters {
        xr:xr-xml-map "netflow_cfg:ExporterTable";
        description
          "Configure exporters to be used by the
          monitor-map";

        list exporter {
          xr:xr-xml-map "netflow_cfg:Exporter";
          key "exporter-name";
          description
            "Configure exporter to be used by the
            monitor-map";
          leaf exporter-name {
            xr:xr-xml-map "netflow_cfg:ExporterName";
            type Nf-map-name;
            description "Exporter name";
          }
        }
      }

      container record {
        xr:xr-xml-map "netflow_cfg:Record";
        presence "Indicates a record node is configured.";
        description "Specify a flow record format";
        leaf record-name {
          xr:xr-xml-map "netflow_cfg:RecordName";
          type Nf-map-name;
          mandatory true;
          description
            "Flow record format (Either 'ipv4-raw'
            ,'ipv4-peer-as', 'ipv6', 'mpls', 'mpls-ipv4',
            'mpls-ipv6', 'mpls-ipv4-ipv6', 'ipv6-peer-as')";
        }
        leaf label {
          xr:xr-xml-map "netflow_cfg:Label";
          type uint32 {
            range "1..6";
          }
          description "Enter label value for MPLS record type";
        }
      }
      leaf cache-update-aging-timeout {
        xr:xr-xml-map "netflow_cfg:CacheUpdateAgingTimeout";
        type Nf-update-cache-aging-timeout;
        units "second";
        default "1800";
        description "Specify the update flow cache aging timeout";
      }
      leaf cache-entries {
        xr:xr-xml-map "netflow_cfg:CacheEntries";
        type Nf-cache-entry;
        default "65535";
        description
          "Specify the number of entries in the flow cache";
      }
      leaf cache-inactive-aging-timeout {
        xr:xr-xml-map "netflow_cfg:CacheInactiveAgingTimeout";
        type Nf-inactive-cache-aging-timeout;
        units "second";
        default "15";
        description "Specify the inactive flow cache aging timeout";
      }
      leaf cache-active-aging-timeout {
        xr:xr-xml-map "netflow_cfg:CacheActiveAgingTimeout";
        type Nf-active-cache-aging-timeout;
        units "second";
        default "1800";
        description "Specify the active flow cache aging timeout";
      }
      leaf cache-timeout-rate-limit {
        xr:xr-xml-map "netflow_cfg:CacheTimeoutRateLimit";
        type Nf-cache-timeout-rate-limit;
        default "2000";
        description
          "Specify the maximum number of entries to age
          each second";
      }
      leaf cache-aging-mode {
        xr:xr-xml-map "netflow_cfg:CacheAgingMode";
        type Nf-cache-aging-mode;
        default "normal";
        description "Specify the flow cache aging mode";
      }
      leaf monitor-map-name {
        xr:xr-xml-map "netflow_cfg:MonitorMapName";
        type Nf-map-name;
        description "Monitor map name";
      }
    }
  }

  container net-flow {
    xr:xr-xml-map "netflow_cfg:NetFlow";
    description "NetFlow Configuration";

    container flow-exporter-maps {
      xr:xr-xml-map "netflow_cfg:FlowExporterMapTable";
      description "Configure a flow exporter map";

      list flow-exporter-map {
        xr:xr-xml-map "netflow_cfg:FlowExporterMap";
        key "exporter-map-name";
        description "Exporter map name";

        container udp {
          xr:xr-xml-map "netflow_cfg:UDP";
          description "Use UDP as transport protocol";
          leaf destination-port {
            xr:xr-xml-map "netflow_cfg:DestinationPort";
            xr:xr-cli-map "exporter-map <string> transport udp <num"+
              "ber> ";
            type uint32 {
              range "1024..65535";
            }
            description "Configure Destination UDP port";
          }
        }

        container versions {
          xr:xr-xml-map "netflow_cfg:VersionTable";
          description "Specify export version parameters";

          list version {
            xr:xr-xml-map "netflow_cfg:Version";
            key "version-number";
            description "Configure export version options";

            container options {
              xr:xr-xml-map "netflow_cfg:Options";
              description "Specify options for exporting templates";
              leaf interface-table-export-timeout {
                xr:xr-xml-map "netflow_cfg:InterfaceTableExportTime"+
                  "out";
                type Nf-export-timeout;
                units "second";
                description
                  "Specify timeout for exporting interface
                  table";
              }
              leaf sampler-table-export-timeout {
                xr:xr-xml-map "netflow_cfg:SamplerTableExportTimeou"+
                  "t";
                type Nf-export-timeout;
                units "second";
                description
                  "Specify timeout for exporting sampler table";
              }
              leaf vrf-table-export-timeout {
                xr:xr-xml-map "netflow_cfg:VrfTableExportTimeout";
                type Nf-export-timeout;
                units "second";
                description
                  "Specify timeout for exporting vrf table";
              }
            }
            leaf options-template-timeout {
              xr:xr-xml-map "netflow_cfg:OptionsTemplateTimeout";
              type Nf-template-timeout;
              units "second";
              default "1800";
              description "Option template configuration options";
            }
            leaf common-template-timeout {
              xr:xr-xml-map "netflow_cfg:CommonTemplateTimeout";
              type Nf-template-timeout;
              units "second";
              default "1800";
              description "Specify custom timeout for the template";
            }
            leaf data-template-timeout {
              xr:xr-xml-map "netflow_cfg:DataTemplateTimeout";
              type Nf-template-timeout;
              units "second";
              default "1800";
              description "Data template configuration options";
            }
            leaf version-number {
              xr:xr-xml-map "netflow_cfg:VersionNumber";
              type Nf-export-version;
              description "Export version number";
            }
          }
        }

        container destination {
          xr:xr-xml-map "netflow_cfg:Destination";
          description "Configure export destination (collector)";
          leaf ip-address {
            xr:xr-xml-map "netflow_cfg:IPAddress";
            type inet:ipv4-address-no-zone;
            description "Destination IPv4 address";
          }
          leaf ipv6-address {
            xr:xr-xml-map "netflow_cfg:IPv6Address";
            type string;
            description "IPV6 address of the tunnel destination";
          }
          leaf vrf-name {
            xr:xr-xml-map "netflow_cfg:VRFName";
            type string;
            description "VRF name";
          }
        }
        leaf source-interface {
          xr:xr-xml-map "netflow_cfg:SourceInterface";
          xr:xr-cli-map "exporter-map <string> source <interface> ";
          type xr:Interface-name;
          description "Configure source interface for collector";
        }
        leaf dscp {
          xr:xr-xml-map "netflow_cfg:DSCP";
          xr:xr-cli-map "exporter-map <string> dscp <number> ";
          type uint32 {
            range "0..63";
          }
          description "Specify DSCP value for export packets";
        }
        leaf exporter-map-name {
          xr:xr-xml-map "netflow_cfg:ExporterMapName";
          type Nf-map-name;
          description "Exporter map name";
        }
      }
    }

    container flow-sampler-maps {
      xr:xr-xml-map "netflow_cfg:FlowSamplerMapTable";
      description "Flow sampler map configuration";

      list flow-sampler-map {
        xr:xr-xml-map "netflow_cfg:FlowSamplerMap";
        key "sampler-map-name";
        description "Sampler map name";

        container sampling-modes {
          xr:xr-xml-map "netflow_cfg:SamplingModeTable";
          description "Configure packet sampling mode";

          list sampling-mode {
            xr:xr-xml-map "netflow_cfg:SamplingMode";
            xr:xr-cli-map "sampler-map <string> random <number> out"+
              "-of <number> ";
            key "mode";
            description "Configure sampling mode";
            leaf mode {
              xr:xr-xml-map "netflow_cfg:Mode";
              type Nf-sampling-mode;
              description "Sampling mode";
            }
            leaf sample-number {
              xr:xr-xml-map "netflow_cfg:SampleNumber";
              type Nf-sample-number;
              mandatory true;
              description
                "Number of packets to be sampled in the
                sampling interval";
            }
            leaf interval {
              xr:xr-xml-map "netflow_cfg:Interval";
              type Nf-sample-interval;
              mandatory true;
              description "Sampling interval in units of packets";
            }
          }
        }
        leaf sampler-map-name {
          xr:xr-xml-map "netflow_cfg:SamplerMapName";
          type Nf-map-name;
          description "Sampler map name";
        }
      }
    }

    container flow-monitor-map-table {
      xr:xr-xml-map "netflow_cfg:FlowMonitorMapTable";
      description "Flow monitor map configuration";
      uses NETFLOW-CFG-FLOW-MONITOR-MAP;
    }

    container flow-monitor-map-performance-table {
      xr:xr-xml-map "netflow_cfg:FlowMonitorMapPerformanceTable";
      description
        "Configure a performance traffic flow monitor map";
      uses NETFLOW-CFG-FLOW-MONITOR-MAP;
    }
  }

  augment "/a1:interface-configurations/a1:interface-configuration" {

    container net-flow {
      xr:xr-xml-map "netflow_interface_cfg:NetFlow";
      description "Interface netflow configuration";

      container mpls {
        xr:xr-xml-map "netflow_interface_cfg:MPLS";
        description "Configure MPLS netflow";
        uses FLOW-MONITOR-MAP;
      }

      container ipv6 {
        xr:xr-xml-map "netflow_interface_cfg:IPv6";
        description "Configure IPv6 netflow";
        uses FLOW-MONITOR-MAP;
      }

      container ipv4 {
        xr:xr-xml-map "netflow_interface_cfg:IPv4";
        description "Configure IPv4 netflow";
        uses FLOW-MONITOR-MAP;
      }
    }
    description
      "This augment extends the configuration data of
      'Cisco-IOS-XR-ifmgr-cfg'";
  }
}
