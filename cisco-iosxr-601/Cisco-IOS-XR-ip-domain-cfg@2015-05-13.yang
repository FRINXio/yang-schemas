module Cisco-IOS-XR-ip-domain-cfg {

  /*** NAMESPACE / PREFIX DEFINITION ***/

  namespace "http://cisco.com/ns/yang/Cisco-IOS-XR-ip-domain-cfg";


  prefix "ip-domain-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-domain package configuration.

     This module contains definitions
     for the following management objects:
       ip-domain: IP domain configuration

     Copyright (c) 2013-2015 by Cisco Systems, Inc.
     All rights reserved.";

  revision "2015-05-13" {
    description
      "IOS XR 5.3.2 revision.";
  }

  revision "2015-01-07" {
    description
      "IOS XR 5.3.1 revision.";
  }


  container ip-domain {
    xr:xr-xml-map "ip_domain_cfg:IPDomain";
    description "IP domain configuration";

    container vrfs {
      xr:xr-xml-map "ip_domain_vrf_cfg:VRFTable";
      description "VRF table";

      list vrf {
        xr:xr-xml-map "ip_domain_vrf_cfg:VRF";
        key "vrf-name";
        description "VRF specific data";

        container ipv6-hosts {
          xr:xr-xml-map "ip_domain_vrf_cfg:IPv6HostTable";
          description "IPv6 host";

          list ipv6-host {
            xr:xr-xml-map "ip_domain_vrf_cfg:IPv6Host";
            xr:xr-cli-map "ipv6 host <string> <IPv6 address> [<IPv6"+
              " address> [<IPv6 address> [<IPv6 address>]]] ";
            key "host-name";
            description "Host name and up to 4 host IPv6 addresses";
            leaf host-name {
              xr:xr-xml-map "ip_domain_vrf_cfg:Hostname";
              type string;
              description "A hostname";
            }
            leaf-list address {
              xr:xr-xml-map "ip_domain_vrf_cfg:Address";
              type inet:ipv6-address-no-zone;
              min-elements "1";
              max-elements "4";
              description "Host IPv6 addresses";
            }
          }
        }

        container servers {
          xr:xr-xml-map "ip_domain_vrf_cfg:ServerTable";
          description "Name server addresses";

          list server {
            xr:xr-xml-map "ip_domain_vrf_cfg:Server";
            xr:xr-cli-map "name-server <IPv4/IPv6 address> ";
            key "order server-address";
            description "Name server address";
            leaf order {
              xr:xr-xml-map "ip_domain_vrf_cfg:Order";
              type int32;
              description
                "This is used to sort the servers in the
                order of precedence";
            }
            leaf server-address {
              xr:xr-xml-map "ip_domain_vrf_cfg:ServerAddress";
              type inet:ip-address-no-zone;
              description "A name server address";
            }
          }
        }

        container lists {
          xr:xr-xml-map "ip_domain_vrf_cfg:ListTable";
          description
            "Domain names to complete unqualified host
            names";

          list list {
            xr:xr-xml-map "ip_domain_vrf_cfg:List";
            xr:xr-cli-map "list <string> ";
            key "order list-name";
            description
              "Domain name to complete unqualified host
              names";
            leaf order {
              xr:xr-xml-map "ip_domain_vrf_cfg:Order";
              type int32;
              description
                "This is used to sort the names in the order
                of precedence";
            }
            leaf list-name {
              xr:xr-xml-map "ip_domain_vrf_cfg:ListName";
              type xr:Cisco-ios-xr-string;
              description "A domain name";
            }
          }
        }

        container ipv4-hosts {
          xr:xr-xml-map "ip_domain_vrf_cfg:IPv4HostTable";
          description "IPv4 host";

          list ipv4-host {
            xr:xr-xml-map "ip_domain_vrf_cfg:IPv4Host";
            xr:xr-cli-map "ipv4 host <string> <IPv4 address> ";
            key "host-name";
            description "Host name and up to 8 host IPv4 addresses";
            leaf host-name {
              xr:xr-xml-map "ip_domain_vrf_cfg:Hostname";
              type string;
              description "A hostname";
            }
            leaf-list address {
              xr:xr-xml-map "ip_domain_vrf_cfg:Address";
              type inet:ipv4-address-no-zone;
              min-elements "1";
              max-elements "8";
              description "Host IPv4 addresses";
            }
          }
        }
        leaf lookup {
          xr:xr-xml-map "ip_domain_vrf_cfg:Lookup";
          xr:xr-cli-map "lookup disable ";
          type empty;
          description
            "Disable Domain Name System hostname
            translation";
        }
        leaf multicast-domain {
          xr:xr-xml-map "ip_domain_vrf_cfg:MulticastDomain";
          type string;
          description "Default multicast domain name";
        }
        leaf source-interface {
          xr:xr-xml-map "ip_domain_vrf_cfg:SourceInterface";
          xr:xr-cli-map "lookup source-interface <interface> ";
          type xr:Interface-name;
          description
            "Specify interface for source address in
            connections";
        }
        leaf name {
          xr:xr-xml-map "ip_domain_vrf_cfg:Name";
          xr:xr-cli-map "name <string> ";
          type string;
          description "Default domain name";
        }
        leaf vrf-name {
          xr:xr-xml-map "ip_domain_vrf_cfg:VRFName";
          type xr:Cisco-ios-xr-string;
          description "Name of the VRF instance";
        }
      }
    }

    container ipv6-host-table {
      xr:xr-xml-map "ip_domain_cfg:IPv6HostTable";
      description "IPv6 host";
    }

    container ipv4-host-table {
      xr:xr-xml-map "ip_domain_cfg:IPv4HostTable";
      description "IPv4 host";
    }
  }
}
