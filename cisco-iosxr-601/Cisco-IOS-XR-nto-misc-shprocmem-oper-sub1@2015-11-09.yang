submodule Cisco-IOS-XR-nto-misc-shprocmem-oper-sub1 {

  belongs-to Cisco-IOS-XR-nto-misc-shprocmem-oper {
    prefix Cisco-IOS-XR-nto-misc-shprocmem-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR nto-misc-shprocmem package operational data.

     Copyright (c) 2013-2015 by Cisco Systems, Inc.
     All rights reserved.";

  revision "2015-11-09" {
    description
      "IOS XR 6.0 revision.";
  }


  grouping PROCESSESMEMORY-ENTRY {
    description " Per Process Information";
    leaf name {
      xr:xr-xml-map "nto_misc_shprocmem:Name";
      type string;
      description "Process name";
    }
    leaf jid {
      xr:xr-xml-map "nto_misc_shprocmem:JID";
      type uint32;
      description "Job ID";
    }
    leaf text-seg-size {
      xr:xr-xml-map "nto_misc_shprocmem:text_seg_size";
      type uint32;
      description "Text Segment Size";
    }
    leaf data-seg-size {
      xr:xr-xml-map "nto_misc_shprocmem:data_seg_size";
      type uint32;
      description "Data Segment Size";
    }
    leaf stack-seg-size {
      xr:xr-xml-map "nto_misc_shprocmem:stack_seg_size";
      type uint32;
      description "Stack Segment Size";
    }
    leaf malloc-size {
      xr:xr-xml-map "nto_misc_shprocmem:malloc_size";
      type uint32;
      description "Malloced Memory Size";
    }
  }
}
