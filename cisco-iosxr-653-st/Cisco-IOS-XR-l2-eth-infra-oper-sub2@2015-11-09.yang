submodule Cisco-IOS-XR-l2-eth-infra-oper-sub2 {

  belongs-to Cisco-IOS-XR-l2-eth-infra-oper {
    prefix Cisco-IOS-XR-l2-eth-infra-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR l2-eth-infra package operational data.

     Copyright (c) 2013-2018 by Cisco Systems, Inc.
     All rights reserved.";

  revision "2015-11-09" {
    description
      "IOS XR 6.0 revision.";
  }

  typedef Vlan-service {
    type enumeration {
      enum vlan-service-l2 {
        value 1;
        description "Layer 2 Transport Service";
      }
      enum vlan-service-l3 {
        value 2;
        description "Layer 3 Terminated Service";
      }
    }
    description "Layer 2 vs. Layer 3 Terminated Service";
  }
  typedef Vlan-encaps {
    type enumeration {
      enum no-encapsulation {
        value 0;
        description "No encapsulation";
      }
      enum dot1q {
        value 1;
        description "IEEE 802.1Q encapsulation";
      }
      enum qinq {
        value 2;
        description "Double 802.1Q encapsulation";
      }
      enum qin-any {
        value 3;
        description "Double 802.1Q wildcarded encapsulation";
      }
      enum dot1q-native {
        value 4;
        description "IEEE 802.1Q native VLAN encapsulation";
      }
      enum dot1ad {
        value 5;
        description "IEEE 802.1ad encapsulation";
      }
      enum dot1ad-native {
        value 6;
        description "IEEE 802.1ad native VLAN encapsulation";
      }
      enum service-instance {
        value 7;
        description "Ethernet Service Instance";
      }
      enum dot1ad-dot1q {
        value 8;
        description "IEEE 802.1ad 802.1Q encapsulation";
      }
      enum dot1ad-any {
        value 9;
        description "IEEE 802.1ad wildcard 802.1Q encapsulation";
      }
    }
    description "VLAN encapsulation";
  }
  typedef Mac-address {
    type yang:mac-address;
    description "MAC address type";
  }
  typedef Efp-payload-etype {
    type enumeration {
      enum payload-ethertype-any {
        value 0;
        description "Any";
      }
      enum payload-ethertype-ip {
        value 1;
        description "IP";
      }
      enum payload-ethertype-pppoe {
        value 2;
        description "PPPoE";
      }
    }
    description "Payload ethertype match";
  }
  typedef Efp-tag-priority {
    type enumeration {
      enum priority0 {
        value 0;
        description "Priority 0";
      }
      enum priority1 {
        value 1;
        description "Priority 1";
      }
      enum priority2 {
        value 2;
        description "Priority 2";
      }
      enum priority3 {
        value 3;
        description "Priority 3";
      }
      enum priority4 {
        value 4;
        description "Priority 4";
      }
      enum priority5 {
        value 5;
        description "Priority 5";
      }
      enum priority6 {
        value 6;
        description "Priority 6";
      }
      enum priority7 {
        value 7;
        description "Priority 7";
      }
      enum priority-any {
        value 8;
        description "Any priority";
      }
    }
    description "Priority";
  }
  typedef Efp-tag-etype {
    type enumeration {
      enum untagged {
        value 0;
        description "Untagged";
      }
      enum dot1q {
        value 33024;
        description "Dot1Q";
      }
      enum dot1ad {
        value 34984;
        description "Dot1ad";
      }
    }
    description "Tag ethertype";
  }
  typedef Vlan-switched-mode {
    type enumeration {
      enum none {
        value 0;
        description "Disabled";
      }
      enum trunk-port {
        value 1;
        description "Trunk port";
      }
      enum access-port {
        value 2;
        description "Access port";
      }
    }
    description "VLAN-Switched mode";
  }
  typedef Eth-filtering {
    type enumeration {
      enum no-filtering {
        value 0;
        description
          "No IEEE 802.1Q/802.1ad/MAC relay multicast MAC
          address filtering";
      }
      enum dot1q-filtering {
        value 1;
        description "IEEE 802.1q C-VLAN filtering";
      }
      enum dot1ad-filtering {
        value 2;
        description "IEEE 802.1ad S-VLAN filtering";
      }
      enum two-port-mac-relay-filtering {
        value 3;
        description "IEEE 802.1aj 2-Port MAC relay filtering";
      }
    }
    description "Ethernet frame filtering";
  }
  typedef Vlan-qinq-outer-etype {
    type enumeration {
      enum ether-type8100 {
        value 33024;
        description "Dot1Q (0x8100)";
      }
      enum ether-type9100 {
        value 37120;
        description "0x9100";
      }
      enum ether-type9200 {
        value 37376;
        description "0x9200";
      }
    }
    description "QinQ Outer Tag Ethertype";
  }
  typedef Vlan-tag-value {
    type uint16;
    description "VLAN Tag Value (1 - 4094)";
  }
  typedef Im-state-enum {
    type enumeration {
      enum im-state-not-ready {
        description "im state not ready";
      }
      enum im-state-admin-down {
        description "im state admin down";
      }
      enum im-state-down {
        description "im state down";
      }
      enum im-state-up {
        description "im state up";
      }
      enum im-state-shutdown {
        description "im state shutdown";
      }
      enum im-state-err-disable {
        description "im state err disable";
      }
      enum im-state-down-immediate {
        description "im state down immediate";
      }
      enum im-state-down-immediate-admin {
        description "im state down immediate admin";
      }
      enum im-state-down-graceful {
        description "im state down graceful";
      }
      enum im-state-begin-shutdown {
        description "im state begin shutdown";
      }
      enum im-state-end-shutdown {
        description "im state end shutdown";
      }
      enum im-state-begin-error-disable {
        description "im state begin error disable";
      }
      enum im-state-end-error-disable {
        description "im state end error disable";
      }
      enum im-state-begin-down-graceful {
        description "im state begin down graceful";
      }
      enum im-state-reset {
        description "im state reset";
      }
      enum im-state-operational {
        description "im state operational";
      }
      enum im-state-not-operational {
        description "im state not operational";
      }
      enum im-state-unknown {
        description "im state unknown";
      }
      enum im-state-last {
        description "im state last";
      }
    }
    description "Im state enum";
  }

  grouping VLAN-DOUBLE-TAG-STACK {
    description "VLAN double tag stack";
    leaf outer-tag {
      type Vlan-tag-value;
      description "Outer tag value";
    }
    leaf second-tag {
      type Vlan-tag-value;
      description "Second tag value";
    }
  }

  grouping VLAN-TAG-STACK-TYPE {
    description "VLAN encapsulation and tag stack";

    container stack {
      when "../vlan-encapsulation = 'qinq'" {
        description "../VLANEncapsulation = 'QinQ'";
      }
      description "Stack value";
      uses VLAN-DOUBLE-TAG-STACK;
    }

    container service-instance-details {
      when "../vlan-encapsulation = 'service-instance'" {
        description "../VLANEncapsulation = 'ServiceInstance'";
      }
      description "Service Instance encapsulation";
      uses EFP-DESCRIPTION;
    }

    container dot1ad-dot1q-stack {
      when "../vlan-encapsulation = 'dot1ad-dot1q'" {
        description "../VLANEncapsulation = 'Dot1adDot1Q'";
      }
      description "802.1ad 802.1Q stack value";
      uses VLAN-DOUBLE-TAG-STACK;
    }
    leaf vlan-encapsulation {
      type Vlan-encaps;
      description "VLANEncapsulation";
    }
    leaf tag {
      when "../vlan-encapsulation = 'dot1q'" {
        description "../VLANEncapsulation = 'Dot1Q'";
      }
      type Vlan-tag-value;
      description "Tag value";
    }
    leaf outer-tag {
      when "../vlan-encapsulation = 'qin-any'" {
        description "../VLANEncapsulation = 'QinAny'";
      }
      type Vlan-tag-value;
      description "Outer tag value";
    }
    leaf native-tag {
      when "../vlan-encapsulation = 'dot1q-native'" {
        description "../VLANEncapsulation = 'Dot1QNative'";
      }
      type Vlan-tag-value;
      description "Native tag value";
    }
    leaf dot1ad-tag {
      when "../vlan-encapsulation = 'dot1ad'" {
        description "../VLANEncapsulation = 'Dot1ad'";
      }
      type Vlan-tag-value;
      description "802.1ad tag value";
    }
    leaf dot1ad-native-tag {
      when "../vlan-encapsulation = 'dot1ad-native'" {
        description "../VLANEncapsulation = 'Dot1adNative'";
      }
      type Vlan-tag-value;
      description "802.1ad native tag value";
    }
    leaf dot1ad-outer-tag {
      when "../vlan-encapsulation = 'dot1ad-any'" {
        description "../VLANEncapsulation = 'Dot1adAny'";
      }
      type Vlan-tag-value;
      description "802.1ad Outer tag value";
    }
  }

  grouping VLAN-INTF {
    description "VLAN Interface information";

    container encapsulation-details {
      description "Encapsulation type and tag stack";
      uses VLAN-TAG-STACK-TYPE;
    }
    leaf interface-xr {
      type xr:Interface-name;
      description "Interface";
    }
    leaf parent-interface {
      type xr:Interface-name;
      description "Parent interface";
    }
    leaf service {
      type Vlan-service;
      description "Service type";
    }
    leaf state {
      type Im-state-enum;
      description "Interface state";
    }
    leaf mtu {
      type uint16;
      description "L2 MTU";
    }
    leaf switched-mtu {
      type uint16;
      description "L2 switched MTU";
    }
  }

  grouping EFP-TAG-LOCAL-TRAFFIC-STACK {
    description "EFP TAG LOCAL TRAFFIC STACK";

    list local-traffic-tag {
      description "VLAN tags for locally-sourced traffic";
      uses EFP-VLAN-TAG;
    }
  }

  grouping EFP-VLAN-TAG {
    description "EFP VLAN TAG";
    leaf ethertype {
      type Efp-tag-etype;
      description "Ethertype of tag";
    }
    leaf vlan-id {
      type Vlan-tag-value;
      description "VLAN Id";
    }
  }

  grouping EFP-RANGE-TYPE {
    description "EFP RANGE TYPE";
    leaf vlan-id-low {
      type Vlan-tag-value;
      description "VLAN ID Low";
    }
    leaf vlan-id-high {
      type Vlan-tag-value;
      description "VLAN ID High";
    }
  }

  grouping EFP-TAG-MATCH {
    description "EFP TAG MATCH";
    leaf ethertype {
      type Efp-tag-etype;
      description "Ethertype of tag to match";
    }
    leaf priority {
      type Efp-tag-priority;
      description "Priority to match";
    }

    list vlan-range {
      description "VLAN Ids to match";
      uses EFP-RANGE-TYPE;
    }
  }

  grouping EFP-DESCRIPTION {
    description "EFP DESCRIPTION";

    container local-traffic-stack {
      description "VLAN tags for locally-sourced traffic";
      uses EFP-TAG-LOCAL-TRAFFIC-STACK;
    }
    leaf payload-ethertype {
      type Efp-payload-etype;
      description "Payload Ethertype to match";
    }
    leaf tags-popped {
      type uint16;
      description "Number of tags popped on ingress";
    }
    leaf is-exact-match {
      type boolean;
      description
        "Whether the packet must match the encapsulation
        exactly, with no further inner tags";
    }
    leaf is-native-vlan {
      type boolean;
      description
        "Whether this represents the native VLAN on the
        port";
    }
    leaf is-native-preserving {
      type boolean;
      description
        "Whether the native VLAN is customer-tag
        preserving";
    }
    leaf source-mac-match {
      type Mac-address;
      description "The source MAC address to match on ingress";
    }
    leaf destination-mac-match {
      type Mac-address;
      description "The destination MAC address to match on ingress";
    }

    list tags-to-match {
      description "Tags to match on ingress packets";
      uses EFP-TAG-MATCH;
    }

    list pushe {
      description "VLAN tags pushed on egress";
      uses EFP-VLAN-TAG;
    }
  }

  grouping VLAN-SWITCHED-INFO {
    description "VLAN-Switched information";

    container trunk-vlan-ranges {
      description "VLAN-Switched Trunk VLAN ranges";
      uses EFP-DESCRIPTION;
    }
    leaf mode {
      type Vlan-switched-mode;
      description "VLAN-Switched mode";
    }
    leaf access-vlan {
      type Vlan-tag-value;
      description "VLAN-Switched Access VLAN";
    }
  }

  grouping VLAN-TRUNK-L3-SUB-INTFS {
    description "Layer 3 Terminated Subinterfaces";

    container state-counters {
      description
        "Numbers of subinterfaces up, down or
        administratively shut down";
      uses VLAN-TRUNK-SUB-INTF-STATE-COUNTERS;
    }
    leaf total-count {
      type uint32;
      description
        "Total number of Layer 3 subinterfaces configured";
    }
    leaf dot1q-count {
      type uint32;
      description "Number of single tagged subinterfaces";
    }
    leaf qin-q-count {
      type uint32;
      description "Number of double tagged subinterfaces";
    }
    leaf untagged-count {
      type uint32;
      description
        "Number of subinterfaces without VLAN tag
        configuration";
    }
    leaf native-vlan {
      type Vlan-tag-value;
      description "Native VLAN ID configured on trunk";
    }
  }

  grouping VLAN-TRUNK-SUB-INTF-STATE-COUNTERS {
    description "Subinterface counters";
    leaf up {
      type uint32;
      description "Number of subinterfaces which are up";
    }
    leaf down {
      type uint32;
      description "Number of subinterfaces which are down";
    }
    leaf admin-down {
      type uint32;
      description
        "Number of subinterfaces which are
        administrativelyshutdown";
    }
  }

  grouping VLAN-TRUNK-L2-SUB-INTFS {
    description "Layer 2 Transport Subinterfaces";

    container state-counters {
      description
        "Numbers of subinterfaces up, down or
        administratively shut down";
      uses VLAN-TRUNK-SUB-INTF-STATE-COUNTERS;
    }
    leaf total-count {
      type uint32;
      description
        "Total number of Layer 2 subinterfaces configured";
    }
    leaf dot1q-count {
      type uint32;
      description "Number of single tagged subinterfaces";
    }
    leaf qin-q-count {
      type uint32;
      description
        "Number of double tagged subinterfaces with
        explicit inner tag";
    }
    leaf qin-any-count {
      type uint32;
      description
        "Number of double tagged subinterfaces with
        wildcarded inner tag";
    }
    leaf untagged-count {
      type uint32;
      description
        "Number of subinterfaces without VLAN tag
        configuration";
    }
  }

  grouping VLAN-TRUNK {
    description "VLAN trunk interface information";

    container layer2-sub-interfaces {
      description "Layer 2 Transport Subinterfaces";
      uses VLAN-TRUNK-L2-SUB-INTFS;
    }

    container layer3-sub-interfaces {
      description "Layer 3 Terminated Subinterfaces";
      uses VLAN-TRUNK-L3-SUB-INTFS;
    }

    container vlan-switched {
      description "VLAN-Switched information";
      uses VLAN-SWITCHED-INFO;
    }
    leaf interface-xr {
      type xr:Interface-name;
      description "Interface name";
    }
    leaf state {
      type Im-state-enum;
      description "Interface state";
    }
    leaf mtu {
      type uint16;
      description "L2 MTU";
    }
    leaf qinq-outer-ether-type {
      type Vlan-qinq-outer-etype;
      description "QinQ Outer Tag Ether Type";
    }
    leaf dot1ad-count {
      type uint32;
      description "Number of subinterfaces with 802.1ad outer tag";
    }
    leaf untagged-interface {
      type xr:Interface-name;
      description
        "Interface/Sub-interface handling untagged frames";
    }
    leaf mac-filtering {
      type Eth-filtering;
      description
        "IEEE 802.1Q/802.1ad multicast MAC address
        filtering";
    }
  }
}
