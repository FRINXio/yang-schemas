module Cisco-IOS-XR-ip-iarm-cfg {

  /*** NAMESPACE / PREFIX DEFINITION ***/

  namespace "http://cisco.com/ns/yang/Cisco-IOS-XR-ip-iarm-cfg";


  prefix "ip-iarm-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-iarm package configuration.

     This module contains definitions
     for the following management objects:
       ip-arm: IP Address Repository Manager (IPv4/IPv6 ARM)
         configuration data

     Copyright (c) 2013-2018 by Cisco Systems, Inc.
     All rights reserved.";

  revision "2015-11-09" {
    description
      "IOS XR 6.0 revision.";
  }

  typedef Ip-arm-conflict-policy {
    type enumeration {
      enum lowest-rack-slot {
        value 0;
        description "Lowest Rack/Slot";
      }
      enum static {
        value 1;
        description "UP interfaces unaffected";
      }
      enum longest-prefix {
        value 2;
        description "Longest Prefix";
      }
      enum highest-ip {
        value 4;
        description "Highest IP";
      }
    }
    description "Ip arm conflict policy";
  }

  grouping CONFLICT-POLICY-TABLE {
    description "Common node of ipv4, ipv6";

    container conflict-policy-table {
      description "IP ARM conflict policy configuration";
      leaf conflict-policy {
        type Ip-arm-conflict-policy;
        description "IP ARM conflict policy value definitions";
      }
    }
  }

  grouping MULTICAST-HOST {
    description "Common node of ipv4, ipv6";

    container multicast-host {
      description "IP ARM Multicast Host configuration";
      leaf multicast-host-interface {
        type xr:Interface-name;
        description "Default multicast host interface name";
      }
    }
  }

  container ip-arm {
    description
      "IP Address Repository Manager (IPv4/IPv6 ARM)
      configuration data";

    container ipv4 {
      description "IPv4 ARM configuration";
      uses CONFLICT-POLICY-TABLE;
      uses MULTICAST-HOST;
    }

    container ipv6 {
      description "IPv6 ARM configuration";
      uses CONFLICT-POLICY-TABLE;
      uses MULTICAST-HOST;
    }
  }
}
