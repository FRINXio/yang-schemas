module Cisco-IOS-XR-ipv6-nd-oper {

  /*** NAMESPACE / PREFIX DEFINITION ***/

  namespace "http://cisco.com/ns/yang/Cisco-IOS-XR-ipv6-nd-oper";


  prefix "ipv6-nd-oper";

  /*** LINKAGE (IMPORTS / INCLUDES) ***/

  import ietf-inet-types { prefix "inet"; }

  import Cisco-IOS-XR-types { prefix "xr"; }

  include Cisco-IOS-XR-ipv6-nd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-nd package operational data.

     This module contains definitions
     for the following management objects:
       ipv6-node-discovery: IPv6 node discovery operational data

     Copyright (c) 2013-2018 by Cisco Systems, Inc.
     All rights reserved.";

  revision "2015-11-09" {
    description
      "IOS XR 6.0 revision.";
  }


  container ipv6-node-discovery {
    config false;
    description "IPv6 node discovery operational data";

    container nodes {
      description "IPv6 node discovery list of nodes";

      list node {
        key "node-name";
        description
          "IPv6 node discovery operational data for a
          particular node";

        container neighbor-interfaces {
          description
            "IPv6 node discovery list of neighbor
            interfaces";

          list neighbor-interface {
            key "interface-name";
            description "IPv6 node discovery neighbor interface";

            container host-addresses {
              description
                "IPv6 node discovery list of neighbor host
                addresses";

              list host-address {
                key "host-address";
                description "IPv6 Neighbor detailed information";
                leaf host-address {
                  type inet:ipv6-address-no-zone;
                  description "Host Address";
                }
                uses IPV6-ND-NEIGHBOR-ENTRY;
              }
            }
            leaf interface-name {
              type xr:Interface-name;
              description "Interface Name";
            }
          }
        }

        container neighbor-summary {
          description "IPv6 Neighbor summary";
          uses IPV6-ND-NEIGHBOR-ENTRY-SUMMARY;
        }

        container bundle-nodes {
          description
            "IPv6 ND list of bundle nodes for a specific
            node";

          list bundle-node {
            key "node-name";
            description
              "IPv6 ND operational data for a specific
              bundle node";
            leaf node-name {
              type xr:Node-id;
              description "The bundle node name";
            }
            uses IPV6-ND-BL-NODE-ENTRY;
          }
        }

        container bundle-interfaces {
          description
            "IPv6 ND list of bundle interfaces for a
            specific node";

          list bundle-interface {
            key "interface-name";
            description
              "IPv6 ND operational data for a specific
              bundler interface";
            leaf interface-name {
              type xr:Interface-name;
              description "Interface Name";
            }
            uses IPV6-ND-IF-ENTRY;
          }
        }

        container interfaces {
          description
            "IPv6 node discovery list of interfaces for a
            specific node";

          list interface {
            key "interface-name";
            description
              "IPv6  node discovery operational data for a
              specific node and interface";
            leaf interface-name {
              type xr:Interface-name;
              description "Interface Name";
            }
            uses IPV6-ND-IF-PARAMS;
          }
        }

        container nd-virtual-routers {
          description
            "IPv6 ND virtual router information for a
            specific interface";

          list nd-virtual-router {
            key "interface-name";
            description
              "IPv6 ND virtual  router operational data for
              a specific interface";
            leaf interface-name {
              type xr:Interface-name;
              description "Interface Name";
            }
            uses IPV6-ND-VR-ENTRY;
          }
        }

        container slaac-interfaces {
          description
            "IPv6 ND list of SLAAC MGMT interfaces for a
            specific node";

          list slaac-interface {
            key "interface-name";
            description
              "IPv6 ND operational data for a specific slaac
              interface";

            container router-advert-detail {
              description
                "IPv6 ND operational data for a specific
                slaac interface";
              uses IPV6-ND-SLAAC-INTFS-INFO;
            }
            leaf interface-name {
              type xr:Interface-name;
              description "Interface Name";
            }
          }
        }
        leaf node-name {
          type xr:Node-id;
          description "The node name";
        }
      }
    }
  }
}
