submodule Cisco-IOS-XR-Subscriber-infra-subdb-oper-sub2 {

  belongs-to Cisco-IOS-XR-Subscriber-infra-subdb-oper {
    prefix Cisco-IOS-XR-Subscriber-infra-subdb-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR Subscriber-infra-subdb package operational data.

     Copyright (c) 2013-2018 by Cisco Systems, Inc.
     All rights reserved.";

  revision "2015-11-09" {
    description
      "IOS XR 6.0 revision.";
  }


  grouping SUBDB-SUMMARY-COUNTS-BAG {
    description "SUBDB SUMMARY COUNTS BAG";
    leaf assoc-db-entries {
      type uint32;
      description "Number of Entries in Association DB";
    }
    leaf assoc-db-associations {
      type uint32;
      description "Number of Associations in Association DB";
    }
    leaf derived-db-entries {
      type uint32;
      description "Number of Entries in Derived DB";
    }
    leaf config-db-entries {
      type uint32;
      description "Number of Entries in Configuration DB";
    }
    leaf interface-db-entries {
      type uint32;
      description "Number of Entries in Interface DB";
    }
    leaf num-ipsub-dhcp {
      type uint32;
      description "Number of IPSUB DHCP subscribers";
    }
    leaf num-ipsub-inband {
      type uint32;
      description "Number of IPSUB Inband subscribers";
    }
    leaf num-pppoe {
      type uint32;
      description "Number of PPPOE subscribers";
    }
    leaf-list subdb-obj-counts-by-type {
      type uint32;
      max-elements "16";
      description
        "The count of the various configuration objects
        by type";
    }
    leaf-list num-subscribers-in-state {
      type uint32;
      max-elements "32";
      description "Number of subscribers in the various states";
    }
    leaf-list num-transitions-through-state {
      type uint32;
      max-elements "32";
      description
        "Cumulative number of transitions through the
        various states";
    }
  }
}
