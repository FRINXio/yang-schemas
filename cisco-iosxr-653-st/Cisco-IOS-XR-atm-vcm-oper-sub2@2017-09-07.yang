submodule Cisco-IOS-XR-atm-vcm-oper-sub2 {

  belongs-to Cisco-IOS-XR-atm-vcm-oper {
    prefix Cisco-IOS-XR-atm-vcm-oper;
  }

  /*** LINKAGE (IMPORTS / INCLUDES) ***/

  import Cisco-IOS-XR-types { prefix "xr"; }

  include Cisco-IOS-XR-atm-vcm-oper-sub4 {
    revision-date 2017-09-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR atm-vcm package operational data.

     Copyright (c) 2013-2018 by Cisco Systems, Inc.
     All rights reserved.";

  revision "2017-09-07" {
    description
      "Fixed type translation error.";
  }

  revision "2015-11-09" {
    description
      "IOS XR 6.0 revision.";
  }

  typedef Vcm-port {
    type enumeration {
      enum port-type-layer-2 {
        value 0;
        description " Layer 2 ATM port type ";
      }
      enum port-type-layer-3 {
        value 1;
        description " Layer 3 ATM port type ";
      }
      enum port-type-unknown {
        value 3;
        description " ATM port type unknown ";
      }
    }
    description "ATM port type";
  }

  grouping ATM-VCM-IF {
    description "ATM Interface configuration";

    container cell-packing-data {
      description "Cell packing specific information";
      uses ATM-VCM-CELL-PACKING-INFO;
    }
    leaf ilmi-vpi {
      type uint32;
      description "ILMI VPI";
    }
    leaf ilmi-vci {
      type uint32;
      description "ILMI VCI";
    }
    leaf pvc-failures {
      type uint32;
      description "Number of PVC Failures";
    }
    leaf currently-failing-layer2pv-ps {
      type uint32;
      description "Number of currently failing Layer 2 PVPs";
    }
    leaf currently-failing-layer2pv-cs {
      type uint32;
      description "Number of currently failing Layer 2 PVCs";
    }
    leaf currently-failing-layer3vp-tunnels {
      type uint32;
      description "Number of currently failing Layer 3 VP tunnels";
    }
    leaf currently-failing-layer3pv-cs {
      type uint32;
      description "Number of currently failing Layer 3 PVCs";
    }
    leaf pvc-failures-trap-enable {
      type boolean;
      description "If true, PVC failures trap is enabled";
    }
    leaf pvc-notification-interval {
      type uint32;
      description "PVC trap notification interval";
    }
    leaf configured-layer2pv-ps {
      type uint32;
      description "Number of Layer 2 PVPs configured";
    }
    leaf configured-layer2pv-cs {
      type uint32;
      description "Number of Layer 2 PVCs configured";
    }
    leaf configured-layer3vp-tunnels {
      type uint32;
      description "Number of Layer 3 VP tunnels configured";
    }
    leaf configured-layer3pv-cs {
      type uint32;
      description "Number of Layer 3 PVCs configured";
    }
    leaf port-type {
      type Vcm-port;
      description "ATM interface port type";
    }
    leaf main-interface {
      type xr:Interface-name;
      description "Main Interface handle";
    }
    leaf l2-cell-packing-count {
      type uint16;
      description
        "Number of L2 attachment circuits with the cell
        packing feature enabled on this main interface";
    }
  }
}
