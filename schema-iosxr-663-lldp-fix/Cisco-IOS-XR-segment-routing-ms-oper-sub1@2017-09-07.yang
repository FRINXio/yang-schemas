submodule Cisco-IOS-XR-segment-routing-ms-oper-sub1 {

  belongs-to Cisco-IOS-XR-segment-routing-ms-oper {
    prefix Cisco-IOS-XR-segment-routing-ms-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR segment-routing-ms package operational data.

     Copyright (c) 2013-2018 by Cisco Systems, Inc.
     All rights reserved.";

  revision "2017-09-07" {
    description
      "Fixed type translation error.";
  }

  revision "2015-11-09" {
    description
      "IOS XR 6.0 revision.";
  }


  grouping MPLS-LSD-SRLB-INCONSISTENCY {
    description "SRLB Inconsistency";
    leaf start-srlb-range {
      type uint32;
      description
        "Start label of Segment Routing Local Block range";
    }
    leaf end-srlb-range {
      type uint32;
      description "End label of Segment Routing Local Block range";
    }
  }
}
