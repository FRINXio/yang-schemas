module Cisco-IOS-XR-ipv4-igmp-dyn-tmpl-cfg {

  /*** NAMESPACE / PREFIX DEFINITION ***/

  namespace "http://cisco.com/ns/yang"+
    "/Cisco-IOS-XR-ipv4-igmp-dyn-tmpl-cfg";


  prefix "ipv4-igmp-dyn-tmpl-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-igmp-dyn-tmpl package configuration.

     This YANG module augments the
       Cisco-IOS-XR-subscriber-infra-tmplmgr-cfg
     module with configuration data.

     Copyright (c) 2013-2018 by Cisco Systems, Inc.
     All rights reserved.";

  revision "2015-11-09" {
    description
      "IOS XR 6.0 revision.";
  }

  typedef Dyn-tmpl-multicast-mode {
    type enumeration {
      enum qos-correlation {
        value 1;
        description "QOS Correlation";
      }
      enum passive {
        value 2;
        description "Passive";
      }
    }
    description "Dyn tmpl multicast mode";
  }

  grouping IGMP {
    description "Common node of ppp, ip-subscriber";

    container igmp {
      description "IGMPconfiguration";

      container default-vrf {
        description "Default VRF";

        container explicit-tracking {
          presence "Indicates a explicit-tracking node is"+
            " configured.";
          description "IGMPv3 explicit host tracking";
          leaf enable {
            type boolean;
            mandatory true;
            description
              "Enable or disable, when value is TRUE or
              FALSE respectively";
          }
          leaf access-list-name {
            type xr:Cisco-ios-xr-string {
              length "1..64";
            }
            description
              "Access list specifying tracking group range";
          }
        }
        leaf max-groups {
          type uint32 {
            range "1..40000";
          }
          default "25000";
          description "IGMP Max Groups";
        }
        leaf access-group {
          type xr:Cisco-ios-xr-string {
            length "1..64";
          }
          description
            "Access list specifying access-list group range";
        }
        leaf version {
          type uint32 {
            range "1..3";
          }
          default "3";
          description "IGMP Version";
        }
        leaf query-interval {
          type uint32 {
            range "1..3600";
          }
          units "second";
          default "60";
          description "Query interval in seconds";
        }
        leaf query-max-response-time {
          type uint32 {
            range "1..25";
          }
          units "second";
          default "10";
          description "Query response value in seconds";
        }
        leaf multicast-mode {
          type Dyn-tmpl-multicast-mode;
          description "Configure Multicast mode variable";
        }
      }
    }
  }

  augment "/a1:dynamic-template/a1:ip-subscribers/a1:ip-subscriber" {
    description
      "This augment extends the configuration data of
      'Cisco-IOS-XR-subscriber-infra-tmplmgr-cfg'";
    uses IGMP;
  }

  augment "/a1:dynamic-template/a1:ppps/a1:ppp" {
    description
      "This augment extends the configuration data of
      'Cisco-IOS-XR-subscriber-infra-tmplmgr-cfg'";
    uses IGMP;
  }
}
