module Cisco-IOS-XR-sysadmin-show-trace-debug-agent {
  namespace "http://www.cisco.com/ns/yang/Cisco-IOS-XR-sysadmin-show-trace-debug-agent";
  prefix debug_agent;
  import Cisco-IOS-XR-sysadmin-show-trace {
    prefix show_trace;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

Copyright(c) 2012-2017 by Cisco Systems, Inc.
All rights reserved.

    Copyright (c) 2012-2018 by Cisco Systems, Inc.
     All rights reserved.";
  revision 2017-04-12 {
    description
      "Changed the namespace and module name";
  }

  container debug_agent {
    config false;
    uses show_trace:traceable;
  }
}
