submodule Cisco-IOS-XR-lpts-ifib-oper-sub1 {

  belongs-to Cisco-IOS-XR-lpts-ifib-oper {
    prefix Cisco-IOS-XR-lpts-ifib-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lpts-ifib package operational data.

     Copyright (c) 2013-2018 by Cisco Systems, Inc.
     All rights reserved.";

  revision "2018-12-17" {
    description
      "slice-id/entry type changed from Integer to Hex-integer.";
  }

  revision "2017-09-07" {
    description
      "Fixed type translation error.";
  }

  revision "2015-11-09" {
    description
      "IOS XR 6.0 revision.";
  }


  grouping FM-IFIB-ENTRY {
    description "LPTS IFIB Slice Entry Information";
    leaf destination-type {
      type string;
      description "Destination Key Type";
    }
    leaf destination-value {
      type string;
      description "Destination Port/ICMP Type/IGMP Type";
    }
    leaf source-port {
      type string;
      description "Source port";
    }
    leaf destination-addr {
      type string;
      description "Destination IP Address";
    }
    leaf source-addr {
      type string;
      description "Source IP Address";
    }
    leaf vrf-name {
      type string;
      description "VRF Name";
    }
    leaf vid {
      type uint32;
      description "VRF ID";
    }
    leaf l3protocol {
      type uint32;
      description "Layer 3 Protocol";
    }
    leaf l4protocol {
      type uint32;
      description "Layer 4 Protocol";
    }
    leaf intf-name {
      type string;
      description "Interface Name";
    }
    leaf intf-handle {
      type uint32;
      description "Interface Handle";
    }
    leaf is-syn {
      type uint8;
      description "Is SYN";
    }
    leaf opcode {
      type string;
      description "Opcode";
    }
    leaf accepts {
      type uint64;
      description "Packets matched to accept";
    }
    leaf drops {
      type uint64;
      description "Packets matched to drop";
    }
    leaf flow-type {
      type string;
      description "Flow type";
    }
    leaf listener-tag {
      type string;
      description "Listener Tag";
    }
    leaf local-flag {
      type uint8;
      description "Local Flag";
    }
    leaf is-fgid {
      type uint8;
      description "Is FGID or not";
    }
    leaf deliver-list-short {
      type string;
      description "Deliver List Short Format";
    }
    leaf deliver-list-long {
      type string;
      description "Deliver List Long Format";
    }
    leaf min-ttl {
      type uint8;
      description "Minimum TTL";
    }
    leaf pending-ifibq-delay {
      type uint32;
      description "pending ifib queue delay";
    }
    leaf sl-ifibq-delay {
      type uint32;
      description "sl_ifibq delay";
    }
    leaf ifib-program-time {
      type string;
      description "ifib program time in netio";
    }
  }
}
