module Cisco-IOS-XR-ipv4-ma-oper {

  /*** NAMESPACE / PREFIX DEFINITION ***/

  namespace "http://cisco.com/ns/yang/Cisco-IOS-XR-ipv4-ma-oper";


  prefix "ipv4-ma-oper";

  /*** LINKAGE (IMPORTS / INCLUDES) ***/

  import Cisco-IOS-XR-types { prefix "xr"; }

  import Cisco-IOS-XR-ipv4-io-oper { prefix "a1"; }

  include Cisco-IOS-XR-ipv4-ma-oper-sub1 {
    revision-date 2018-08-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-ma package operational data.

     This YANG module augments the
       Cisco-IOS-XR-ipv4-io-oper
     module with state data.

     Copyright (c) 2013-2018 by Cisco Systems, Inc.
     All rights reserved.";

  revision "2018-08-01" {
    description
      "Removed empty groupings.";
  }

  revision "2017-08-23" {
    description
      "IPV4 MA schema file has all the latest changes.";
  }

  revision "2015-01-07" {
    description
      "IOS XR 5.3.1 revision.";
  }


  augment "/a1:ipv4-network" {

    container interfaces {
      description "IPv4 network operational interface data";

      list interface {
        key "interface-name";
        description "Interface names with VRF";

        container vrfs {
          description "List of VRF on the interface";

          list vrf {
            key "vrf-name";
            description "VRF information on the interface";

            container detail {
              description
                "Detail IPv4 network operational data for an
                interface";
              uses IPV4-IF-DETAIL;
            }

            container brief {
              description
                "Brief IPv4 network operational data for an
                interface";
              uses IPV4-IF-BRIEF;
            }
            leaf vrf-name {
              type xr:Cisco-ios-xr-string;
              description "The VRF name";
            }
          }
        }
        leaf interface-name {
          type xr:Interface-name;
          description "The name of the interface";
        }
      }
    }
    description
      "This augment extends the operational data of
      'Cisco-IOS-XR-ipv4-io-oper'";
  }
}
