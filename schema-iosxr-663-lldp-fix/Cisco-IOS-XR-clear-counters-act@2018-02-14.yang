module Cisco-IOS-XR-clear-counters-act {

    namespace "http://cisco.com/ns/yang/Cisco-IOS-XR-clear-counters-act";
    
    prefix "clear-counters-act";
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR Controller to clear alarm counters.

     Copyright (c) 2018 by Cisco Systems, Inc.
     All rights reserved.";
    
    revision "2018-02-14" {
        description
            "IOS XR 6.5.1 revision.";
    } 
    
    rpc clear-counters {
        description "Execute clear counters operations";
        input {
            leaf controller {
                description "Controller name in R/S/I/P format";
                type string;
            }
        }
    }
}
