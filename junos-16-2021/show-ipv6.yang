/*
 * Copyright (c) 2021 Juniper Networks, Inc.
 * All rights reserved.
 */

// FRINX use empty string namespace
 module show-ipv6 {
  namespace "urn:ietf:params:xml:ns:netconf:base:1.0";
  prefix jrpc;


  // FRINX include submodules
  include "show-rip";

  import junos-extension {
    prefix junos;
  }
  
  // FRINX add operation types
  import operation_types {
    prefix "operation_type";
  }

  organization
    "Juniper Networks, Inc.";

  description
    "Junos YANG module for RPC";


   rpc get-ipv6-nd-information {
     description "Show IPv6 neighbor cache information";
     // FRINX change to anyxml output
     output{
      anyxml ipv6-nd-information;
     }
   }
   rpc get-ipv6-ra-information {
     description "Show IPv6 router advertisement information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf conflicts {
         description "Display conflicting information";
         type empty;
       }
       leaf prefix {
         description "Prefix and optional prefix length";
         type operation_type:ipv6prefix;
       }
       leaf virtual-router {
         description "Display only virtual-interface information";
         type empty;
       }
     }
     output {
       container ipv6-ra-information {
         container ipv6-ra-interface {
           leaf interface-name {
             type string;
             description "Name of interface";
           }
           leaf ipv6-ra-advertisements-sent {
             type int32;
             description "Number of router advertisements sent";
           }
           leaf ipv6-ra-advertisement-sent-time {
             type string;
             description "How long since the last router advertisement was sent";
           }
           leaf ipv6-ra-solicits-received {
             type int32;
             description "Number of router solicitations received";
           }
           leaf ipv6-ra-solicit-receive-time {
             type string;
             description "How long since the last router solicitation was sent";
           }
           leaf ipv6-ra-advertisements-received {
             type int32;
             description "Number of router advertisements received";
           }
           leaf ipv6-ra-solicit-router-advertisement-unicast {
             type int32;
             description "Enable forwarding IPv6 Solicited Router Advert as unicast";
           }
           leaf ipv6-ra-solicit-router-advertisement-preference {
             type string;
             description "Preference for Router Selection based on RA";
           }
           container vrrp-group {
             leaf vrrp-group-id {
               type int32;
               description "Group ID of the configured VRRP group";
             }
             leaf vrrp-advertisements-sent {
               type int32;
               description "Number of advertisements sent";
             }
             leaf vrrp-advertisement-sent-time {
               type string;
               description "How long since the last advertisement was sent";
             }
             leaf vrrp-solicits-received {
               type int32;
               description "Number of router solicitations received";
             }
             leaf vrrp-solicit-receive-time {
               type string;
               description "How long since the last solicitation was sent";
             }
             leaf vrrp-advertisements-received {
               type int32;
               description "Number of advertisements received";
             }
           }
           container ipv6-ra-advertisement {
             leaf ipv6-source-address {
               type operation_type:ipv6addr;
               description "Sender of the advertisement";
             }
             leaf ipv6-ra-time-since {
               type string;
               description "How long since the advertisement was received";
             }
             leaf ipv6-ra-managed-flag {
               type int32;
               description "Advertised managed flag";
             }
             leaf ipv6-ra-managed-flag-conflict {
               type int32;
               description "Conflict with the advertised managed flag";
             }
             leaf ipv6-ra-other-config-flag {
               type int32;
               description "Advertised other configuration flag";
             }
             leaf ipv6-ra-other-config-flag-conflict {
               type int32;
               description "Conflict with the advertised other configuration flag";
             }
             leaf ipv6-ra-link-mtu {
               type int32;
               description "Advertised link MTU";
             }
             leaf ipv6-ra-link-mtu-conflict {
               type int32;
               description "Conflict with the advertised link MTU";
             }
             leaf ipv6-ra-reachable-time {
               type int32;
               description "Advertised reachable time";
             }
             leaf ipv6-ra-reachable-time-conflict {
               type int32;
               description "Conflict with the advertised reachable time";
             }
             leaf ipv6-ra-default-lifetime {
               type int32;
               description "Advertised default lifetime flag";
             }
             leaf ipv6-ra-default-lifetime-conflict {
               type int32;
               description "Conflict with the advertised default lifetime flag";
             }
             leaf ipv6-ra-retransmit-timer {
               type int32;
               description "Advertised retransmit timer flag";
             }
             leaf ipv6-ra-retransmit-timer-conflict {
               type int32;
               description "Conflict with the advertised retransmit timer flag";
             }
             leaf ipv6-ra-current-hop-limit {
               type int32;
               description "Advertised current hop limit flag";
             }
             leaf ipv6-ra-current-hop-limit-conflict {
               type int32;
               description "Conflict with the advertised current hop limit flag";
             }
             container ipv6-ra-rdnss {
               leaf ipv6-ra-rdnss-address {
                 type operation_type:ipv6addr;
                 description "Advertised RDNSS address";
               }
               leaf ipv6-ra-rdnss-lifetime {
                 type int32;
                 description "Advertised lifetime of the RDNSS address";
               }
               leaf ipv6-ra-rdnss-lifetime-conflict {
                 type int32;
                 description "Conflict with the advertised lifetime of the RDNSS address";
               }
             }
             container ipv6-ra-prefix {
               leaf ipv6-ra-prefix-address {
                 type operation_type:ipv6prefix;
                 description "Advertised prefix";
               }
               leaf ipv6-ra-prefix-valid-lifetime {
                 type int32;
                 description "Advertised valid lifetime of the prefix";
               }
               leaf ipv6-ra-prefix-valid-lifetime-conflict {
                 type int32;
                 description "Conflict with the advertised valid lifetime of the prefix";
               }
               leaf ipv6-ra-prefix-preferred-lifetime {
                 type int32;
                 description "Advertised preferred lifetime of the prefix";
               }
               leaf ipv6-ra-prefix-preferred-lifetime-conflict {
                 type int32;
                 description "Conflict with the advertised preferred lifetime of the prefix";
               }
               leaf ipv6-ra-prefix-on-link {
                 type int32;
                 description "Advertised on-link flag of the prefix";
               }
               leaf ipv6-ra-prefix-on-link-conflict {
                 type int32;
                 description "Conflict with the advertised on-link flag of the prefix";
               }
               leaf ipv6-ra-prefix-autonomous {
                 type int32;
                 description "Advertised autonomous flag of the prefix";
               }
               leaf ipv6-ra-prefix-autonomous-conflict {
                 type int32;
                 description "Conflict with the advertised autonomous flag of the prefix";
               }
             }
           }
         }
       }
     }
   }
 }
