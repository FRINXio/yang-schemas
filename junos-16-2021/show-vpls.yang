/*
 * Copyright (c) 2021 Juniper Networks, Inc.
 * All rights reserved.
 */


// FRINX change show-vpls to submodule 
 submodule show-vpls {
  belongs-to show-route {
    prefix "jrpc";
  }

  import junos-extension {
    prefix junos;
  }

  // FRINX add operation types
  import operation_types {
    prefix "operation_type";
  }

  organization
    "Juniper Networks, Inc.";

  description
    "Junos YANG module for RPC";


   rpc get-vpls-connection-information {
     description "Show VPLS connections information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of VPLS instance";
         default "all";
         type string;
       }
       leaf local-site {
         description "Name or ID of VPLS local site";
         default "all";
         type string;
       }
       leaf remote-site {
         description "ID of VPLS remote site";
         default "all";
         type string;
       }
       leaf state {
         default "up-down";
         type enumeration {
           enum "down" {
             description "Display nonoperational connections";
           }
           enum "up" {
             description "Display operational connections";
           }
           enum "up-down" {
             description "Display both non- and operational connections (default)";
           }
         }
       }
       leaf level {
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and circuit status (default)";
           }
           enum "summary" {
             description "Display summary output";
           }
         }
       }
     }
     // FRINX change to anyxml output
     output{
      anyxml vpls-connection-information;
     }
   }
   rpc get-vpls-statistics-information {
     description "Show VPLS statistics information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of VPLS instance";
         default "all";
         type string;
       }
     }
     output {
       container vpls-statistics-information {
         container instance {
           leaf instance-name {
             type string;
           }
// FRINX comment out container normal {
             leaf instance-display-error {
               type string;
             }
             leaf edge-protection {
               type string;
             }
             leaf edge-protector {
               type string;
             }
            // FRINX change reference site from container to list  (There is multiple reference site in output)
            list reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type operation_type:ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               container mesh-group-interfaces {
                 description "Information about all interfaces associated with a mesh-group";
                 leaf mesh-group-name {
                   type string;
                   description "Name of mesh-group";
                 }
                 leaf mesh-group-state {
                   type string;
                   description "Mesh-group state";
                 }
                 leaf mesh-group-id {
                   type int32;
                   description "Mesh-group Identifier";
                 }
                 container interface {
                   leaf interface-name {
                     type string;
                     description "Name of interface";
                   }
                   leaf interface-description {
                     type string;
                   }
                   leaf interface-flags-description {
                     type string;
                   }
                   leaf interface-flags {
                     type int32;
                   }
                 }
               }
               container interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container label-block {
                 leaf label-block.heading {
                   type string;
                 }
                 leaf label-block-base {
                   type int32;
                 }
                 leaf label-block-offset {
                   type int32;
                 }
                 leaf label-block-size {
                   type int32;
                 }
                 leaf label-block-range {
                   type int32;
                 }
                 leaf label-block-preference {
                   type int32;
                 }
                 leaf label-block-status-vector {
                   type string;
                 }
               }
               container connection {
                 leaf connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type operation_type:ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 container local-interface {
                   leaf interface-name {
                     type string;
                     description "Name of interface";
                   }
                   leaf interface-status {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   description "Information about one or more VPLS RSVP-TE point-to-multipoint LSPs";
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container spe-info {
                   leaf spe-info.heading {
                     type string;
                   }
                   leaf local-ip-addr {
                     type operation_type:ipaddr;
                   }
                   leaf remote-ip-addr {
                     type operation_type:ipaddr;
                   }
                   leaf pw-status {
                     type string;
                   }
                 }
                 container history {
                   leaf history.category-heading {
                     type string;
                   }
                   leaf history.heading {
                     type string;
                   }
                   leaf log-time-stamp {
                     type string;
                   }
                   leaf log-event {
                     type string;
                   }
                   leaf changed-entity {
                     type string;
                   }
                 }
               }
               container mesh-group-connection {
                 description "Information about all vc-connections of a specific mesh-group";
                 leaf mesh-group-name {
                   type string;
                   description "Name of mesh-group";
                 }
                 container connection {
                   leaf connection.heading {
                     type string;
                   }
                   leaf connection-id {
                     type string;
                   }
                   leaf connection-type {
                     type string;
                   }
                   leaf connection-status {
                     type string;
                   }
                   leaf last-change {
                     type string;
                   }
                   leaf up-transitions {
                     type int32;
                   }
                   leaf remote-pe {
                     type operation_type:ipaddr;
                   }
                   leaf control-word {
                     type string;
                   }
                   leaf control-word-type {
                     type string;
                   }
                   leaf interface-encapsulation {
                     type string;
                   }
                   leaf inbound-label {
                     type string;
                   }
                   leaf outbound-label {
                     type string;
                   }
                   leaf pw-status-tlv {
                     type string;
                   }
                   leaf local-pw-status-code {
                     type int32;
                   }
                   leaf remote-pw-status-code {
                     type int32;
                   }
                   leaf connection-protection {
                     type string;
                   }
                   leaf vc-flow-label-transmit {
                     type string;
                   }
                   leaf vc-flow-label-receive {
                     type string;
                   }
                   container local-interface {
                     leaf interface-name {
                       type string;
                       description "Name of interface";
                     }
                     leaf interface-status {
                       type string;
                     }
                     leaf working-status {
                       type string;
                     }
                     leaf profile-name {
                       type string;
                     }
                     leaf profile-varset-name {
                       type string;
                     }
                     leaf interface-description {
                       type string;
                     }
                   }
                   container remote-interface {
                     leaf interface-name {
                       type string;
                       description "Name of interface";
                     }
                     leaf interface-status {
                       type string;
                     }
                     leaf interface-encapsulation {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
               container automatic-site-timers {
                 leaf automatic-site-timers.heading {
                   type string;
                 }
                 leaf automatic-site-startup-wait-time {
                   type string;
                 }
                 leaf automatic-site-new-site-wait-time {
                   type string;
                 }
                 leaf automatic-site-collision-detect-time {
                   type string;
                 }
                 leaf automatic-site-reclaim-wait-time {
                   type string;
                 }
               }
             }
             container ldp-vpls-reference-site {
               description "Information about LDP-VPLS";
               leaf vpls-signaling-protocol-identifier {
                 type string;
               }
               leaf local-site-id {
                 type string;
               }
               leaf vpls-id {
                 type int32;
                 description "VPLS instance identifier";
               }
               leaf l2vpn-id {
                 type string;
               }
               leaf local-id {
                 type operation_type:ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               container mesh-group-interfaces {
                 description "Information about all interfaces associated with a mesh-group";
                 leaf mesh-group-name {
                   type string;
                   description "Name of mesh-group";
                 }
                 leaf mesh-group-state {
                   type string;
                   description "Mesh-group state";
                 }
                 leaf mesh-group-id {
                   type int32;
                   description "Mesh-group Identifier";
                 }
                 container interface {
                   leaf interface-name {
                     type string;
                     description "Name of interface";
                   }
                   leaf interface-description {
                     type string;
                   }
                   leaf interface-flags-description {
                     type string;
                   }
                   leaf interface-flags {
                     type int32;
                   }
                 }
               }
               container interface {
                 leaf interface-name {
                   type string;
                   description "Name of interface";
                 }
                 leaf interface-id {
                   type int32;
                 }
                 leaf interface-description {
                   type string;
                 }
                 leaf interface-flags-description {
                   type string;
                 }
                 leaf interface-flags {
                   type int32;
                 }
               }
               container connection {
                 leaf connection.heading {
                   type string;
                 }
                 leaf connection-id {
                   type string;
                 }
                 leaf connection-type {
                   type string;
                 }
                 leaf connection-status {
                   type string;
                 }
                 leaf last-change {
                   type string;
                 }
                 leaf up-transitions {
                   type int32;
                 }
                 leaf remote-pe {
                   type operation_type:ipaddr;
                 }
                 leaf control-word {
                   type string;
                 }
                 leaf control-word-type {
                   type string;
                 }
                 leaf interface-encapsulation {
                   type string;
                 }
                 leaf inbound-label {
                   type string;
                 }
                 leaf outbound-label {
                   type string;
                 }
                 leaf pw-status-tlv {
                   type string;
                 }
                 leaf local-pw-status-code {
                   type int32;
                 }
                 leaf remote-pw-status-code {
                   type int32;
                 }
                 leaf connection-protection {
                   type string;
                 }
                 leaf mesh-group-name {
                   type string;
                   description "Name of mesh-group";
                 }
                 leaf vc-flow-label-transmit {
                   type string;
                 }
                 leaf vc-flow-label-receive {
                   type string;
                 }
                 container local-interface {
                   leaf interface-name {
                     type string;
                     description "Name of interface";
                   }
                   leaf interface-status {
                     type string;
                   }
                   leaf working-status {
                     type string;
                   }
                   leaf profile-name {
                     type string;
                   }
                   leaf profile-varset-name {
                     type string;
                   }
                   leaf interface-description {
                     type string;
                   }
                 }
                 container remote-interface {
                   leaf interface-name {
                     type string;
                     description "Name of interface";
                   }
                   leaf interface-status {
                     type string;
                   }
                   leaf interface-encapsulation {
                     type string;
                   }
                 }
                 container connection-bandwidth {
                   description "Bandwidth of a layer 2 connection";
                   leaf connection-bandwidth.heading {
                     type string;
                     description "Bandwidth of a layer 2 connection";
                   }
                   leaf bandwidth {
                     type int32;
                   }
                   leaf class-type {
                     type int32;
                   }
                   leaf class-bandwidth {
                     type int32;
                   }
                 }
                 container vpls-rsvp-te-p2mp-lsp-information {
                   description "Information about one or more VPLS RSVP-TE point-to-multipoint LSPs";
                   leaf vpls-ingress-p2mp-branch-lsp-name {
                     type string;
                     description "Name of ingress point-to-multipoint branch LSP";
                   }
                   leaf vpls-ingress-p2mp-branch-lsp-state {
                     type string;
                     description "State of ingress point-to-multipoint branch LSP";
                   }
                   leaf vpls-egress-p2mp-branch-lsp-name {
                     type string;
                     description "Name of egress point-to-multipoint branch LSP";
                   }
                   leaf vpls-egress-p2mp-branch-lsp-state {
                     type string;
                     description "State of egress point-to-multipoint branch LSP";
                   }
                 }
                 container history {
                   leaf history.category-heading {
                     type string;
                   }
                   leaf history.heading {
                     type string;
                   }
                   leaf log-time-stamp {
                     type string;
                   }
                   leaf log-event {
                     type string;
                   }
                   leaf changed-entity {
                     type string;
                   }
                 }
               }
               container mesh-group-connection {
                 description "Information about all vc-connections of a specific mesh-group";
                 leaf mesh-group-name {
                   type string;
                   description "Name of mesh-group";
                 }
                 container connection {
                   leaf connection.heading {
                     type string;
                   }
                   leaf connection-id {
                     type string;
                   }
                   leaf connection-type {
                     type string;
                   }
                   leaf connection-status {
                     type string;
                   }
                   leaf last-change {
                     type string;
                   }
                   leaf up-transitions {
                     type int32;
                   }
                   leaf remote-pe {
                     type operation_type:ipaddr;
                   }
                   leaf control-word {
                     type string;
                   }
                   leaf control-word-type {
                     type string;
                   }
                   leaf interface-encapsulation {
                     type string;
                   }
                   leaf inbound-label {
                     type string;
                   }
                   leaf outbound-label {
                     type string;
                   }
                   leaf pw-status-tlv {
                     type string;
                   }
                   leaf local-pw-status-code {
                     type int32;
                   }
                   leaf remote-pw-status-code {
                     type int32;
                   }
                   leaf connection-protection {
                     type string;
                   }
                   leaf vc-flow-label-transmit {
                     type string;
                   }
                   leaf vc-flow-label-receive {
                     type string;
                   }
                   container local-interface {
                     leaf interface-name {
                       type string;
                       description "Name of interface";
                     }
                     leaf interface-status {
                       type string;
                     }
                     leaf working-status {
                       type string;
                     }
                     leaf profile-name {
                       type string;
                     }
                     leaf profile-varset-name {
                       type string;
                     }
                     leaf interface-description {
                       type string;
                     }
                   }
                   container remote-interface {
                     leaf interface-name {
                       type string;
                       description "Name of interface";
                     }
                     leaf interface-status {
                       type string;
                     }
                     leaf interface-encapsulation {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
             }
             container vpls-protocol-state {
               leaf vpls-signaling-protocol-identifier {
                 type string;
               }
               leaf num-local-interfaces {
                 type int32;
               }
               leaf num-local-interfaces-up {
                 type int32;
               }
               leaf irb-present {
                 type string;
               }
               leaf mesh-group-count {
                 type int32;
               }
               leaf mesh-group-up-count {
                 type int32;
               }
               container mesh-group-interfaces {
                 description "Information about all interfaces associated with a mesh-group";
                 container interface {
                   leaf interface-flags {
                     type int32;
                   }
                 }
               }
               container interface {
                 leaf interface-flags {
                   type int32;
                 }
               }
               container mesh-group-connection {
                 description "Information about all vc-connections of a specific mesh-group";
                 leaf mesh-group-name {
                   type string;
                   description "Name of mesh-group";
                 }
                 container connection {
                   leaf connection.heading {
                     type string;
                   }
                   leaf remote-pe {
                     type operation_type:ipaddr;
                   }
                   leaf l2vpn-local-site-id {
                     type int32;
                     description "Local site identifier";
                   }
                   leaf l2vpn-remote-site-id {
                     type int32;
                     description "Remote site identifier";
                   }
                   leaf connection-status {
                     type string;
                   }
                   leaf last-change {
                     type string;
                   }
                   leaf inbound-label {
                     type string;
                   }
                   leaf outbound-label {
                     type string;
                   }
                   container local-interface {
                     leaf interface-name {
                       type string;
                       description "Name of interface";
                     }
                     leaf interface-status {
                       type string;
                     }
                     leaf interface-encapsulation {
                       type string;
                     }
                     leaf working-status {
                       type string;
                     }
                     leaf profile-name {
                       type string;
                     }
                     leaf profile-varset-name {
                       type string;
                     }
                     leaf interface-description {
                       type string;
                     }
                   }
                   container connection-bandwidth {
                     description "Bandwidth of a layer 2 connection";
                     leaf connection-bandwidth.heading {
                       type string;
                       description "Bandwidth of a layer 2 connection";
                     }
                     leaf bandwidth {
                       type int32;
                     }
                     leaf class-type {
                       type int32;
                     }
                     leaf class-bandwidth {
                       type int32;
                     }
                   }
                   container vpls-rsvp-te-p2mp-lsp-information {
                     description "Information about one or more VPLS RSVP-TE point-to-multipoint LSPs";
                     leaf vpls-ingress-p2mp-branch-lsp-name {
                       type string;
                       description "Name of ingress point-to-multipoint branch LSP";
                     }
                     leaf vpls-ingress-p2mp-branch-lsp-state {
                       type string;
                       description "State of ingress point-to-multipoint branch LSP";
                     }
                     leaf vpls-egress-p2mp-branch-lsp-name {
                       type string;
                       description "Name of egress point-to-multipoint branch LSP";
                     }
                     leaf vpls-egress-p2mp-branch-lsp-state {
                       type string;
                       description "State of egress point-to-multipoint branch LSP";
                     }
                   }
                   container history {
                     leaf history.category-heading {
                       type string;
                     }
                     leaf history.heading {
                       type string;
                     }
                     leaf log-time-stamp {
                       type string;
                     }
                     leaf log-event {
                       type string;
                     }
                     leaf changed-entity {
                       type string;
                     }
                   }
                 }
               }
            // FRINX change reference site from container to list  (There is multiple reference site in output)
            list reference-site {
                 leaf automatic-site-name {
                   type string;
                   description "VPLS automatic site name";
                 }
                 leaf automatic-site-id-status {
                   type string;
                   description "VPLS automatic site identifier status";
                 }
                 leaf automatic-site-claim-id {
                   type int32;
                   description "Claim site identifier";
                 }
                 leaf automatic-site-collisions {
                   type int32;
                   description "Number of collisions";
                 }
                 leaf automatic-site-timer-status {
                   type string;
                   description "VPLS automatic site timer status";
                 }
                 leaf vpls-signaling-protocol-identifier {
                   type string;
                 }
                 leaf local-site-id {
                   type string;
                 }
                 leaf source-attachment-id {
                   type string;
                   description "Local source attachment identifier";
                 }
                 leaf vpls-id {
                   type int32;
                   description "VPLS instance identifier";
                 }
                 leaf l2vpn-id {
                   type string;
                 }
                 leaf local-id {
                   type operation_type:ipaddr;
                 }
                 leaf num-local-interfaces {
                   type int32;
                 }
                 leaf num-local-interfaces-up {
                   type int32;
                 }
                 leaf irb-present {
                   type string;
                 }
                 leaf mesh-group-count {
                   type int32;
                 }
                 leaf mesh-group-up-count {
                   type int32;
                 }
                 leaf remote-site-id {
                   type string;
                 }
                 leaf target-attachment-id {
                   type string;
                   description "Remote target attachment identifier";
                 }
                 container mesh-group-interfaces {
                   description "Information about all interfaces associated with a mesh-group";
                   leaf mesh-group-name {
                     type string;
                     description "Name of mesh-group";
                   }
                   leaf mesh-group-state {
                     type string;
                     description "Mesh-group state";
                   }
                   leaf mesh-group-id {
                     type int32;
                     description "Mesh-group Identifier";
                   }
                   container interface {
                     leaf interface-name {
                       type string;
                       description "Name of interface";
                     }
                     leaf interface-description {
                       type string;
                     }
                     leaf interface-flags-description {
                       type string;
                     }
                     leaf interface-flags {
                       type int32;
                     }
                   }
                 }
                 container interface {
                   leaf interface-name {
                     type string;
                     description "Name of interface";
                   }
                   leaf interface-id {
                     type int32;
                   }
                   leaf interface-description {
                     type string;
                   }
                   leaf interface-flags-description {
                     type string;
                   }
                   leaf interface-flags {
                     type int32;
                   }
                 }
                 container connection {
                 }
                 container mesh-group-connection {
                   description "Information about all vc-connections of a specific mesh-group";
                   container connection {
                   }
                 }
               }
             }
             container vpls-rsvp-te-ingress-p2mp-lsp {
               leaf vpls-ingress-p2mp-lsp-name {
                 type string;
                 description "Name of ingress point-to-multipoint LSP";
               }
               leaf vpls-rsvp-te-p2mp-flood-nexthop-id {
                 type int32;
                 description "Identifier for VPLS RSVP traffic-engineering ingress flood next hop";
               }
             }
             container multihome {
               leaf multihome.heading {
                 type string;
               }
               container multihome-site {
                 leaf multihome-site-name {
                   type string;
                   description "Name of site";
                 }
                 leaf multihome-site-id {
                   type int32;
                   description "Site Identifier";
                 }
                 leaf multihome-site-preference {
                   type int32;
                   description "Site Preference";
                 }
                 leaf multihome-site-state {
                   type string;
                   description "Site state";
                 }
                 leaf multihome-num-interfaces {
                   type int32;
                 }
                 leaf multihome-num-interfaces-up {
                   type int32;
                 }
                 container interface {
                   leaf interface-name {
                     type string;
                     description "Name of interface";
                   }
                   leaf interface-id {
                     type int32;
                   }
                   leaf interface-description {
                     type string;
                   }
                   leaf interface-flags-description {
                     type string;
                   }
                   leaf interface-flags {
                     type int32;
                   }
                 }
                 container remote-advertisements {
                   leaf remote-advertisements.heading {
                     type string;
                   }
                   container remote-adv {
                     leaf remote-adv-addr {
                       type string;
                     }
                     leaf remote-adv-preference {
                       type int32;
                       description "Remote PE preference";
                     }
                     leaf remote-adv-ctrl-flag {
                       type int32;
                       description "Remote PE Control flags";
                     }
                     leaf remote-adv-ctrl-flag-description {
                       type string;
                       description "Control flags description";
                     }
                   }
                 }
               }
             }
             container history {
               leaf history.category-heading {
                 type string;
               }
               leaf history.heading {
                 type string;
               }
               leaf log-time-stamp {
                 type string;
               }
               leaf log-event {
                 type string;
               }
               leaf changed-entity {
                 type string;
               }
             }
           // FRINX comment out container normal}
           container summary {
             leaf instance-name {
               type string;
             }
             leaf instance-display-error {
               type string;
             }
             leaf edge-protection {
               type string;
             }
             leaf edge-protector {
               type string;
             }
            // FRINX change reference site from container to list  (There is multiple reference site in output)
            list reference-site {
               leaf automatic-site-name {
                 type string;
                 description "VPLS automatic site name";
               }
               leaf automatic-site-id-status {
                 type string;
                 description "VPLS automatic site identifier status";
               }
               leaf automatic-site-claim-id {
                 type int32;
                 description "Claim site identifier";
               }
               leaf automatic-site-collisions {
                 type int32;
                 description "Number of collisions";
               }
               leaf automatic-site-timer-status {
                 type string;
                 description "VPLS automatic site timer status";
               }
               leaf vpls-signaling-protocol-identifier {
                 type string;
               }
               leaf local-site-id {
                 type string;
               }
               leaf source-attachment-id {
                 type string;
                 description "Local source attachment identifier";
               }
               leaf vpls-id {
                 type int32;
                 description "VPLS instance identifier";
               }
               leaf l2vpn-id {
                 type string;
               }
               leaf local-id {
                 type operation_type:ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               leaf target-attachment-id {
                 type string;
                 description "Remote target attachment identifier";
               }
               container mesh-group-interfaces {
                 description "Information about all interfaces associated with a mesh-group";
                 container interface {
                   leaf interface-flags {
                     type int32;
                   }
                 }
               }
               container interface {
                 leaf interface-flags {
                   type int32;
                 }
               }
               container connection {
               }
               container mesh-group-connection {
                 description "Information about all vc-connections of a specific mesh-group";
                 container connection {
                 }
               }
               container connections-summary {
                 leaf vc-up-count {
                   type int32;
                 }
                 leaf vc-down-count {
                   type int32;
                 }
               }
             }
             container ldp-vpls-reference-site {
               description "Information about LDP-VPLS";
               leaf vpls-signaling-protocol-identifier {
                 type string;
               }
               leaf local-site-id {
                 type string;
               }
               leaf vpls-id {
                 type int32;
                 description "VPLS instance identifier";
               }
               leaf l2vpn-id {
                 type string;
               }
               leaf local-id {
                 type operation_type:ipaddr;
               }
               leaf num-local-interfaces {
                 type int32;
               }
               leaf num-local-interfaces-up {
                 type int32;
               }
               leaf irb-present {
                 type string;
               }
               leaf mesh-group-count {
                 type int32;
               }
               leaf mesh-group-up-count {
                 type int32;
               }
               leaf remote-site-id {
                 type string;
               }
               container mesh-group-interfaces {
                 description "Information about all interfaces associated with a mesh-group";
                 container interface {
                   leaf interface-flags {
                     type int32;
                   }
                 }
               }
               container interface {
                 leaf interface-flags {
                   type int32;
                 }
               }
               container connection {
               }
               container mesh-group-connection {
                 description "Information about all vc-connections of a specific mesh-group";
                 container connection {
                 }
               }
               container connections-summary {
                 leaf vc-up-count {
                   type int32;
                 }
                 leaf vc-down-count {
                   type int32;
                 }
               }
             }
             container vpls-protocol-state {
               leaf vpls-signaling-protocol-identifier {
                 type string;
               }
               leaf num-local-interfaces {
                 type int32;
               }
               leaf num-local-interfaces-up {
                 type int32;
               }
               leaf irb-present {
                 type string;
               }
               leaf mesh-group-count {
                 type int32;
               }
               leaf mesh-group-up-count {
                 type int32;
               }
               container mesh-group-interfaces {
                 description "Information about all interfaces associated with a mesh-group";
                 container interface {
                   leaf interface-flags {
                     type int32;
                   }
                 }
               }
               container interface {
                 leaf interface-flags {
                   type int32;
                 }
               }
               container mesh-group-connection {
                 description "Information about all vc-connections of a specific mesh-group";
                 leaf mesh-group-name {
                   type string;
                   description "Name of mesh-group";
                 }
                 container connection {
                 }
                 container connections-summary {
                   leaf vc-up-count {
                     type int32;
                   }
                   leaf vc-down-count {
                     type int32;
                   }
                 }
               }
            // FRINX change reference site from container to list  (There is multiple reference site in output)
            list reference-site {
                 container mesh-group-interfaces {
                   description "Information about all interfaces associated with a mesh-group";
                   container interface {
                     leaf interface-flags {
                       type int32;
                     }
                   }
                 }
                 container interface {
                   leaf interface-flags {
                     type int32;
                   }
                 }
                 container connection {
                 }
                 container mesh-group-connection {
                   description "Information about all vc-connections of a specific mesh-group";
                   container connection {
                   }
                 }
               }
             }
             container multihome {
               container multihome-site {
                 container interface {
                   leaf interface-flags {
                     type int32;
                   }
                 }
                 container remote-advertisements {
                 }
               }
             }
           }
         }
         container interface-statistics {
           leaf remote-pe {
             type operation_type:ipaddr;
           }
           leaf broadcast-packets {
             type uint64;
             description "Broadcast packets";
           }
           leaf broadcast-bytes {
             type uint64;
             description "Broadcast bytes";
           }
           leaf multicast-packets {
             type uint64;
             description "Multicast packets";
           }
           leaf multicast-bytes {
             type uint64;
             description "Multicast bytes";
           }
           leaf flooded-packets {
             type uint64;
             description "Flooded packets";
           }
           leaf flooded-bytes {
             type uint64;
             description "Flooded bytes";
           }
           leaf unicast-packets {
             type uint64;
             description "Unicast packets";
           }
           leaf unicast-bytes {
             type uint64;
             description "Unicast bytes";
           }
           leaf num-mac-count {
             type int32;
             description "Number of addresses learned on the interface";
           }
           leaf mac-limit {
             type int32;
             description "Limit of number of addresses learned on interface";
           }
           container interface {
             leaf interface-name {
               type string;
               description "Name of interface";
             }
             leaf local-interface-index {
               type int32;
               description "SNMP ifIndex of local interface";
             }
             leaf interface-flags {
               type int32;
             }
           }
         }
       }
     }
   }
   rpc get-vpls-mac-table {
     description "Show media access control table";
     input {
       leaf instance {
         description "Display information for a specified vpls";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Display MAC address learned on a specified VLAN";
         type string;
       }
       leaf isid {
         description "Display Information for specified ISID or all ISID(s)";
         type string;
       }
       leaf address {
         description "MAC address";
         default "all";
         type operation_type:mac-addr;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       container l2ald-rtb-macdb {
         leaf l2ald-macdb-rtb-name {
           type string;
           description "Bridging MAC database for a routing instance";
         }
         container l2ald-mac-entry {
// FRINX COMMENT OUT BRIEF begin            container brief {
             leaf l2-mac-address {
               type operation_type:mac-addr;
               description "Media access control address learned from another source";
             }
             leaf l2-mac-logical-interface {
               type string;
               description "Name of logical interface on which MAC address was learned";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
// FRINX COMMENT OUT BRIEF end            }
           container brief-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pvlan {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pbn-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-beb-mac-address {
               type operation_type:mac-addr;
               description "Media access control address of remote backbone edge bridge (BEB)";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container extensive {
             leaf l2-mac-address {
               type operation_type:mac-addr;
               description "Media access control address learned from another source";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-logical-interface {
               type string;
               description "Name of logical interface on which MAC address was learned";
             }
             leaf l2-mac-base-logical-interface {
               type string;
               description "Name of logical interface on which MAC address was learnt first";
             }
             leaf l2-remote-beb-mac-address {
               type operation_type:mac-addr;
               description "Media access control address of remote backbone edge bridge (BEB)";
             }
             leaf l2-mac-entry-flags {
               type string;
               description "Forwarding entry flags associated with these MAC addresses";
             }
             leaf l2-mac-epoch {
               type uint32;
               description "Spanning Tree Protocol (STP) epoch number when MAC address was learned";
             }
             leaf l2-mac-sequence-number {
               type uint32;
               description "Sequence number assigned to this MAC address";
             }
             leaf l2-mac-learn-mask {
               type string;
               description "Mask of Packet Forwarding Engines where this MAC address was learned";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
             container l2ald-mac-source-address-statistics {
               description "MAC source address statistics";
               leaf packet-count {
                 type uint64;
                 description "Packet count";
               }
               leaf byte-count {
                 type uint64;
                 description "Byte count";
               }
             }
             container l2ald-mac-destination-address-statistics {
               description "MAC destination address statistics";
               leaf packet-count {
                 type uint64;
                 description "Packet count";
               }
               leaf byte-count {
                 type uint64;
                 description "Byte count";
               }
             }
           }
           container brief-rvtep {
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-vtep-address {
               type string;
               description "Remote VXLAN tunnel endpoint ip address";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-vxlan-evpn {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-active-source {
               type string;
               description "Remote VXLAN tunnel endpoint ip address or ESI value";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
         }
       }
     }
   }
   rpc get-vpls-interface-mac-table {
     description "Display MAC table for a specified interface";
     input {
       container interface-choice {
         choice interface-choice_c {
           case interface-name {
             leaf interface-name {
               description "Name of interface for which to display table";
               type string;
             }
           }
           case all {
             leaf all {
               description "Display MAC table for all the interfaces";
               type empty;
             }
           }
         }
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       container l2ald-interface-macdb {
         leaf l2ald-macdb-if-name {
           type string;
         }
         container l2ald-mac-entry {
// FRINX COMMENT OUT BRIEF begin            container brief {
             leaf l2-mac-address {
               type operation_type:mac-addr;
               description "Media access control address learned from another source";
             }
             leaf l2-mac-logical-interface {
               type string;
               description "Name of logical interface on which MAC address was learned";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
// FRINX COMMENT OUT BRIEF end            }
           container brief-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pvlan {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-mac-fwd-next-hop {
               type uint32;
               description "Forwarding next hop for Control MAC to be routed to";
             }
             leaf l2-mac-property {
               type string;
               description "Property of MAC route";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-pbn-rtb {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-beb-mac-address {
               type operation_type:mac-addr;
               description "Media access control address of remote backbone edge bridge (BEB)";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container extensive {
             leaf l2-mac-address {
               type operation_type:mac-addr;
               description "Media access control address learned from another source";
             }
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-isid {
               type uint32;
               description "ISID for the bridging domain";
             }
             leaf l2-bridge-vlan {
               type string;
               description "Vlan for the bridging domain";
             }
             leaf l2-mac-logical-interface {
               type string;
               description "Name of logical interface on which MAC address was learned";
             }
             leaf l2-mac-base-logical-interface {
               type string;
               description "Name of logical interface on which MAC address was learnt first";
             }
             leaf l2-remote-beb-mac-address {
               type operation_type:mac-addr;
               description "Media access control address of remote backbone edge bridge (BEB)";
             }
             leaf l2-mac-entry-flags {
               type string;
               description "Forwarding entry flags associated with these MAC addresses";
             }
             leaf l2-mac-epoch {
               type uint32;
               description "Spanning Tree Protocol (STP) epoch number when MAC address was learned";
             }
             leaf l2-mac-sequence-number {
               type uint32;
               description "Sequence number assigned to this MAC address";
             }
             leaf l2-mac-learn-mask {
               type string;
               description "Mask of Packet Forwarding Engines where this MAC address was learned";
             }
             leaf l2-mac-pvlan-port-role {
               type string;
               description "The PVLAN port role for interface associated with these MAC addresses";
             }
             leaf l2-mac-pvlan-vlan-id {
               type string;
               description "The PVLAN vlan ID associated with these MAC addresses";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
             container l2ald-mac-source-address-statistics {
               description "MAC source address statistics";
               leaf packet-count {
                 type uint64;
                 description "Packet count";
               }
               leaf byte-count {
                 type uint64;
                 description "Byte count";
               }
             }
             container l2ald-mac-destination-address-statistics {
               description "MAC destination address statistics";
               leaf packet-count {
                 type uint64;
                 description "Packet count";
               }
               leaf byte-count {
                 type uint64;
                 description "Byte count";
               }
             }
           }
           container brief-rvtep {
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-remote-vtep-address {
               type string;
               description "Remote VXLAN tunnel endpoint ip address";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
           container brief-vxlan-evpn {
             leaf l2-mac-logical-system {
               type string;
               description "Name of logical system in which this MAC address was learned";
             }
             leaf l2-mac-routing-instance {
               type string;
               description "Routing instance in which the MAC address was learned";
             }
             leaf l2-mac-bridging-domain {
               type string;
               description "Bridging domain in which the MAC address was learned";
             }
             leaf l2-bridge-vlan {
               type string;
               description "Vlan for the bridging domain";
             }
             leaf l2-mac-address {
               type operation_type:mac-addr;
               description "Media access control address learned from another source";
             }
             leaf l2-mac-flags {
               type string;
               description "Forwarding entry flags associated with MACs displayed in short form";
             }
             leaf l2-mac-logical-interface {
               type string;
               description "Name of logical interface on which MAC address was learned";
             }
             leaf l2-active-source {
               type string;
               description "Remote VXLAN tunnel endpoint ip address or ESI value";
             }
             leaf l2-mac-interface-device {
               type string;
               description "Name of interface device on which MAC address was learned";
             }
             leaf l2-mac-rtr-id {
               type uint32;
               description "Remote Rourter ID for Control MAC to be routed to";
             }
             leaf l2-mac-vlan {
               type uint32;
               description "VLAN ID of the routing instance in which the MAC address was learned";
             }
             leaf l2-mac-stp-index {
               type uint32;
               description "Spanning Tree Protocol (STP) index of the logical interface in which the MAC address was learned";
             }
             leaf l2-mac-ifl-generation {
               type uint32;
               description "Creation time of the logical interface when this MAC address was learned";
             }
             leaf l2-mac-entry-age {
               type string;
               description "Age of the mac entry";
             }
           }
         }
       }
     }
   }
   rpc get-vpls-flood-information {
     description "Show VPLS flooding information";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf verbosity {
         default "detail";
         type enumeration {
           enum "detail" {
             description "Display detailed output";
           }
           enum "brief" {
             description "Display brief output";
           }
           enum "extensive" {
             description "Display extensive output";
           }
         }
       }
     }
     output {
       container l2ald-vpls-flood-instance {
         container l2ald-vpls-lr-information {
           container logical-system-info {
             leaf logical-system-name {
               type string;
               description "Logical System";
             }
           }
           container l2ald-vpls-flood-instance-information {
// FRINX COMMENT OUT BRIEF begin              container brief {
               leaf instance-name {
                 type string;
               }
               leaf num-active-ce-iffs {
                 type int32;
               }
               leaf num-active-ve-iffs {
                 type int32;
               }
               leaf bridging-domain {
                 type string;
               }
               container flood-route {
                 container detail {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container extensive {
                   leaf route-prefix {
                     type string;
                   }
                   leaf route-type {
                     type string;
                   }
                   leaf owner {
                     type string;
                   }
                   leaf route-flood-group-name {
                     type string;
                   }
                   leaf route-flood-group-index {
                     type int32;
                   }
                   leaf nhtype {
                     type string;
                   }
                   leaf nhindex {
                     type int32;
                   }
                   leaf make-before-break {
                     type string;
                   }
                   leaf make-before-break-state {
                     type string;
                   }
                   container flood-nh-evpn-core-components {
                     leaf component-nhindex {
                       type int32;
                     }
                     leaf peer {
                       type string;
                     }
                     leaf nh-type {
                       type string;
                     }
                     leaf interface-esi {
                       type string;
                       description "ESI";
                     }
                   }
                   container flood-nh-p2mp-components {
                     leaf component-nhindex {
                       type int32;
                     }
                   }
                   container flood-nh-components {
                     leaf interface-name {
                       type string;
                       description "Bridging media access control address interface";
                     }
                     leaf interface-type {
                       type string;
                     }
                     leaf nhtype {
                       type string;
                     }
                     leaf nhindex {
                       type int32;
                     }
                     leaf interface-esi {
                       type string;
                       description "ESI";
                     }
                     container group {
                     }
                   }
                   container flood-nh-group {
                     leaf flood-nh-group-name {
                       type string;
                     }
                     leaf flood-nh-group-type {
                       type string;
                     }
                     leaf nhtype {
                       type string;
                     }
                     leaf nhindex {
                       type int32;
                     }
                     container extensive {
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
               }
// FRINX COMMENT OUT BRIEF end              }
             container detail {
               leaf instance-name {
                 type string;
               }
               leaf num-active-ce-iffs {
                 type int32;
               }
               leaf num-active-ve-iffs {
                 type int32;
               }
               leaf bridge-domain-name {
                 type string;
                 description "Name of the bridging domain";
               }
               leaf bridge-domain-evpn-extension {
                 type string;
                 description "EVPN extension for the BD";
               }
               leaf bridging-domain {
                 type string;
               }
               container flood-route {
                 leaf route-prefix {
                   type string;
                 }
                 leaf route-type {
                   type string;
                 }
                 leaf owner {
                   type string;
                 }
                 leaf nhtype {
                   type string;
                 }
                 leaf nhindex {
                   type int32;
                 }
// FRINX COMMENT OUT BRIEF begin                  container brief {
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
// FRINX COMMENT OUT BRIEF end                  }
                 container detail {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container extensive {
                   leaf route-prefix {
                     type string;
                   }
                   leaf route-type {
                     type string;
                   }
                   leaf owner {
                     type string;
                   }
                   leaf route-flood-group-name {
                     type string;
                   }
                   leaf route-flood-group-index {
                     type int32;
                   }
                   leaf nhtype {
                     type string;
                   }
                   leaf nhindex {
                     type int32;
                   }
                   leaf make-before-break {
                     type string;
                   }
                   leaf make-before-break-state {
                     type string;
                   }
                   container flood-nh-evpn-core-components {
                     leaf component-nhindex {
                       type int32;
                     }
                     leaf peer {
                       type string;
                     }
                     leaf nh-type {
                       type string;
                     }
                     leaf interface-esi {
                       type string;
                       description "ESI";
                     }
                   }
                   container flood-nh-p2mp-components {
                     leaf component-nhindex {
                       type int32;
                     }
                   }
                   container flood-nh-components {
                     leaf interface-name {
                       type string;
                       description "Bridging media access control address interface";
                     }
                     leaf interface-type {
                       type string;
                     }
                     leaf nhtype {
                       type string;
                     }
                     leaf nhindex {
                       type int32;
                     }
                     leaf interface-esi {
                       type string;
                       description "ESI";
                     }
                     container group {
                     }
                   }
                   container flood-nh-group {
                     leaf flood-nh-group-name {
                       type string;
                     }
                     leaf flood-nh-group-type {
                       type string;
                     }
                     leaf nhtype {
                       type string;
                     }
                     leaf nhindex {
                       type int32;
                     }
                     container extensive {
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
               }
             }
             container extensive {
               leaf instance-name {
                 type string;
               }
               leaf num-active-ce-iffs {
                 type int32;
               }
               leaf num-active-ve-iffs {
                 type int32;
               }
               leaf bridge-domain-name {
                 type string;
                 description "Name of the bridging domain";
               }
               leaf bridge-domain-evpn-extension {
                 type string;
                 description "EVPN extension for the BD";
               }
               leaf bridging-domain {
                 type string;
               }
               container flood-route {
// FRINX COMMENT OUT BRIEF begin                  container brief {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
// FRINX COMMENT OUT BRIEF end                  }
                 container detail {
                   leaf route-prefix {
                     type string;
                   }
                   leaf route-type {
                     type string;
                   }
                   leaf owner {
                     type string;
                   }
                   leaf nhtype {
                     type string;
                   }
                   leaf nhindex {
                     type int32;
                   }
                   container flood-nh-components {
                     container group {
                       leaf interface-name {
                         type string;
                         description "Bridging media access control address interface";
                       }
                       leaf interface-type {
                         type string;
                       }
                       leaf interface-esi {
                         type string;
                         description "ESI";
                       }
                     }
                   }
                   container flood-nh-group {
                     container extensive {
                       leaf flood-nh-group-name {
                         type string;
                       }
                       leaf flood-nh-group-type {
                         type string;
                       }
                       leaf nhtype {
                         type string;
                       }
                       leaf nhindex {
                         type int32;
                       }
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
                 container extensive {
                   leaf route-prefix {
                     type string;
                   }
                   leaf route-type {
                     type string;
                   }
                   leaf owner {
                     type string;
                   }
                   leaf route-flood-group-name {
                     type string;
                   }
                   leaf route-flood-group-index {
                     type int32;
                   }
                   leaf nhtype {
                     type string;
                   }
                   leaf nhindex {
                     type int32;
                   }
                   leaf make-before-break {
                     type string;
                   }
                   leaf make-before-break-state {
                     type string;
                   }
                   container flood-nh-evpn-core-components {
                     leaf component-nhindex {
                       type int32;
                     }
                     leaf peer {
                       type string;
                     }
                     leaf nh-type {
                       type string;
                     }
                     leaf interface-esi {
                       type string;
                       description "ESI";
                     }
                   }
                   container flood-nh-p2mp-components {
                     leaf component-nhindex {
                       type int32;
                     }
                   }
                   container flood-nh-components {
                     leaf interface-name {
                       type string;
                       description "Bridging media access control address interface";
                     }
                     leaf interface-type {
                       type string;
                     }
                     leaf nhtype {
                       type string;
                     }
                     leaf nhindex {
                       type int32;
                     }
                     leaf interface-esi {
                       type string;
                       description "ESI";
                     }
                     container group {
                     }
                   }
                   container flood-nh-group {
                     leaf flood-nh-group-name {
                       type string;
                     }
                     leaf flood-nh-group-type {
                       type string;
                     }
                     leaf nhtype {
                       type string;
                     }
                     leaf nhindex {
                       type int32;
                     }
                     container extensive {
                       container flood-nh-components {
                         leaf interface-name {
                           type string;
                           description "Bridging media access control address interface";
                         }
                         leaf interface-type {
                           type string;
                         }
                         leaf interface-esi {
                           type string;
                           description "ESI";
                         }
                         container group {
                         }
                       }
                       container flood-nh-p2mp-components {
                         leaf component-nhindex {
                           type int32;
                         }
                       }
                       container flood-nh-evpn-core-components {
                         leaf component-nhindex {
                           type int32;
                         }
                         leaf peer {
                           type string;
                         }
                         leaf nh-type {
                           type string;
                         }
                         leaf interface-esi {
                           type string;
                           description "ESI";
                         }
                       }
                     }
                   }
                 }
               }
             }
           }
         }
       }
     }
   }
   rpc get-vpls-ce-flood-route-information {
     description "Show customer edge flood route";
     input {
       leaf interface {
         description "Interface for which to show CE flood route";
         type operation_type:interface-unit;
         mandatory true;
       }
     }
     output {
       container l2ald-vpls-flood-route-information {
         container flood-route {
// FRINX COMMENT OUT BRIEF begin            container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
// FRINX COMMENT OUT BRIEF end            }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-vpls-all-flood-route-information {
     description "Show route for flooding traffic from CE router";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         container flood-route {
// FRINX COMMENT OUT BRIEF begin            container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
// FRINX COMMENT OUT BRIEF end            }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-vpls-all-ce-flood-route-information {
     description "Show route for flooding traffic to all CE routers";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         container flood-route {
// FRINX COMMENT OUT BRIEF begin            container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
// FRINX COMMENT OUT BRIEF end            }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-vpls-re-flood-route-information {
     description "Show route for routing engine flooding to all interfaces";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         container flood-route {
// FRINX COMMENT OUT BRIEF begin            container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
// FRINX COMMENT OUT BRIEF end            }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-vpls-mlp-flood-route-information {
     description "Show route for flooding traffic to MAC learning chips";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         container flood-route {
// FRINX COMMENT OUT BRIEF begin            container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
// FRINX COMMENT OUT BRIEF end            }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-vpls-alt-root-flood-route-information {
     description "Show STP alt-root flooding route used for interface";
     input {
       leaf interface {
         description "Interface for which to show alternate-root flooding route";
         type operation_type:interface-unit;
         mandatory true;
       }
     }
     output {
       container l2ald-vpls-flood-route-information {
         container flood-route {
// FRINX COMMENT OUT BRIEF begin            container brief {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
// FRINX COMMENT OUT BRIEF end            }
           container detail {
             leaf route-prefix {
               type string;
             }
             leaf route-type {
               type string;
             }
             leaf owner {
               type string;
             }
             leaf nhtype {
               type string;
             }
             leaf nhindex {
               type int32;
             }
             container flood-nh-components {
               container group {
                 leaf interface-name {
                   type string;
                   description "Bridging media access control address interface";
                 }
                 leaf interface-type {
                   type string;
                 }
                 leaf interface-esi {
                   type string;
                   description "ESI";
                 }
               }
             }
             container flood-nh-group {
               container extensive {
                 leaf flood-nh-group-name {
                   type string;
                 }
                 leaf flood-nh-group-type {
                   type string;
                 }
                 leaf nhtype {
                   type string;
                 }
                 leaf nhindex {
                   type int32;
                 }
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
           container extensive {
             leaf route-prefix {
               type string;
             }
             leaf route-type {
               type string;
             }
             leaf owner {
               type string;
             }
             leaf route-flood-group-name {
               type string;
             }
             leaf route-flood-group-index {
               type int32;
             }
             leaf nhtype {
               type string;
             }
             leaf nhindex {
               type int32;
             }
             leaf make-before-break {
               type string;
             }
             leaf make-before-break-state {
               type string;
             }
             container flood-nh-evpn-core-components {
               leaf component-nhindex {
                 type int32;
               }
               leaf peer {
                 type string;
               }
               leaf nh-type {
                 type string;
               }
               leaf interface-esi {
                 type string;
                 description "ESI";
               }
             }
             container flood-nh-p2mp-components {
               leaf component-nhindex {
                 type int32;
               }
             }
             container flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               container group {
               }
             }
             container flood-nh-group {
               leaf flood-nh-group-name {
                 type string;
               }
               leaf flood-nh-group-type {
                 type string;
               }
               leaf nhtype {
                 type string;
               }
               leaf nhindex {
                 type int32;
               }
               container extensive {
                 container flood-nh-components {
                   leaf interface-name {
                     type string;
                     description "Bridging media access control address interface";
                   }
                   leaf interface-type {
                     type string;
                   }
                   leaf interface-esi {
                     type string;
                     description "ESI";
                   }
                   container group {
                   }
                 }
                 container flood-nh-p2mp-components {
                   leaf component-nhindex {
                     type int32;
                   }
                 }
                 container flood-nh-evpn-core-components {
                   leaf component-nhindex {
                     type int32;
                   }
                   leaf peer {
                     type string;
                   }
                   leaf nh-type {
                     type string;
                   }
                   leaf interface-esi {
                     type string;
                     description "ESI";
                   }
                 }
               }
             }
           }
         }
       }
     }
   }
   rpc get-vpls-event-queue-information {
     description "Show queue of pending VPLS flood events";
     output {
       container l2ald-vpls-flood-event-queue {
         container l2ald-vpls-flood-next-event {
           container l2ald-vpls-flood-event-info {
             leaf event-name {
               type string;
             }
             leaf event-owner {
               type string;
             }
             leaf event-type {
               type string;
             }
             leaf event-op {
               type string;
             }
             leaf event-error {
               type string;
             }
             container detail {
             }
// FRINX COMMENT OUT BRIEF begin              container brief { and delete brief leafs

// FRINX COMMENT OUT BRIEF end              }
           }
         }
         container l2ald-vpls-flood-event-list {
           container l2ald-vpls-flood-event-info {
             leaf event-name {
               type string;
             }
             leaf event-type {
               type string;
             }
             leaf event-op {
               type string;
             }
             leaf event-owner {
               type string;
             }
             container detail {
               leaf event-error {
                 type string;
               }
             }
// FRINX COMMENT OUT BRIEF begin              container brief { and delete brief leafs
               
// FRINX COMMENT OUT BRIEF end              }
           }
         }
       }
     }
   }
   rpc get-vpls-mac-move-action {
     description "Show IFLs disabled due to rapid mac moves";
     input {
       leaf instance {
         description "Display information for a specified vpls";
         default "all";
         type string;
       }
     }
     output {
       container l2ald-vpls-mac-move-action {
         leaf l2ald-vpls-mac-move-action-instance-name {
           type string;
           description "VPLS mac-move-actions for a routing instance";
         }
         container l2ald-vpls-ifl-disabled-entry {
           leaf l2ald-vpls-disabled-ifl {
             type string;
             description "This IFL is disabled by mac move";
           }
           leaf l2ald-vpls-disabled-ifl-index {
             type uint32;
             description "Layer 2 interface index";
           }
           leaf l2ald-vpls-algo-used {
             type string;
             description "Algorithm used to decide the Loop-Connected-PE";
           }
           leaf l2ald-vpls-mac-address {
             type operation_type:mac-addr;
             description "Media access control address used for base ifl algorithm";
           }
           leaf l2ald-vpls-mac-move-time-rec {
             type string;
             description "Time of the MAC move";
           }
           leaf l2ald-vpls-mac-move-is-timer {
             type string;
             description "Is reopen timer running for this IFL";
           }
         }
       }
     }
   }
 }
