/*
 * Copyright (c) 2017 Juniper Networks, Inc.
 * All rights reserved.
 */

 module ping {
  namespace "http://xml.juniper.net/junos/16.1R7/junos-probe-tests";
  prefix jrpc;

  import junos-extension {
    prefix junos;
  }

  organization
    "Juniper Networks, Inc.";

  description
    "Junos YANG module for RPC";

   typedef daemon {
     type string;
   }
   typedef filename {
     type string;
   }
   typedef client-filename {
     type string;
   }
   typedef hostname {
     type string;
   }
   typedef ipaddr {
     type string;
   }
   typedef sysid {
     type string;
   }
   typedef interface-device {
     type string;
   }
   typedef ddl-bits {
     type string;
   }
   typedef isoaddr {
     type string;
   }
   typedef ipprefix {
     type string;
   }
   typedef ipprefix-mandatory {
     type string;
   }
   typedef interface-unit {
     type string;
   }
   typedef ipaddr-or-interface {
     type string;
   }
   typedef areaid {
     type string;
   }
   typedef interface-name {
     type string;
   }
   typedef community {
     type string;
   }
   typedef interface-wildcard {
     type string;
   }
   typedef unreadable {
     type string;
   }
   typedef ipprefix-optional {
     type string;
   }
   typedef policy-algebra {
     type string;
   }
   typedef regular-expression {
     type string;
   }
   typedef group-glob {
     type string;
   }
   typedef atm-vci {
     type string;
   }
   typedef ipprefix-only {
     type string;
   }
   typedef ipv4addr {
     type string;
   }
   typedef ipv4prefix {
     type string;
   }
   typedef ipv4prefix-mandatory {
     type string;
   }
   typedef ipv4addr-or-interface {
     type string;
   }
   typedef ipv4prefix-optional {
     type string;
   }
   typedef ipv4prefix-only {
     type string;
   }
   typedef ipv6addr {
     type string;
   }
   typedef ipv6prefix {
     type string;
   }
   typedef ipv6prefix-mandatory {
     type string;
   }
   typedef ipv6addr-or-interface {
     type string;
   }
   typedef ipv6prefix-optional {
     type string;
   }
   typedef ipv6prefix-only {
     type string;
   }
   typedef interface-device-wildcard {
     type string;
   }
   typedef time {
     type string;
   }
   typedef mac-addr {
     type string;
   }
   typedef mac-addr-prefix {
     type string;
   }
   typedef mac-unicaset {
     type string;
   }
   typedef mac-unicast-prefix {
     type string;
   }
   typedef mac-multicast {
     type string;
   }
   typedef mac-multicast-prefix {
     type string;
   }
   typedef mpls-label {
     type string;
   }
   typedef unsigned-float {
     type string;
   }
   typedef isoprefix {
     type string;
   }
   typedef isosysid {
     type string;
   }
   typedef string-huge {
     type string;
   }
   typedef variable {
     type string;
   }
   typedef glob-variable {
     type string;
   }
   typedef vlan-range {
     type string;
   }
   typedef interface-range-wild {
     type string;
   }
   typedef fc-addr {
     type string;
   }
   typedef wwn {
     type string;
   }
   typedef logfilename {
     type string;
   }
   typedef range {
     type string;
   }
   typedef esi {
     type string;
   }

   rpc ping {
     description "Ping remote target";
     input {
       leaf count {
         description "Number of ping requests to send";
         units "packets";
         type uint32 {
           range "1 .. 2000000000";
         }
       }
       leaf wait {
         description "Maximum wait time after sending final packet";
         units "seconds";
         type uint32;
       }
       leaf no-resolve {
         description "Don't attempt to print addresses symbolically";
         type empty;
       }
       leaf rapid {
         description "Send requests rapidly (default count of 5)";
         type empty;
       }
       leaf record-route {
         description "Record and report packet's path (IPv4)";
         type empty;
       }
       leaf brief {
         status deprecated;
         type empty;
       }
       leaf detail {
         description "Display incoming interface of received packet";
         type empty;
       }
       leaf do-not-fragment {
         description "Don't fragment echo request packets (IPv4)";
         type empty;
       }
       leaf-list loose-source {
         description "Intermediate loose source route entry (IPv4)";
         type string;
       }
       leaf interface {
         description "Source interface (multicast, all-ones, unrouted packets)";
         type string;
       }
       leaf interval {
         description "Delay between ping requests";
         units "seconds";
         type string;
       }
       leaf source {
         description "Source address of echo request";
         type string;
       }
       leaf pattern {
         description "Hexadecimal fill pattern";
         type string;
       }
       leaf size {
         description "Size of request packets";
         units "bytes";
         type uint32 {
           range "0 .. 65468";
         }
       }
       leaf strict {
         description "Use strict source route option (IPv4)";
         type empty;
       }
       leaf-list strict-source {
         description "Intermediate strict source route entry (IPv4)";
         type string;
       }
       leaf ttl {
         description "IP time-to-live value (IPv6 hop-limit value)";
         units "hops";
         type uint32 {
           range "1 .. 255";
         }
       }
       leaf verbose {
         description "Display detailed output";
         type empty;
       }
       leaf tos {
         description "IP type-of-service value";
         type uint32 {
           range "0 .. 255";
         }
       }
       leaf bypass-routing {
         description "Bypass routing table, use specified interface";
         type empty;
       }
       leaf inet {
         description "Force ping to IPv4 destination";
         type empty;
       }
       leaf inet6 {
         description "Force ping to IPv6 destination";
         type empty;
       }
       leaf routing-instance {
         description "Routing instance for ping attempt";
         type string;
       }
       leaf mac-address {
         description "MAC address of the nexthop in xx:xx:xx:xx:xx:xx format";
         type mac-unicaset;
       }
       leaf host {
         description "Hostname or IP address of remote host";
         type string;
         mandatory true;
       }
       leaf logical-system {
         description "Name of logical system";
         type string {
           junos:posix-pattern "^[a-zA-Z0-9_-]{1,63}$";
           junos:pattern-message "Logical-system name is a string consisting of up to 63 letters, numbers, dashes and underscores";
         }
       }
     }
     // FRINX change output to anyxml
     output {
          anyxml ping-results;
     }
   }
   rpc request-ping-rsvp-lsp {
     description "Ping RSVP-signaled LSP";
     input {
       leaf lsp-name {
         description "Name of LSP";
         type string {
           length "1 .. 64";
         }
         mandatory true;
       }
       leaf standby {
         description "Name of standby path";
         type string;
       }
       leaf multipoint {
         description "Probe multipoint LSP";
         type empty;
       }
       leaf egress {
         description "Request only a specific multipoint egress to respond";
         type ipv4addr;
       }
       leaf instance {
         description "Routing-instance name";
         type string;
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-rsvp-dynamic-bypass-lsp {
     description "Dynamically created LSP, used for protecting other LSPs";
     input {
       leaf lsp-name {
         description "Name of dynamic bypass LSP";
         type string {
           length "1 .. 64";
         }
         mandatory true;
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-rsvp-manual-bypass-lsp {
     description "Manually configured LSP, used for protecting other LSPs";
     input {
       leaf lsp-name {
         description "Name of manual bypass LSP";
         type string {
           length "1 .. 64";
         }
         mandatory true;
       }
       leaf interface {
         description "Name of the interface, which is protected by this bypass";
         type interface-name;
         mandatory true;
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-ldp-lsp {
     description "Ping LDP-signaled LSP";
     input {
       leaf fec {
         description "IP prefix/length of forwarding equivalence class";
         type ipprefix;
         mandatory true;
       }
       leaf instance {
         description "Routing-instance name";
         type string;
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-ldp-p2mp-lsp {
     description "Ping LDP-signaled P2MP LSP";
     input {
       leaf root-addr {
         description "IP address of p2mp lsp root";
         type ipv4addr;
         mandatory true;
       }
       leaf lsp-id {
         description "LSP ID of p2mp lsp";
         type uint32 {
           range "1 .. 4294967295";
         }
         mandatory true;
       }
       leaf egress {
         description "Request only a specific multipoint egress to respond";
         type ipv4addr;
       }
       leaf instance {
         description "Routing-instance name";
         type string;
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-bgp-lsp {
     description "Ping BGP-signaled LSP";
     input {
       leaf fec {
         description "IP prefix/length of forwarding equivalence class";
         type ipprefix;
         mandatory true;
       }
       leaf bottom-label-ttl {
         description "Time to live for the bottom label in the label stack";
         type uint32 {
           range "1 .. 255";
         }
       }
       leaf instance {
         description "Routing-instance name";
         type string;
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-l3vpn {
     description "Ping LSP to Layer 3 VPN prefix";
     input {
       leaf l3vpn-name {
         description "Name of Layer 3 VPN";
         type string;
         mandatory true;
       }
       leaf prefix {
         description "IP prefix/length of Layer 3 VPN";
         type ipprefix;
         mandatory true;
       }
       leaf bottom-label-ttl {
         description "Time to live for the bottom label in the label stack";
         type uint32 {
           range "1 .. 255";
         }
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-l2vpn-interface {
     description "Locate LSP using interface name";
     input {
       leaf interface-name {
         description "Interface name";
         type interface-name;
         mandatory true;
       }
       leaf bottom-label-ttl {
         description "Time to live for the bottom label in the label stack";
         type uint32 {
           range "1 .. 255";
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-l2vpn-instance {
     description "Instance to which this connection belongs";
     input {
       leaf instance-name {
         description "Layer 2 VPN name";
         type string;
         mandatory true;
       }
       leaf local-site-id {
         description "Layer 2 VPN local site identifier";
         type uint32 {
           range "1 .. 65534";
         }
         mandatory true;
       }
       leaf remote-site-id {
         description "Layer 2 VPN remote site identifier";
         type uint32 {
           range "1 .. 65534";
         }
         mandatory true;
       }
       leaf bottom-label-ttl {
         description "Time to live for the bottom label in the label stack";
         type uint32 {
           range "1 .. 255";
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-l2vpn-fec129-interface {
     description "Locate Pseudowire using interface name";
     input {
       leaf interface-name {
         description "Interface name";
         type interface-name;
         mandatory true;
       }
       leaf bottom-label-ttl {
         description "Time to live for the bottom label in the label stack";
         type uint32 {
           range "1 .. 255";
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-l2vpn-fec129-instance {
     description "Instance to which this connection belongs";
     input {
       leaf instance-name {
         description "Layer 2 VPN name";
         type string;
         mandatory true;
       }
       leaf local-id {
         description "Layer 2 VPN Source Attachment Individual Identifier (SAII)";
         type string {
           junos:posix-pattern "^([[:digit:].]){0,15}$|^([[:digit:]]){0,10}:([[:digit:].]){0,15}:([[:digit:]]){1,10}$";
           junos:pattern-message "Invalid Local-id";
         }
         mandatory true;
       }
       leaf remote-id {
         description "Layer 2 VPN Target Attachment Individual Identifier (TAII)";
         type string {
           junos:posix-pattern "^([[:digit:].]){0,15}$|^([[:digit:]]){0,10}:([[:digit:].]){0,15}:([[:digit:]]){1,10}$";
           junos:pattern-message "Invalid Remode-id";
         }
         mandatory true;
       }
       leaf remote-pe-address {
         description "Layer 2 Remote PE address";
         type ipv4addr;
         mandatory true;
       }
       leaf bottom-label-ttl {
         description "Time to live for the bottom label in the label stack";
         type uint32 {
           range "1 .. 255";
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-l2circuit-interface {
     description "Locate LSP from interface name";
     input {
       leaf v1 {
         description "Ping using Layer 2 circuit TLV (type 9)";
         type empty;
       }
       leaf interface-name {
         description "Interface name";
         type interface-name;
         mandatory true;
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-l2circuit-virtual-circuit {
     description "Locate LSP from virtual circuit information";
     input {
       leaf v1 {
         description "Ping using Layer 2 circuit TLV (type 9)";
         type empty;
       }
       leaf neighbor {
         description "Address of remote neighbor";
         type ipprefix;
         mandatory true;
       }
       leaf virtual-circuit-id {
         description "Layer 2 circuit identifier";
         type uint32 {
           range "1 .. 4294967295";
         }
         mandatory true;
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-lsp-end-point {
     description "Ping end point of LSP";
     input {
       leaf prefix {
         description "IP prefix/length of end point";
         type ipprefix;
         mandatory true;
       }
       leaf instance {
         description "Routing-instance name";
         type string;
       }
       leaf count {
         description "Number of ping requests to send";
         units "packets";
         type uint32 {
           range "1 .. 1000000";
         }
       }
       leaf source {
         description "IP source address of echo request";
         type ipprefix;
       }
       leaf destination {
         description "IP address of destination for echo request";
         type ipv4addr;
       }
       leaf exp {
         description "Forwarding class";
         type uint32 {
           range "0 .. 7";
         }
       }
       leaf detail {
         description "Display detailed output";
         type empty;
       }
       leaf size {
         description "Size of lsp ping request packet";
         units "bytes";
         type uint32 {
           range "1 .. 65468";
         }
       }
       leaf sweep {
         description "Incremental ping to find MTU";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }

   rpc request-ping-vpls-instance {
     description "Instance to which this VPLS connection belongs";
     input {
       leaf instance-name {
         description "Layer 2 VPLS name";
         type string;
         mandatory true;
       }
       leaf destination-mac {
         description "Destination MAC address";
         type mac-addr;
         mandatory true;
       }
       leaf source-ip {
         description "Source IP address";
         type ipv4addr;
         mandatory true;
       }
       leaf learning-vlan-id {
         description "Learning VLAN identifier";
         type int32 {
           range "0 .. 4094";
         }
       }
       leaf control-plane-response {
         description "Request VPLS OAM responses using the control plane ";
         type empty;
       }
       leaf bd-name {
         description "Name of bridge domain";
         type string;
       }
       leaf count {
         description "Number of ping requests to send";
         units "packets";
         type uint32 {
           range "1 .. 1000000";
         }
       }
       leaf detail {
         description "Display detailed output";
         type empty;
       }
       leaf logical-system {
         description "Name of logical system";
         type string {
           junos:posix-pattern "^[a-zA-Z0-9_-]{1,63}$";
           junos:pattern-message "Logical-system name is a string consisting of up to 63 letters, numbers, dashes and underscores";
         }
       }
     }
     output {
       container lsping-results {
         leaf lsping-route-comment {
           type string;
           description "Route established using this protocol";
         }
         leaf lsping-success {
           type empty;
           description "Destination reached";
         }
         leaf lsping-failure {
           type string;
           description "Lsping failed";
         }
         container lsping-probe-request {
           description "One request probe";
           leaf lsping-sequence-number {
             type int32;
             description "Sequence number in request packet";
           }
           leaf lsping-interface-index {
             type int32;
           }
           leaf lsping-label {
             type int32;
             description "Label of MPLS packet";
           }
           leaf lsping-packet-size {
             type int32;
             description "Ping request packet size";
           }
         }
         container lsping-probe-reply {
           leaf lsping-sequence-number {
             type int32;
             description "Sequence number in request packet";
           }
           leaf lsping-return-code {
             type string;
             description "Success or failure code";
           }
           leaf lsping-ip-address {
             type string;
             description "IPV4 Egress address";
           }
           leaf lsping-round-trip-time {
             type int32;
             description "Round Trip Time in ms";
           }
           leaf lsping-local-transmit-time {
             type string;
             description "Local transmit time in seconds since Jan 1,1970";
           }
           leaf lsping-local-transmit-time-us {
             type int32;
             description "Local transmit time in micro-seconds since Jan 1,1970";
           }
           leaf lsping-remote-receive-time {
             type string;
             description "Remote receive time in seconds since Jan 1,1970";
           }
           leaf lsping-remote-receive-time-us {
             type int32;
             description "Remote receive time in micro-seconds since Jan 1,1970";
           }
         }
         container lsping-results-summary {
           description "Summary of lsping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container vpls-ping-results-summary {
           description "Summary of vpls ping probe results";
           leaf lsping-packets-transmitted {
             type int32;
             description "Number of packets sent to target host";
           }
           leaf lsping-packets-received {
             type int32;
             description "Number of packets received from the target host";
           }
           leaf lsping-packet-loss {
             type int32;
             description "Lsping percentage of packets that resulted in no response";
           }
           leaf lsping-error-packets {
             type int32;
             description " Number of packets received with error status";
           }
         }
         container lsping-sweep-summary {
           description "Ping sweep result";
           leaf lsping-mtu {
             type int32;
             description " Maximum Transmission Unit (MTU)";
           }
         }
       }
     }
   }
   rpc request-ping-overlay {
     description "Ping overlay path";
     input {
       leaf tunnel-type {
         description "Tunnel type";
         default "vxlan";
         type enumeration {
           enum "vxlan" {
             description "Vxlan tunnel-type";
           }
         }
       }
       leaf vni {
         description "Value of the vni that identifies the overlay segment";
         type uint32 {
           range "1 .. 16777215";
         }
         mandatory true;
       }
       leaf tunnel-src {
         description "Source VTEP IP address";
         type ipv4addr;
         mandatory true;
       }
       leaf tunnel-dst {
         description "Remote VTEP IP address";
         type ipv4addr;
         mandatory true;
       }
       container address {
         choice address_c {
           case mac {
             leaf mac {
               description "Validate MAC address";
               type mac-unicaset;
             }
           }
         }
       }
       leaf count {
         description "Number of pings to send";
         default "5";
         type uint32 {
           range "1 .. 65535";
         }
       }
       leaf ttl {
         description "TTL to use in the ping packets";
         default "255";
         type uint32 {
           range "1 .. 255";
         }
       }
       leaf hash-input-interface {
         type interface-device;
       }
       leaf hash-source-mac {
         type mac-unicaset;
       }
       leaf hash-destination-mac {
         type mac-unicaset;
       }
       leaf hash-protocol {
         type uint32 {
           range "1 .. 255";
         }
       }
       leaf hash-source-address {
         type ipv4addr;
       }
       leaf hash-destination-address {
         type ipv4addr;
       }
       leaf hash-source-port {
         type uint32 {
           range "1 .. 65535";
         }
       }
       leaf hash-destination-port {
         type uint32 {
           range "1 .. 65535";
         }
       }
       leaf hash-vlan {
         type uint32 {
           range "1 .. 4094";
         }
       }
     }
   }
 }
