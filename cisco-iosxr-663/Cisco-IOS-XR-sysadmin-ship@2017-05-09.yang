module Cisco-IOS-XR-sysadmin-ship {
  namespace "http://www.cisco.com/ns/yang/Cisco-IOS-XR-sysadmin-ship";
  prefix ship;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin operational.

This module defines operational data for
sysadmin ship process.

Copyright(c) 2010-2016 by Cisco Systems, Inc.
All rights reserved.

    Copyright (c) 2012-2018 by Cisco Systems, Inc.
     All rights reserved.";
  revision 2017-05-09 {
    description
      "Namespace change to comply with Cisco guidelines";
  }

  container stat {
    description
      "SHIP Info";
    config false;
    list ship_comp {
      description
        "Select ship client component";
      key "comp-name";
      leaf comp-name {
        type string;
        description
          "Name of component";
      }
      list process {
        key "process-name";
        leaf process-name {
          type string;
        }
        list client {
          key "client-name";
          leaf client-name {
            type string;
          }
          list cat {
            key "cat-name";
            leaf cat-name {
              type enumeration {
                enum "SHIP_TRANSPORT_COUNTERS" {
                  value 0;
                }
                enum "SHIP_SERVER_COUNTERS" {
                  value 1;
                }
                enum "SHIP_CLIENT_LIB_COUNTERS" {
                  value 2;
                }
                enum "SHIP_REPLICATION_COUNTERS" {
                  value 3;
                }
                enum "SHIP_READER_REPLICA_COUNTERS" {
                  value 4;
                }
                enum "SHIP_WRITER_REPLICA_COUNTERS" {
                  value 5;
                }
                enum "SHIP_TRANSPORT_COUNTERS_FAILOVER" {
                  value 6;
                }
                enum "SHIP_SERVER_COUNTERS_FAILOVER" {
                  value 7;
                }
                enum "SHIP_CLIENT_LIB_COUNTERS_FAILOVER" {
                  value 8;
                }
                enum "SHIP_REPLICATION_COUNTERS_FAILOVER" {
                  value 9;
                }
                enum "SHIP_TRANSPORT_ERRORS" {
                  value 10;
                }
                enum "SHIP_SERVER_ERRORS" {
                  value 11;
                }
                enum "SHIP_CLIENT_LIB_ERRORS" {
                  value 12;
                }
                enum "SHIP_REPLICATION_ERRORS" {
                  value 13;
                }
                enum "SHIP_READER_REPLICA_ERRORS" {
                  value 14;
                }
                enum "SHIP_WRITER_REPLICA_ERRORS" {
                  value 15;
                }
                enum "SHIP_TRANSPORT_ERRORS_FAILOVER" {
                  value 16;
                }
                enum "SHIP_SERVER_ERRORS_FAILOVER" {
                  value 17;
                }
                enum "SHIP_CLIENT_LIB_ERRORS_FAILOVER" {
                  value 18;
                }
                enum "SHIP_REPLICATION_ERRORS_FAILOVER" {
                  value 19;
                }
                enum "FEATURE_MA_COUNTERS" {
                  value 20;
                }
                enum "FEATURE_MA_COUNTERS_ERRORS" {
                  value 21;
                }
                enum "FEATURE_MA_COUNTERS_FAILOVER" {
                  value 22;
                }
                enum "VIRTUAL_INTERFACE_MA_COUNTERS" {
                  value 23;
                }
                enum "VIRTUAL_INTERFACE_MA_COUNTERS_ERRORS" {
                  value 24;
                }
                enum "VIRTUAL_INTERFACE_MA_COUNTERS_FAILOVER" {
                  value 25;
                }
                enum "FEATURE_EA_COUNTERS" {
                  value 26;
                }
                enum "FEATURE_EA_COUNTERS_ERRORS" {
                  value 27;
                }
                enum "VIRTUAL_INTERFACE_EA_COUNTERS" {
                  value 28;
                }
                enum "VIRTUAL_INTERFACE_EA_COUNTERS_ERRORS" {
                  value 29;
                }
                enum "VIRTUAL_INTERFACE_EA_COUNTERS_FAILOVER" {
                  value 30;
                }
                enum "SHIP_HISTOGRAM_COUNTERS" {
                  value 31;
                }
                enum "SHIP_WATERMARK_COUNTERS" {
                  value 32;
                }
                enum "SHIP_NODE_COUNTERS" {
                  value 33;
                }
              }
            }
            list counter-32b {
              key "counter-name";
              leaf counter-name {
                type string;
              }
              leaf counter-value {
                type uint32;
              }
              leaf watermark {
                type uint32;
              }
              leaf time-stamp {
                type uint64;
              }
              leaf hist-info1 {
                type uint32;
              }
              leaf hist-info2 {
                type uint32;
              }
              leaf hist-info3 {
                type uint32;
              }
              leaf hist-info4 {
                type uint32;
              }
              leaf hist-info5 {
                type uint32;
              }
              leaf hist-info6 {
                type uint32;
              }
              leaf hist-info7 {
                type uint32;
              }
              leaf hist-info8 {
                type uint32;
              }
            }
          }
        }
      }
    }
  }
}
