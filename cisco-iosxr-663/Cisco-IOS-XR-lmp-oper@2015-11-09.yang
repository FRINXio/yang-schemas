module Cisco-IOS-XR-lmp-oper {

  /*** NAMESPACE / PREFIX DEFINITION ***/

  namespace "http://cisco.com/ns/yang/Cisco-IOS-XR-lmp-oper";


  prefix "lmp-oper";

  /*** LINKAGE (IMPORTS / INCLUDES) ***/

  import Cisco-IOS-XR-types { prefix "xr"; }

  include Cisco-IOS-XR-lmp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lmp package operational data.

     This module contains definitions
     for the following management objects:
       lmp: Main common UCP/OLM operational data

     Copyright (c) 2013-2018 by Cisco Systems, Inc.
     All rights reserved.";

  revision "2015-11-09" {
    description
      "IOS XR 6.0 revision.";
  }


  container lmp {
    config false;
    description "Main common UCP/OLM operational data";

    container global-status {
      description "Global OLM process information";
      uses OLM-GLOBAL-INFO;
    }

    container clients {
      description "UCP OLM clients container class";

      list client {
        key "client-name";
        description "Information on a particular OLM API client";
        leaf client-name {
          type xr:Cisco-ios-xr-string;
          description "Client name";
        }
        uses OLM-CLIENT-INFO;
      }
    }

    container gmpls-uni {
      description "GMPLS UNI specific OLM/LMP configuration";

      container te-links {
        description "UCP OLM TE Links container class";

        list te-link {
          key "controller-name";
          description "Information on a particular OLM TE Link";
          leaf controller-name {
            type xr:Interface-name;
            description "Controller name";
          }
          uses OLM-TE-LINK-INFO;
        }
      }

      container neighbors {
        description "UCP OLM neighbors container class";

        list neighbor {
          key "neighbor-name";
          description "Information on a particular OLM neighbor";
          leaf neighbor-name {
            type xr:Cisco-ios-xr-string {
              length "1..64";
            }
            description "Neighbor name";
          }
          uses OLM-NEIGHBOR-INFO;
        }
      }
    }

    container component-link-ids {
      description "UCP OLM component link ID container class";

      list component-link-id {
        key "controller-name";
        description
          "Retrieve the LMP component link ID for a given
          controller";
        leaf controller-name {
          type xr:Interface-name;
          description "Controller name";
        }
        uses OLM-COMPONENT-LINK-ID-INFO;
      }
    }
  }
}
