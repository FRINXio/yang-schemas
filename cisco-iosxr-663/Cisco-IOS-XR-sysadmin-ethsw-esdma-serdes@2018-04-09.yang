module Cisco-IOS-XR-sysadmin-ethsw-esdma-serdes {
  namespace "http://www.cisco.com/ns/yang/Cisco-IOS-XR-sysadmin-ethsw-esdma-serdes";
  prefix esdma_serdes;
  import Cisco-IOS-XR-sysadmin-ethsw-esdma-types {
    prefix esdma_types;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains the YANG definitions
for the Cisco IOS-XR SysAdmin
'show controller switch serdes' commands.

Copyright(c) 2011-2017 by Cisco Systems, Inc.
All rights reserved.

    Copyright (c) 2012-2018 by Cisco Systems, Inc.
     All rights reserved.";
  revision 2018-04-09 {
    description
      "Required changes for ConfD 6.4.5";
  }


  grouping switch-serdes-group {
    container serdes {
      container serdes-statistics {
        list location {
          key "rack card switch-id";
          leaf rack {
            type esdma_types:esdma-rack-num-enum;
          }
          leaf card {
            type esdma_types:esdma-cpu;
            description
              "Card to list the switch Serdes information for";
          }
          leaf switch-id {
            type esdma_types:esdma-switch-type-enum;
            description
              "Switch type";
          }
          list port-iter {
            key "port";
            leaf port {
              type esdma_types:esdma-switch-port-type;
              description
                "Switch port";
            }
            list serdes-entry {
              key "id";
              leaf id {
                type uint32;
              }
              leaf base-reg {
                type string;
              }
              leaf desc {
                type string;
              }
              leaf lane-0 {
                type string;
              }
              leaf lane-1 {
                type string;
              }
              leaf lane-2 {
                type string;
              }
              leaf lane-3 {
                type string;
              }
            }
          }
        }
      }
    }
  }
}
