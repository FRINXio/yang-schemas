module Cisco-IOS-XR-ipv4-arp-oper {

  /*** NAMESPACE / PREFIX DEFINITION ***/

  namespace "http://cisco.com/ns/yang/Cisco-IOS-XR-ipv4-arp-oper";


  prefix "ipv4-arp-oper";

  /*** LINKAGE (IMPORTS / INCLUDES) ***/

  import ietf-inet-types { prefix "inet"; }

  import Cisco-IOS-XR-types { prefix "xr"; }

  include Cisco-IOS-XR-ipv4-arp-oper-sub2 {
    revision-date 2017-05-01;
  }

  include Cisco-IOS-XR-ipv4-arp-oper-sub1 {
    revision-date 2017-05-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-arp package operational data.

     This module contains definitions
     for the following management objects:
       arp-gmp: ARP-GMP global operational data
       arp: arp

     Copyright (c) 2013-2018 by Cisco Systems, Inc.
     All rights reserved.";

  revision "2017-05-01" {
    description
      "Fixing backward compatibility error in module.";
  }

  revision "2016-12-19" {
    description
      "IOS XR 6.2.1 revision.";
  }

  revision "2015-11-09" {
    description
      "IOS XR 6.0 revision.";
  }


  container arp-gmp {
    config false;
    description "ARP-GMP global operational data";

    container vrf-infos {
      description "Table of VRF related ARP-GMP operational data";

      list vrf-info {
        key "vrf-name";
        description "VRF related ARP-GMP operational data";
        leaf vrf-name {
          type xr:Cisco-ios-xr-string;
          description "VRF name for the default VRF use 'default'";
        }
        uses ARP-GMP-VRF-ENTRY;
      }
    }

    container vrfs {
      description "Table of per VRF ARP-GMP operational data";

      list vrf {
        key "vrf-name";
        description "Per VRF ARP-GMP operational data";

        container configured-ip-addresses {
          description
            "Table of ARP-GMP configured IP addresses
            information";

          list configured-ip-address {
            key "address";
            description "ARP-GMP configured IP address information";
            leaf address {
              type inet:ipv4-address-no-zone;
              description "Configured ARP-GMP IP";
            }
            uses ARP-GMP-CONFIG-ENTRY;
          }
        }

        container routes {
          description "Table of ARP GMP route information";

          list route {
            description "ARP GMP route information";
            leaf address {
              type inet:ipv4-address-no-zone;
              description "IP address";
            }
            leaf prefix-length {
              type uint32 {
                range "0..32";
              }
              description "Prefix length";
            }
            uses ARP-GMP-ROUTE-ENTRY;
          }
        }

        container interface-configured-ips {
          description
            "Table of ARP GMP interface and associated
            configured IP data";

          list interface-configured-ip {
            description
              "ARP GMP interface and associated configured
              IP data";
            leaf interface-name {
              type xr:Interface-name;
              description "Interface name";
            }
            leaf address {
              type inet:ipv4-address-no-zone;
              description "Configured ARP-GMP IP";
            }
            uses ARP-GMP-INTF-ENTRY;
          }
        }
        leaf vrf-name {
          type xr:Cisco-ios-xr-string;
          description "VRF name for the default VRF use 'default'";
        }
      }
    }
  }

  container arp {
    config false;
    description "arp";

    container nodes {
      description "Table of per-node ARP operational data";

      list node {
        key "node-name";
        description "Per-node ARP operational data";

        container resolution-history-dynamic {
          description
            "Per node dynamically-resolved ARP resolution
            history data";
          uses ARP-RESHIST;
        }

        container arp-status-info {
          description "Per node ARP status information";
          uses ARP-STATUS-INFO;
        }

        container traffic-vrfs {
          description "ARP Traffic information per VRF";

          list traffic-vrf {
            key "vrf-name";
            description "Per VRF traffic data";
            leaf vrf-name {
              type string;
              description "VRF name";
            }
            uses IP-ARP-STATISTICS;
          }
        }

        container traffic-node {
          description "Per node ARP Traffic data";
          uses IP-ARP-STATISTICS;
        }

        container resolution-history-client {
          description
            "Per node client-installed ARP resolution
            history data";
          uses ARP-RESHIST;
        }

        container entries {
          description "Table of ARP entries";

          list entry {
            key "address interface-name";
            description "ARP entry";
            leaf address {
              type inet:ipv4-address-no-zone;
              description "IP Address of ARP entry";
            }
            leaf interface-name {
              type xr:Interface-name;
              description "Interface name";
            }
            uses IP-ARP-TABLE-ENTRY;
          }
        }

        container traffic-interfaces {
          description "ARP Traffic information per interface";

          list traffic-interface {
            key "interface-name";
            description "Per interface traffic data";
            leaf interface-name {
              type xr:Interface-name;
              description "Interface name";
            }
            uses IP-ARP-STATISTICS;
          }
        }
        leaf node-name {
          type xr:Node-id;
          description "Node name";
        }
      }
    }
  }
}
