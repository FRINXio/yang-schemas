submodule Cisco-IOS-XR-ip-rib-ipv4-oper-sub1 {

  belongs-to Cisco-IOS-XR-ip-rib-ipv4-oper {
    prefix Cisco-IOS-XR-ip-rib-ipv4-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rib-ipv4 package operational data.

     Copyright (c) 2013-2018 by Cisco Systems, Inc.
     All rights reserved.";

  revision "2019-01-11" {
    description
      "Route lookup key is limited to Prefix and Prefix Length";
  }

  revision "2018-11-20" {
    description
      "Add keys for route lookup via resconf.";
  }

  revision "2015-11-09" {
    description
      "IOS XR 6.0 revision.";
  }

  typedef Rib-edm-nnh {
    type enumeration {
      enum unknown {
        description "Unknown - Invalid";
      }
      enum ipv4-address {
        description "IPv4 Address";
      }
      enum if-index {
        description "Interface Index";
      }
    }
    description "Rib edm nnh";
  }
  typedef Ipv4-rib-edm-addr {
    type inet:ipv4-address;
    description "Ipv4 rib edm addr";
  }

  grouping IPV4-RIB-EDM-TABLE {
    description "Information of a routing table";
    leaf tableid {
      type uint32;
      description "Table id";
    }
    leaf afi {
      type uint32;
      description "Address Family";
    }
    leaf safi {
      type uint32;
      description "sub Address Family";
    }
    leaf vrf-name {
      type string;
      description "VRF Name of the table";
    }
    leaf table-name {
      type string;
      description "Name of the table";
    }
    leaf version {
      type uint64;
      description "Table version";
    }
    leaf conf-prefix-limit {
      type uint32;
      description "Configured prefix limit";
    }
    leaf current-prefix-count {
      type uint32;
      description "Num prefixes in table";
    }
    leaf num-svdlcl-prefix {
      type uint32;
      description "Num SVD local prefixes";
    }
    leaf num-svdrem-prefix {
      type uint32;
      description "Num SVD remote prefixes";
    }
    leaf table-version {
      type uint64;
      description "Version no. of the table";
    }
    leaf prefix-limit-notified {
      type boolean;
      description "Prefix limit state indicator";
    }
    leaf fwd-referenced {
      type boolean;
      description "Table in fwd reference state?";
    }
    leaf deleted {
      type boolean;
      description "Table deleted?";
    }
    leaf initial-converge {
      type boolean;
      description "Table has reached convergence";
    }
  }

  grouping RIB-EDM-ROUTE-COUNT {
    description "Specifics of route count";
    leaf active-routes-count {
      type uint32;
      description "Number of active routes";
    }
    leaf num-backup-routes {
      type uint32;
      description "Number of backup (inactive) routes";
    }
    leaf num-active-paths {
      type uint32;
      description "Number of paths to active routes";
    }
    leaf num-backup-paths {
      type uint32;
      description "Number of paths to backup routes";
    }
  }

  grouping RIB-EDM-PROTO-ROUTE-SUMM-DETAIL {
    description "Details of Protocol route types";

    container proto-route-count {
      description "Count for proto. instance";
      uses RIB-EDM-ROUTE-COUNT;
    }

    container rtype-none {
      description "No route type";
      uses RIB-EDM-ROUTE-COUNT;
    }

    container rtype-other {
      description "Unknown route type";
      uses RIB-EDM-ROUTE-COUNT;
    }

    container rtype-ospf-intra {
      description "OSPF route within an area";
      uses RIB-EDM-ROUTE-COUNT;
    }

    container rtype-ospf-inter {
      description "OSPF route across diff. areas";
      uses RIB-EDM-ROUTE-COUNT;
    }

    container rtype-ospf-extern1 {
      description "OSPF external route of type 1";
      uses RIB-EDM-ROUTE-COUNT;
    }

    container rtype-ospf-extern2 {
      description "OSPF external route of type 2";
      uses RIB-EDM-ROUTE-COUNT;
    }

    container rtype-isis-sum {
      description "IS-IS summary route";
      uses RIB-EDM-ROUTE-COUNT;
    }

    container rtype-isis-l1 {
      description "IS-IS level 1 route";
      uses RIB-EDM-ROUTE-COUNT;
    }

    container rtype-isis-l2 {
      description "IS-IS level 2 route";
      uses RIB-EDM-ROUTE-COUNT;
    }

    container rtype-isis-l1-ia {
      description "IS-IS level1 inter-area route";
      uses RIB-EDM-ROUTE-COUNT;
    }

    container rtype-bgp-int {
      description "iBGP route";
      uses RIB-EDM-ROUTE-COUNT;
    }

    container rtype-bgp-ext {
      description "eBGP route";
      uses RIB-EDM-ROUTE-COUNT;
    }

    container rtype-bgp-loc {
      description "BGP local route";
      uses RIB-EDM-ROUTE-COUNT;
    }

    container rtype-ospf-nssa1 {
      description "OSPF NSSA ext. route type 1";
      uses RIB-EDM-ROUTE-COUNT;
    }

    container rtype-ospf-nssa2 {
      description "OSPF NSSA ext. route type 2";
      uses RIB-EDM-ROUTE-COUNT;
    }

    container rtype-igrp2-int {
      description "EIGRP internal route";
      uses RIB-EDM-ROUTE-COUNT;
    }

    container rtype-igrp2-ext {
      description "EIGRP external route";
      uses RIB-EDM-ROUTE-COUNT;
    }
    leaf name {
      type string;
      description "Proto name";
    }
    leaf instance {
      type string;
      description "Instance";
    }
  }

  grouping IPV4-RIB-EDM-ADVERT {
    description "Route advertisement information";

    list ipv4-rib-edm-advert {
      description "Next advertising proto";
      leaf protocol-id {
        type uint32;
        description "Protocol advertising the route";
      }
      leaf client-id {
        type uint32;
        description "  Client advertising the route";
      }
      leaf number-of-extended-communities {
        type uint32;
        description "Number of extended communities";
      }
      leaf extended-communities {
        type yang:hex-string;
        description "Extended communities";
      }
      leaf protocol-opaque-flags {
        type uint8;
        description "OSPF area-id flags";
      }
      leaf protocol-opaque {
        type uint32;
        description "OSPF area-id";
      }
      leaf code {
        type int8;
        description "Protocol code";
      }
      leaf instance-name {
        type string {
          length "0..41";
        }
        description "Instance name";
      }
    }
  }

  grouping IPV4-RIB-EDM-PROTO {
    description "Information of a rib protocol";
    leaf protocol-names {
      type string;
      description "Name";
    }
    leaf instance {
      type string;
      description "Instance";
    }
    leaf version {
      type uint32;
      description "Proto version";
    }
    leaf redistribution-client-count {
      type uint32;
      description "Number of redist clients";
    }
    leaf protocol-clients-count {
      type uint32;
      description "Number of proto clients";
    }
    leaf routes-counts {
      type uint32;
      description
        "Number of routes (including active, backup and
        deleted), where, number of backup routes =
        RoutesCounts - ActiveRoutesCount -
        DeletedRoutesCount ";
    }
    leaf active-routes-count {
      type uint32;
      description "Number of active routes (not deleted)";
    }
    leaf deleted-routes-count {
      type uint32;
      description "Number of deleted routes";
    }
    leaf paths-count {
      type uint32;
      description "Number of paths for all routes";
    }
    leaf protocol-route-memory {
      type uint32;
      units "byte";
      description "Memory for proto's routes and paths in bytes";
    }
    leaf backup-routes-count {
      type uint32;
      description "Number of backup routes";
    }
  }

  grouping RIB-EDM-OPAQUE-OBJ {
    description "Informaton of an opaque data";
    leaf key {
      type yang:hex-string;
      description "key";
    }
    leaf data {
      type yang:hex-string;
      description "data";
    }
  }

  grouping RIB-EDM-SRV6-SID {
    description
      "Information of SRv6 SID attribute installed in
      the RIB";
    leaf sid {
      type inet:ipv6-address;
      description "Segment Identifier Attribute";
    }
  }

  grouping RIB-EDM-NNH {
    description "Information of a NNH in path installed in RIB";
    leaf type {
      type Rib-edm-nnh;
      description "type";
    }
    leaf unknownval {
      when "../type = 'unknown'" {
        description "../type = 'Unknown'";
      }
      type uint32;
      description "Unknown Value";
    }
    leaf address {
      when "../type = 'ipv4-address'" {
        description "../type = 'IPv4Address'";
      }
      type inet:ipv4-address;
      description "IPv4 Address";
    }
    leaf interface-index {
      when "../type = 'if-index'" {
        description "../type = 'IfIndex'";
      }
      type uint32;
      description "Interface Index";
    }
  }

  grouping IPV4-RIB-EDM-PATH {
    description "Information of a rib path";

    list ipv4-rib-edm-path {
      description "Next path";
      leaf address {
        xr:event-telemetry "Subscribe Telemetry Event";
        type Ipv4-rib-edm-addr;
        description "Nexthop";
      }
      leaf information-source {
        xr:event-telemetry "Subscribe Telemetry Event";
        type Ipv4-rib-edm-addr;
        description "Infosource";
      }
      leaf v6-nexthop {
        xr:event-telemetry "Subscribe Telemetry Event";
        type inet:ipv6-address;
        description "V6 nexthop";
      }
      leaf v6-information-source {
        xr:event-telemetry "Subscribe Telemetry Event";
        type inet:ipv6-address;
        description "V6 Infosource";
      }
      leaf interface-name {
        xr:event-telemetry "Subscribe Telemetry Event";
        type xr:Interface-name;
        description "Interface Name";
      }
      leaf metric {
        xr:event-telemetry "Subscribe Telemetry Event";
        type uint32;
        description "Metrics";
      }
      leaf load-metric {
        xr:event-telemetry "Subscribe Telemetry Event";
        type uint32;
        description "Load Metrics";
      }
      leaf flags64 {
        type uint64;
        description "Flags extended to 64 bits";
      }
      leaf flags {
        xr:event-telemetry "Subscribe Telemetry Event";
        type uint16;
        description "Flags";
      }
      leaf private-flags {
        type uint16;
        description "Private Flags";
      }
      leaf minimum-recurse-length {
        type uint8;
        description
          "Minimum netmask length of recursive resolving
          route";
      }
      leaf looped {
        type boolean;
        description "Looping path";
      }
      leaf next-hop-table-id {
        xr:event-telemetry "Subscribe Telemetry Event";
        type uint32;
        description "Nexthop tableid";
      }
      leaf next-hop-vrf-name {
        xr:event-telemetry "Subscribe Telemetry Event";
        type string;
        description "VRF Name of the nh table";
      }
      leaf next-hop-table-name {
        xr:event-telemetry "Subscribe Telemetry Event";
        type string;
        description "NH table name";
      }
      leaf next-hop-afi {
        xr:event-telemetry "Subscribe Telemetry Event";
        type uint32;
        description "NH afi";
      }
      leaf next-hop-safi {
        xr:event-telemetry "Subscribe Telemetry Event";
        type uint32;
        description "NH safi";
      }
      leaf route-label {
        xr:event-telemetry "Subscribe Telemetry Event";
        type uint32;
        description "Label associated with this path";
      }
      leaf tunnel-id {
        xr:event-telemetry "Subscribe Telemetry Event";
        type uint32;
        description "Tunnel ID associated with this path";
      }
      leaf pathid {
        xr:event-telemetry "Subscribe Telemetry Event";
        type uint32;
        description "Path id of this path";
      }
      leaf backup-pathid {
        xr:event-telemetry "Subscribe Telemetry Event";
        type uint32;
        description "Path id of this path's backup";
      }
      leaf ref-cnt-of-backup {
        type uint32;
        description "Refcnt of backup";
      }
      leaf number-of-extended-communities {
        xr:event-telemetry "Subscribe Telemetry Event";
        type uint32;
        description "Number of extended communities";
      }
      leaf mvpn-present {
        xr:event-telemetry "Subscribe Telemetry Event";
        type boolean;
        description "MVPN attribute present";
      }
      leaf path-rt-present {
        type boolean;
        description "Path RT present";
      }
      leaf vrf-import-rt-present {
        xr:event-telemetry "Subscribe Telemetry Event";
        type boolean;
        description "VRFIMPORTRTPresent";
      }
      leaf source-asrt-present {
        xr:event-telemetry "Subscribe Telemetry Event";
        type boolean;
        description "SOURCEASRTPresent";
      }
      leaf source-rd-present {
        xr:event-telemetry "Subscribe Telemetry Event";
        type boolean;
        description "SOURCERDPresent";
      }
      leaf segmented-nexthop-present {
        xr:event-telemetry "Subscribe Telemetry Event";
        type boolean;
        description "SegmentedNexthopPresent";
      }
      leaf number-of-nnh {
        type uint32;
        description "Number of Next Next Hops";
      }
      leaf next-hop-id {
        xr:event-telemetry "Subscribe Telemetry Event";
        type uint32;
        description "NHID associated with this path";
      }
      leaf next-hop-id-refcount {
        type uint32;
        description "NHID references";
      }
      leaf ospf-area-id {
        xr:event-telemetry "Subscribe Telemetry Event";
        type string;
        description "OSPF area associated with the path";
      }
      leaf has-labelstk {
        xr:event-telemetry "Subscribe Telemetry Event";
        type boolean;
        description "Path has a label stack";
      }
      leaf num-labels {
        xr:event-telemetry "Subscribe Telemetry Event";
        type uint8;
        description "Number of labels in stack";
      }
      leaf binding-label {
        xr:event-telemetry "Subscribe Telemetry Event";
        type uint32;
        description "binding Label for this path";
      }
      leaf nhid-feid {
        type uint64;
        description "Fib nhid encap id";
      }
      leaf mpls-feid {
        type uint64;
        description "Fib mpls encap id";
      }
      leaf has-vxlan-network-id {
        type boolean;
        description "VXLAN Network Identifier exists for this path";
      }
      leaf vxlan-network-id {
        type uint32;
        description "VXLAN Network Identifier for this path";
      }
      leaf has-xcid {
        type boolean;
        description "L2 Cross Connect ID exists for this path";
      }
      leaf xcid {
        type uint32;
        description "L2 Cross Connect ID for this path";
      }
      leaf has-span-diag-interface {
        type boolean;
        description
          "SPAN Diagnostics Interface exists for this path";
      }
      leaf span-diag-interface {
        type xr:Interface-name;
        description "SPAN Diagnostics Interface for this path";
      }
      leaf has-subscriber-parent-interface {
        type boolean;
        description
          "Subscriber Parent Interface exists for this
          path";
      }
      leaf subscriber-parent-interface {
        type xr:Interface-name;
        description "Subscriber Parent Interface for this path";
      }
      leaf interface-index-present {
        type boolean;
        description "Interface Index present";
      }
      leaf interface-index-attribute {
        type uint32;
        description "Interface Index attribute";
      }
      leaf number-of-srv6-sids {
        type uint16;
        description "Number of SRv6 Segment Identifiers";
      }
      leaf has-srv6-transit-function {
        type boolean;
        description
          "Path has some SRv6 transit function associated";
      }
      leaf srv6-transit-function {
        type string;
        description
          "String representation of SRv6 transit function";
      }
      list remote-backup-addr {
        max-elements "2";

        description "Remote backup node address";
          leaf entry {
                      xr:event-telemetry "Subscribe Telemetry Event";

                      type Ipv4-rib-edm-addr;

                      description "Remote backup node address";
          }
      }
      list labelstk {
        description "Outgoing label stack for this path";
          leaf entry {
                      xr:event-telemetry "Subscribe Telemetry Event";

                      type uint32;

                      description "Outgoing label stack for this path";
          }
      }

      list next-next-hop {
        description "List of Next Next Hops";
        uses RIB-EDM-NNH;
      }

      list srv6-sid {
        description "List of SRv6 Segment Identifiers";
        uses RIB-EDM-SRV6-SID;
      }
    }
  }

  grouping IPV4-RIB-EDM-ROUTE {
    description
      "Information of a rib route head and rib proto
      route";

    container route-path {
      description "Path(s) of the route";
      uses IPV4-RIB-EDM-PATH;
    }
    leaf prefix {
      type Ipv4-rib-edm-addr;
      description "Route prefix";
    }
    leaf prefix-length-xr {
      type uint8;
      description "Length of prefix";
    }
    leaf route-version {
      type uint32;
      description "Route version";
    }
    leaf protocol-id {
      xr:event-telemetry "Subscribe Telemetry Event";
      type uint32;
      description "Protocol advertising the route";
    }
    leaf protocol-name {
      xr:event-telemetry "Subscribe Telemetry Event";
      type string;
      description " Name of Protocol";
    }
    leaf instance {
      type string;
      description "Instance name";
    }
    leaf client-id {
      type uint32;
      description "Client adding the route to RIB";
    }
    leaf route-type {
      xr:event-telemetry "Subscribe Telemetry Event";
      type uint16;
      description "Route type";
    }
    leaf priority {
      xr:event-telemetry "Subscribe Telemetry Event";
      type uint8;
      description "Route priority";
    }
    leaf svd-type {
      type uint8;
      description "SVD Type of route";
    }
    leaf flags {
      xr:event-telemetry "Subscribe Telemetry Event";
      type uint32;
      description "Route flags";
    }
    leaf extended-flags {
      xr:event-telemetry "Subscribe Telemetry Event";
      type uint64;
      description "Extended Route flags";
    }
    leaf tag {
      xr:event-telemetry "Subscribe Telemetry Event";
      type uint32;
      description "Opaque proto specific info";
    }
    leaf distance {
      xr:event-telemetry "Subscribe Telemetry Event";
      type uint32;
      description "Distance of the route";
    }
    leaf diversion-distance {
      type uint32;
      description "Diversion distance of the route";
    }
    leaf metric {
      xr:event-telemetry "Subscribe Telemetry Event";
      type uint32;
      description "Route metric";
    }
    leaf paths-count {
      xr:event-telemetry "Subscribe Telemetry Event";
      type uint32;
      description "Number of paths";
    }
    leaf attribute-identity {
      type uint32;
      description "BGP Attribute ID";
    }
    leaf traffic-index {
      type uint8;
      description "BGP Traffic Index";
    }
    leaf route-precedence {
      xr:event-telemetry "Subscribe Telemetry Event";
      type uint8;
      description "Route ip precedence";
    }
    leaf qos-group {
      xr:event-telemetry "Subscribe Telemetry Event";
      type uint8;
      description "Route qos group";
    }
    leaf flow-tag {
      xr:event-telemetry "Subscribe Telemetry Event";
      type uint8;
      description "Flow tag";
    }
    leaf fwd-class {
      xr:event-telemetry "Subscribe Telemetry Event";
      type uint8;
      description "Forward Class";
    }
    leaf pic-count {
      type uint8;
      description "Number of pic paths in this route";
    }
    leaf active {
      type boolean;
      description "Is the route active or backup";
    }
    leaf diversion {
      type boolean;
      description "Route has a diversion path";
    }
    leaf diversion-proto-name {
      type string;
      description "Diversion route protocol name";
    }
    leaf route-age {
      type uint32;
      units "second";
      description "Age of route (seconds)";
    }
    leaf route-label {
      type uint32;
      description "Local label of the route";
    }
    leaf version {
      type uint32;
      description "Route Version";
    }
    leaf tbl-version {
      type uint64;
      description "Table Version";
    }
    leaf route-modify-time {
      type uint64;
      units "nanosecond";
      description "Route modification time(nanoseconds)";
    }
    leaf has-srv6-function {
      type boolean;
      description "Route has some SRv6 function associated";
    }
    leaf srv6-function {
      type string;
      description "String representation of SRv6 function";
    }
  }
}
