submodule Cisco-IOS-XR-ethernet-lldp-oper-sub2 {

  belongs-to Cisco-IOS-XR-ethernet-lldp-oper {
    prefix Cisco-IOS-XR-ethernet-lldp-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ethernet-lldp package operational data.

     Copyright (c) 2013-2018 by Cisco Systems, Inc.
     All rights reserved.";

  revision "2015-11-09" {
    description
      "IOS XR 6.0 revision.";
  }


  grouping LLDP-MGR-GLOBAL-INFO {
    description "LLDP global info";
    leaf chassis-id {
      type string;
      description "Chassis identifier";
    }
    leaf chassis-id-sub-type {
      type uint8;
      description "Chassis ID sub type";
    }
    leaf system-name {
      type string;
      description "System Name";
    }
    leaf timer {
      type uint32;
      description "Rate at which LLDP packets re sent (in sec)";
    }
    leaf hold-time {
      type uint32;
      description
        "Length  of time  (in sec)that receiver must keep
        thispacket";
    }
    leaf re-init {
      type uint32;
      description
        "Delay (in sec) for LLDPinitialization on
        anyinterface";
    }
  }
}
