submodule Cisco-IOS-XR-l2vpn-oper-sub3 {

  belongs-to Cisco-IOS-XR-l2vpn-oper {
    prefix Cisco-IOS-XR-l2vpn-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR l2vpn package operational data.

     Copyright (c) 2013-2018 by Cisco Systems, Inc.
     All rights reserved.";

  revision "2019-03-30" {
    description
      "- Rename l2fib-mac-learning-mac* interface-handle to interface-name - Rename l2fib-pw-group tunnel-if-handle to tunnel-interface-name - Convert several array from leaf-list to list syntax. - Implement range datatypes for all L2FIB integers.";
  }

  revision "2018-08-01" {
    description
      "Removed empty groupings.";
  }

  revision "2017-09-07" {
    description
      "Fixed type translation error.";
  }

  revision "2017-06-26" {
    description
      "Change identifiers to be more readable.";
  }

  revision "2017-05-01" {
    description
      "Fixing backward compatibility error in module.";
  }

  revision "2015-11-09" {
    description
      "IOS XR 6.0 revision.";
  }

  typedef L2vpn-pwhe-iflist-rep-status {
    type enumeration {
      enum invalid {
        value 0;
        description "Invalid";
      }
      enum pending {
        value 1;
        description "Pending";
      }
      enum success {
        value 2;
        description "Success";
      }
      enum failed {
        value 3;
        description "Failed";
      }
      enum not-supported {
        value 4;
        description "Not supported";
      }
    }
    description "Interface list replication status";
  }
  typedef L2vpn-pwhe-intf {
    type enumeration {
      enum pseudowire-ether {
        value 0;
        description "PW Ether";
      }
      enum pseudowire-iw {
        value 1;
        description "PW IW";
      }
    }
    description "Interface type";
  }
  typedef Pwhe-port-im-state {
    type enumeration {
      enum unknown {
        value 0;
        description "Unknown";
      }
      enum down {
        value 1;
        description "Down";
      }
      enum up {
        value 2;
        description "Up";
      }
    }
    description "Pseudowire headend port states";
  }

  grouping L2VPN-PWHE-SUMMARY {
    description "Pseudowire headend summary";
    leaf interfaces {
      type uint32;
      description "Number of PW-HE interfaces";
    }
    leaf up-interfaces {
      type uint32;
      description "Number of interfaces up";
    }
    leaf down-interfaces {
      type uint32;
      description "Number of interfaces down";
    }
    leaf admin-down-interfaces {
      type uint32;
      description "Number of interfaces admin down";
    }
    leaf psuedowire-ether-interfaces {
      type uint32;
      description "Number of PW-Ether interfaces";
    }
    leaf up-psuedowire-ether-interfaces {
      type uint32;
      description "Number of PW-Ether interfaces up";
    }
    leaf down-pseudowire-ether-interfaces {
      type uint32;
      description "Number of PW-Ether interfaces down";
    }
    leaf admin-down-pseudowire-ether-interfaces {
      type uint32;
      description "Number of PW-Ether interfaces admin down";
    }
    leaf pseudowire-iw-interfaces {
      type uint32;
      description "Number of PW-IW interfaces";
    }
    leaf up-pseudowire-iw-interfaces {
      type uint32;
      description "Number of PW-IW interfaces up";
    }
    leaf down-pseudowire-iw-interfaces {
      type uint32;
      description "Number of PW-IW interfaces down";
    }
    leaf admin-down-pseudowire-iw-interfaces {
      type uint32;
      description "Number of PW-IW interfaces admin down";
    }
  }

  grouping L2VPN-PWHE-GENERIC-IFLIST-INTF {
    description "Pseudowire headend generic interface list";
    leaf interface-name {
      type xr:Interface-name;
      description "Interface name";
    }
    leaf bundle-interface-name {
      type xr:Interface-name;
      description "Bundle Interface name";
    }
    leaf interface-state {
      type Pwhe-port-im-state;
      description "Interface Status";
    }
    leaf replicate-state {
      type L2vpn-pwhe-iflist-rep-status;
      description "Replication status";
    }
    leaf misconfigured {
      type boolean;
      description "Interface misconfigured";
    }
  }

  grouping L2VPN-PWHE-GENERIC-IFLIST {
    description "Pseudowire headend generic-interface-list details";
    leaf generic-interface-list-name {
      type string;
      description "Generic interface list name";
    }
    leaf id {
      type uint32;
      description "Generic interface list ID";
    }

    list interface-detail {
      description "Interfaces";
      uses L2VPN-PWHE-GENERIC-IFLIST-INTF;
    }
  }

  grouping L2VPN-PWHE-MAC-ADDR {
    description "MAC Address";
    leaf mac-address {
      type yang:mac-address;
      description "MAC Address";
    }
  }

  grouping L2VPN-L2-ADDR-PWHE-DETAIL {
    description "L2VPN L2 ADDR PWHE DETAIL";

    container mac-address {
      when "../interface-type = 'pseudowire-ether'" {
        description "../InterfaceType = 'PseudowireEther'";
      }
      description "MAC address";
      uses L2VPN-PWHE-MAC-ADDR;
    }
    leaf interface-type {
      type L2vpn-pwhe-intf;
      description "InterfaceType";
    }
  }

  grouping L2VPN-PWHE-DETAIL {
    description "Pseudowire headend detail";

    container l2-address {
      description "Layer2 Address";
      uses L2VPN-L2-ADDR-PWHE-DETAIL;
    }

    container generic-interface-list {
      description "Generic Interface List";
      uses L2VPN-PWHE-GENERIC-IFLIST;
    }
    leaf interface-state {
      type Pwhe-port-im-state;
      description "Interface Status";
    }
    leaf admin-state {
      type Pwhe-port-im-state;
      description "Interface Admin Status";
    }
    leaf mtu {
      type uint32;
      description "MTU";
    }
    leaf bandwidth {
      type uint32;
      units "kbit/s";
      description "Bandwidth (Kbps)";
    }
    leaf label {
      type uint32;
      description "Label";
    }
    leaf l2-overhead {
      type uint32;
      description "L2 Overhead";
    }
    leaf vctype {
      type uint32;
      description "VC Type";
    }
    leaf control-word {
      type boolean;
      description "Control Word";
    }
  }
}
