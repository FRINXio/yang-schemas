module IPV6-TC {
  namespace "http://tail-f.com/ns/mibs/IPV6-TC/199812010000Z";
  prefix IPV6_TC;
  tailf:id "";
  tailf:snmp-mib-module-name "IPV6-TC";

  import ietf-inet-types {
    prefix inet;
  }
  import tailf-common {
    prefix tailf;
  }

  revision 1998-12-01 {
    description
      "";
  }

  typedef Ipv6Address {
    type inet:ipv6-address;
  }

  typedef Ipv6AddressPrefix {
    type inet:ipv6-prefix;
  }

  typedef Ipv6AddressIfIdentifier {
    type string {
      pattern "(((([0-9A-Fa-f]{2}):){0,7}([0-9A-Fa-f]{2}))){0,1}";
    }
  }

  typedef Ipv6IfIndex {
    type int32 {
      range "1 .. 2147483647";
    }
  }

  typedef Ipv6IfIndexOrZero {
    type int32 {
      range "0 .. 2147483647";
    }
  }
}
