module Cisco-IOS-XR-asr9k-fia-cfg {

  /*** NAMESPACE / PREFIX DEFINITION ***/

  namespace "http://cisco.com/ns/yang/Cisco-IOS-XR-asr9k-fia-cfg";


  prefix "asr9k-fia-cfg";

  /*** LINKAGE (IMPORTS / INCLUDES) ***/

  import Cisco-IOS-XR-config-mda-cfg { prefix "node"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-fia package configuration.

     This module contains definitions
     for the following management objects:
       fabric-fia-config: Configure Global Fabric Fia Settings

     This YANG module augments the
       Cisco-IOS-XR-config-mda-cfg
     module with configuration data.

     Copyright (c) 2013-2018 by Cisco Systems, Inc.
     All rights reserved.";

  revision "2017-08-17" {
    description
      "IOS XR 6.4.1 revision.";
  }

  revision "2015-11-09" {
    description
      "IOS XR 6.0 revision.";
  }


  grouping NODE-CFG {
    description "active/preconfigured nodes configuration";

    container fia-buffer-profile-cfg {
      description "fia buffer profile cfg";
      leaf xl {
        type boolean;
        description "Enable to use Extra large Buffer profile";
      }
    }

    container fia-vqi-shaper-cfg {
      description "fia vqi shaper cfg";
      leaf enhance {
        type boolean;
        description "Enable to use Enhanced VQI shaper limit";
      }
    }

    container port-queue-remaps {
      description "port queue remaps";

      list port-queue-remap {
        key "port";
        description "Front panel port number";
        leaf fabric-queue {
          type uint32 {
            range "0..19";
          }
          description "queue number <0-19>";
        }
        leaf port {
          type uint32 {
            range "0..47";
          }
          description "port number <10,11,22,23 34,35,46,47>";
        }
      }
    }
  }

  container fabric-fia-config {
    description "Configure Global Fabric Fia Settings";

    container fia-intf-policer {
      description "FIA interface rate-limiter on 7-Fabric LC";
      leaf disable {
        type boolean;
        description "disable FIA interface policer ";
      }
    }
  }

  augment "/node:active-nodes/node:active-node" {
    uses NODE-CFG;
    description "This augment extends active nodes configuration";
  }

  augment "/node:preconfigured-nodes/node:preconfigured-node" {
    uses NODE-CFG;
    description
      "This augment extends preconfigured nodes
      configuration";
  }
}
