module Cisco-IOS-XR-ipv4-autorp-oper {

  /*** NAMESPACE / PREFIX DEFINITION ***/

  namespace "http://cisco.com/ns/yang/Cisco-IOS-XR-ipv4-autorp-oper";


  prefix "ipv4-autorp-oper";

  /*** LINKAGE (IMPORTS / INCLUDES) ***/

  import ietf-inet-types { prefix "inet"; }

  import Cisco-IOS-XR-types { prefix "xr"; }

  import Cisco-IOS-XR-ipv4-autorp-datatypes { prefix "dt1"; }

  include Cisco-IOS-XR-ipv4-autorp-oper-sub2 {
    revision-date 2015-11-09;
  }

  include Cisco-IOS-XR-ipv4-autorp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-autorp package operational data.

     This module contains definitions
     for the following management objects:
       auto-rp: AutoRP operational data

     Copyright (c) 2013-2018 by Cisco Systems, Inc.
     All rights reserved.";

  revision "2015-11-09" {
    description
      "IOS XR 6.0 revision.";
  }


  grouping MAPPING-AGENT {
    description "Common node of active, standby";

    container mapping-agent {
      description "AutoRP Mapping Agent Table";

      container traffic {
        description "AutoRP Mapping Agent Traffic Counters";
        uses AUTORP-MAP-TRAFFIC-BAG;
      }

      container rp-addresses {
        description "AutoRP Mapping Agent Table Entries";

        list rp-address {
          key "rp-address";
          description "AutoRP Mapping Agent Entry";
          leaf rp-address {
            type inet:ipv4-address-no-zone;
            description "RP Address";
          }
          uses AUTORP-MAP-RP-BAG;
        }
      }

      container summary {
        description "AutoRP Mapping Agent Summary Information";
        uses AUTORP-MAP-SUMMARY-BAG;
      }
    }
  }

  grouping CANDIDATE-RP {
    description "Common node of active, standby";

    container candidate-rp {
      description "AutoRP Candidate RP";

      container traffic {
        description "AutoRP Candidate Traffic Counters";
        uses AUTORP-CRP-TRAFFIC-BAG;
      }

      container rps {
        description "AutoRP Candidate RP Table";

        list rp {
          description "AutoRP Candidate RP Entry";
          leaf interface-name {
            type xr:Interface-name;
            description "Interface Name";
          }
          leaf protocol-mode {
            type dt1:Auto-rp-protocol-mode;
            description "Protocol Mode";
          }
          uses AUTORP-CRP-BAG;
        }
      }
    }
  }

  container auto-rp {
    config false;
    description "AutoRP operational data";

    container standby {
      description "Standby Process";
      uses CANDIDATE-RP;
      uses MAPPING-AGENT;
    }

    container active {
      description "Active Process";
      uses CANDIDATE-RP;
      uses MAPPING-AGENT;
    }
  }
}
