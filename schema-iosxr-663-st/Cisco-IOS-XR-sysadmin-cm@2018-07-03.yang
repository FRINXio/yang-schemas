module Cisco-IOS-XR-sysadmin-cm {
  namespace "http://www.cisco.com/ns/yang/Cisco-IOS-XR-sysadmin-cm";
  prefix cmh;
  import tailf-common {
    prefix tailf;
  }
  import tailf-xsd-types {
    prefix xs;
  }
  import Cisco-IOS-XR-sysadmin-types {
    prefix calvados;
  }
  import ietf-yang-types {
    prefix yang;
  }
  import ietf-inet-types {
    prefix inet;
  }
  import Cisco-IOS-XR-sysadmin-show-trace-cm {
    prefix cm;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

The System Admin Manager (CM)

Copyright(c) 2010-2017 by Cisco Systems, Inc.
All rights reserved.

    Copyright (c) 2012-2018 by Cisco Systems, Inc.
     All rights reserved.";
  revision 2018-07-03 {
    description
      "Suppress Tail-f warnings in ConfD 6.4.5";
  }


  typedef area_type {
    type enumeration {
      enum "SYSTEM";
      enum "RACK";
      enum "UNKNOWN";
    }
  }

  typedef hex8ValueType {
    type xs:hexBinary {
    }
  }

  grouping nodeInfoGroup {
    container summary {
      description
        "System Admin Manager Node Inventory. All accesses are 
         read-only. CLI show command looks like show node-inventory
         location <location>";
      config false;
      list node_locations {
        key "node_location";
        leaf node_location {
          type calvados:location-id;
        }
        list nodei {
          key "ip_address";
          uses nodeInfoSummary;
        }
      }
    }
    container detail {
      description
        "System Admin Manager Node Inventory. All accesses are 
         read-only. CLI show command looks like show node-inventory
         location <location>";
      config false;
      list node_locations {
        key "node_location";
        leaf node_location {
          type calvados:location-id;
        }
        list nodei {
          key "ip_address";
          uses nodeInfoSummary;
          uses nodeInfoDetail;
        }
      }
    }
  }

  grouping nodeInfoSummary {
    description
      "All the parameters needed to describe a node as
       represented in CM.";
    leaf type {
      type string;
      description
        "Node Type";
    }
    leaf ip_address {
      type inet:ip-address;
      description
        "IP address of the node";
    }
    leaf mac_address {
      type yang:mac-address;
      description
        "Node MAC";
    }
    leaf card_serial {
      type string;
      description
        "Card serial# the node belongs to";
    }
    leaf nti {
      type uint32;
      description
        "Node NTI";
    }
  }

  grouping nodeInfoDetail {
    description
      "All the parameters needed to describe a node as
       represented in CM.";
    leaf restart {
      type boolean;
      description
        "Node in Restart";
    }
    leaf data {
      type hex8ValueType;
      description
        "Node Data";
    }
    leaf sdr {
      type string;
      description
        "SDR Name the node belongs to";
    }
  }

  grouping cardInfo {
    description
      "All the parameters needed to describe a card as
       represented in CM.";
    leaf node_id {
      type string;
      description
        "Node name";
    }
    leaf card_type {
      type string;
      description
        "Card Type";
    }
    leaf hw_state {
      type string;
      description
        "Card State";
    }
    leaf sw_state {
      type string;
      description
        "Card Software State";
    }
    leaf slot {
      type uint32;
      description
        "Card Slot Number";
    }
    leaf card_serial {
      type string;
      description
        "Serial Number of the Card";
    }
    leaf cti {
      type uint32;
      description
        "Card CTI";
    }
  }

  grouping rackInfo {
    description
      "All the parameters needed to describe a rack as
       represented in CM.";
    leaf rack_number {
      type int32;
      description
        "Rack Number";
    }
    leaf rack_serial {
      type string;
      description
        "Serial Number of the Rack";
    }
    leaf rack_state {
      type int32;
      description
        "Rack State";
    }
  }

  grouping serviceInfo {
    description
      "All the parameters needed to describe a service as
       represented in CM.";
    leaf svc_name {
      type string;
      description
        "Service Name";
    }
    leaf placement_first {
      type string;
      description
        "Serial Number of the first card selected";
    }
    leaf nodeid_first {
      type string;
      description
        "Node id of the first card selected";
    }
    leaf placement_second {
      type string;
      description
        "Serial Number of the second card selected";
    }
    leaf nodeid_second {
      type string;
      description
        "Node id of the second card selected";
    }
    leaf svc_load {
      type uint8;
      description
        "Service Load";
    }
  }

  grouping sdrInfo {
    description
      "All the parameters needed to describe a SDR as
       represented in CM.";
    leaf sdr_id {
      type uint32;
      description
        "SDR ID";
    }
    leaf sdr_name {
      type string;
      description
        "SDR NAME";
    }
    leaf sdr_vlan_baseid {
      type uint8;
      description
        "SDR VLAN ID";
    }
    leaf sdr_version {
      type uint64;
      description
        "SDR Image Version";
    }
  }

  grouping ldrInfo {
    description
      "All the parameters needed to describe leader statistics.";
    leaf syslead {
      type string;
      description
        "Primary System Leader";
    }
    leaf bkup_syslead {
      type string;
      description
        "Backup System Leader";
    }
    leaf racklead {
      type string;
      description
        "Primary Rack Leader";
    }
    leaf bkup_racklead {
      type string;
      description
        "Backup Rack Leader";
    }
    leaf l1_dis {
      type string;
      description
        "L1 DIS";
    }
    leaf l2_dis {
      type string;
      description
        "L2 DIS";
    }
  }

  grouping nbrInfo {
    description
      "All the parameters needed to describe a topology neighbor";
    leaf nbr_system_id {
      type string;
      description
        "Neighbor System ID";
    }
    leaf nbr_area_type {
      type string;
      description
        "Neighbor Area Type";
    }
    leaf nbr_interface {
      type string;
      description
        "Adjacency Interface";
    }
    leaf nbr_state {
      type string;
      description
        "Neighbor State";
    }
    leaf nbr_holdtime {
      type uint64;
      description
        "Neighbor Hold Time";
    }
    leaf nbr_uptime {
      type xs:duration;
      description
        "Neighbor Up Time";
    }
  }

  grouping lspdbInfo {
    description
      "All the parameters needed to describe a lsps from lspdb";
    leaf lsp_id {
      type string;
      description
        "LSP System ID";
    }
    leaf lsp_area_type {
      type area_type;
      description
        "LSP Area Type";
    }
    leaf lsp_sequence {
      type uint32;
      description
        "LSP sequence number";
    }
    leaf lsp_core {
      type string;
      description
        "LSP core data bits";
    }
    leaf-list lsp_tlvs {
      type string;
      description
        "LSP TLV data";
    }
  }
  container node-inventory {
    description
      "System Admin Manager Node Inventory. All accesses are 
       read-only. CLI show command looks like show node-inventory
       location <location>";
    config false;
    uses nodeInfoGroup;
  }
  container card-inventory {
    description
      "System Admin Manager Card Inventory. All accesses are 
       read-only. CLI show command looks like show card-inventory
       location <location>";
    config false;
    list card_locations {
      key "card_location";
      leaf card_location {
        type calvados:location-id;
      }
      list cardi {
        key "card_serial";
        uses cardInfo;
      }
    }
  }
  container rack-inventory {
    description
      "System Admin Manager Rack Inventory";
    config false;
    list rack_locations {
      key "rack_location";
      leaf rack_location {
        type calvados:location-id;
      }
      list racki {
        key "rack_serial";
        uses rackInfo;
      }
    }
  }
  container system-service-inventory {
    description
      "System Admin Manager System Services Inventory";
    config false;
    list ssvc_locations {
      key "ssvc_location";
      leaf ssvc_location {
        type calvados:location-id;
      }
      list ssvci {
        key "svc_name";
        uses serviceInfo;
      }
    }
  }
  container rack-service-inventory {
    description
      "System Admin Manager Rack Services Inventory";
    config false;
    list rsvc_locations {
      key "rsvc_location";
      leaf rsvc_location {
        type calvados:location-id;
      }
      list rsvci {
        key "svc_name";
        uses serviceInfo;
      }
    }
  }
  container sdr-inventory {
    description
      "System Admin Manager SDR Inventory";
    config false;
    list sdr_locations {
      key "sdr_location";
      leaf sdr_location {
        type calvados:location-id;
      }
      list sdri {
        key "sdr_name";
        uses sdrInfo;
      }
    }
  }
  container leader-statistics {
    description
      "System Admin Manager Leader Statistics";
    config false;
    list ldr_locations {
      key "ldr_location";
      leaf ldr_location {
        type calvados:location-id;
      }
      uses ldrInfo;
    }
  }
  container topology-neighbors {
    description
      "System Admin Manager Neighbors of a location";
    config false;
    list nbr_locations {
      key "nbr_location";
      leaf nbr_location {
        type calvados:location-id;
      }
      list nbri {
        key "nbr_system_id nbr_area_type";
        uses nbrInfo;
      }
    }
  }
  container placement {
    tailf:action "reoptimize" {
      description
        "Reoptimize Placement for System Scope Services";
    }
  }
  augment "/cm:cm" {
    container lsp {
      description
        "System Admin Manager lspdb of a location";
      config false;
      list lspdb_locations {
        key "lspdb_location";
        leaf lspdb_location {
          type calvados:location-id;
        }
        list lspdbi {
          key "lsp_id lsp_area_type";
          uses lspdbInfo;
        }
      }
    }
  }
}
