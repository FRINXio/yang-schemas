submodule Cisco-IOS-XR-mediasvr-linux-oper-sub1 {

  belongs-to Cisco-IOS-XR-mediasvr-linux-oper {
    prefix Cisco-IOS-XR-mediasvr-linux-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mediasvr-linux package operational data.

     Copyright (c) 2013-2018 by Cisco Systems, Inc.
     All rights reserved.";

  revision "2015-11-09" {
    description
      "IOS XR 6.0 revision.";
  }


  grouping SHOW-MEDIA-EDM-STRING {
    description "SHOW MEDIA EDM STRING";
    leaf show-output {
      type string;
      description "string output";
    }
  }
}
