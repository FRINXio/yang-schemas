submodule Cisco-IOS-XR-fib-common-oper-sub5 {

  belongs-to Cisco-IOS-XR-fib-common-oper {
    prefix Cisco-IOS-XR-fib-common-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2018 by Cisco Systems, Inc.
     All rights reserved.";

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }


  grouping FIB-GLOBAL-SUMMARY-OBJ-HISTORY {
    description "FIB Global summary object history";
    leaf count {
      type uint32;
      description "Placeholder for obj history counts";
    }
  }

  grouping FIB-GLOBAL-SUMMARY-OBJ-HISTORY-PROTO {
    description "FIB GLOBAL SUMMARY OBJ HISTORY PROTO";

    container base-object {
      description "Base object";
      uses FIB-GLOBAL-BASE-ST;
    }

    container object-history {
      description "Obj History";
      uses FIB-GLOBAL-SUMMARY-OBJ-HISTORY;
    }
  }

  grouping FIB-GLOBAL-SUMMARY-HEALTH {
    description "FIB Global summary health";
    leaf is-retry-db-empty {
      type boolean;
      description "Is the retry db empty?";
    }
  }

  grouping FIB-GLOBAL-BASE-ST {
    description "FIB Global Base st";
    leaf protocol {
      type uint32;
      description "protocol";
    }
  }

  grouping FIB-GLOBAL-SUMMARY {
    description "FIB Global summary";

    container base-object {
      description "Base object";
      uses FIB-GLOBAL-BASE-ST;
    }

    container summary-counts {
      description "Global Summary counts";
      uses FIB-GLOBAL-SUMMARY-COUNTS;
    }

    container health {
      description "Global summary health";
      uses FIB-GLOBAL-SUMMARY-HEALTH;
    }
  }

  grouping FIB-GLOBAL-SUMMARY-PROTO {
    description "FIB GLOBAL SUMMARY PROTO";

    container common-info {
      description "Common Info";
      uses FIB-GLOBAL-SUMMARY-COMMON-INFO;
    }

    container summary {
      description "Global summary";
      uses FIB-GLOBAL-SUMMARY;
    }
  }

  grouping FIB-GLOBAL-NUM-OBJECTS-ST {
    description "FIB Global summary num retries";
    leaf object-type {
      type string {
        length "0..30";
      }
      description "object";
    }
    leaf num-objects {
      type uint32;
      description "number of elements for this obj type";
    }
  }

  grouping FIB-GLOBAL-NUM-RETRIES-ST {
    description "FIB Global summary num retries";
    leaf retry-object-type {
      type string {
        length "0..30";
      }
      description "retry object";
    }
    leaf num-retries {
      type uint64;
      description
        "number of elements for this obj type in retry db";
    }
  }

  grouping FIB-GLOBAL-SUMMARY-COUNTS {
    description "FIB Global summary counts";
    leaf num-retry-timeouts {
      type uint64;
      description "number of retry timeouts";
    }
    leaf num-retry-ojbects {
      type uint32;
      description "number of elements in retry db";
    }

    list array-number-of-retry {
      description "number of objects in retry db";
      uses FIB-GLOBAL-NUM-RETRIES-ST;
    }

    list array-number-of-object {
      description "total number of objects";
      uses FIB-GLOBAL-NUM-OBJECTS-ST;
    }
  }

  grouping FIB-GLOBAL-SUMMARY-COMMON-INFO {
    description "FIB Global summary common";
    leaf count {
      type uint32;
      description "Placeholder for common info counts";
    }
  }

  grouping FIB-GLOBAL-SUMMARY-TOTAL {
    description "FIB GLOBAL SUMMARY TOTAL";

    container common-info {
      description "Common info";
      uses FIB-GLOBAL-SUMMARY-COMMON-INFO;
    }

    container total-counters {
      description "Aggregate counters of all protocols";
      uses FIB-GLOBAL-SUMMARY-COUNTS;
    }
  }
}
