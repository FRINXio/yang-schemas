submodule Cisco-IOS-XR-icpe-infra-oper-sub12 {

  belongs-to Cisco-IOS-XR-icpe-infra-oper {
    prefix Cisco-IOS-XR-icpe-infra-oper;
  }

  /*** LINKAGE (IMPORTS / INCLUDES) ***/

  include Cisco-IOS-XR-icpe-infra-oper-sub4 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2018 by Cisco Systems, Inc.
     All rights reserved.";

  revision "2015-11-09" {
    description
      "IOS XR 6.0 revision.";
  }


  grouping ICPE-RELOAD-OP-STATUS-DETAIL {
    description "Detailed breakdown of reload status";
    leaf operation-id-xr {
      type uint32;
      description "Operation ID";
    }
    leaf satellite-range {
      type Xr-yang-string;
      description "Satellite range";
    }
    leaf-list sats-not-initiated {
      type uint16;
      description "Sats not initiated";
    }
    leaf-list sats-reloading {
      type uint16;
      description "Sats reloading";
    }
    leaf-list sats-reloaded {
      type uint16;
      description "Sats reloaded";
    }
    leaf-list sats-reload-failed {
      type uint16;
      description "Sats reload failed";
    }
  }
}
