module Cisco-IOS-XR-ppp-ma-ssrp-cfg {

  /*** NAMESPACE / PREFIX DEFINITION ***/

  namespace "http://cisco.com/ns/yang/Cisco-IOS-XR-ppp-ma-ssrp-cfg";


  prefix "ppp-ma-ssrp-cfg";

  /*** LINKAGE (IMPORTS / INCLUDES) ***/

  import ietf-inet-types { prefix "inet"; }

  import Cisco-IOS-XR-types { prefix "xr"; }

  import Cisco-IOS-XR-config-mda-cfg { prefix "a1"; }

  import Cisco-IOS-XR-ifmgr-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ppp-ma-ssrp package configuration.

     This module contains definitions
     for the following management objects:
       ssrp: Shared plane SSRP configuration data

     This YANG module augments the
       Cisco-IOS-XR-config-mda-cfg,
       Cisco-IOS-XR-ifmgr-cfg
     modules with configuration data.

     Copyright (c) 2013-2018 by Cisco Systems, Inc.
     All rights reserved.";

  revision "2015-11-09" {
    description
      "IOS XR 6.0 revision.";
  }


  container ssrp {
    description "Shared plane SSRP configuration data";

    container profiles {
      description "Table of SSRP Profiles";

      list profile {
        key "name";
        description "SSRP Profile configuration";
        leaf max-hops {
          type uint32 {
            range "1..255";
          }
          description
            "This specifies the maximum number of hops for
            packets on the SSO channel";
        }
        leaf peer-ipv4-address {
          type inet:ipv4-address-no-zone;
          description
            "This specifies the remote end's IPv4-address
            for the SSO channel";
        }
        leaf name {
          type xr:Cisco-ios-xr-string;
          description "The name of the profile";
        }
      }
    }
  }

  augment "/a2:interface-configurations/a2:interface-configuration" {

    container ssrp-session {
      description "SSRP Config";

      container group-id {
        description "This specifies the SSRP group and session-id";
        leaf group {
          type uint32 {
            range "1..65535";
          }
          description "SSRP Group-ID";
        }
        leaf id {
          type uint32 {
            range "1..4294967295";
          }
          description "SSRP Session-ID";
        }
      }
    }
    description
      "This augment extends the configuration data of
      'Cisco-IOS-XR-ifmgr-cfg'";
  }

  augment "/a1:active-nodes/a1:active-node" {

    container ssrp-group {
      description "Per-node SSRP configuration data";

      container groups {
        description "Table of SSRP Group configuration";

        list group {
          key "group-id";
          description "SSRP Group configuration";
          leaf profile {
            type string;
            description
              "This specifies the SSRP profile to use for
              this group";
          }
          leaf group-id {
            type uint32 {
              range "1..65535";
            }
            description "The identifier for this group";
          }
        }
      }
    }
    description
      "This augment extends the configuration data of
      'Cisco-IOS-XR-config-mda-cfg'";
  }
}
