submodule Cisco-IOS-XR-mpls-te-oper-sub3 {

  belongs-to Cisco-IOS-XR-mpls-te-oper {
    prefix Cisco-IOS-XR-mpls-te-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2018 by Cisco Systems, Inc.
     All rights reserved.";

  revision "2018-08-01" {
    description
      "Removed empty groupings.";
  }

  revision "2017-09-07" {
    description
      "Fixed type translation error.";
  }

  revision "2017-05-01" {
    description
      "Fixing backward compatibility error in module.";
  }

  revision "2015-11-09" {
    description
      "IOS XR 6.0 revision.";
  }

  typedef Tp-link-state {
    type enumeration {
      enum down {
        description "Deprecated";
      }
      enum admin-down {
        description "Deprecated";
      }
      enum up {
        description "Deprecated";
      }
      enum unknown {
        description "Deprecated";
      }
    }
    description "Deprecated";
  }

  grouping MPLS-TE-TP-LINK-INFO {
    description "Deprecated";
    leaf link-id {
      type uint32;
      description "Deprecated";
    }
    leaf interface {
      type string;
      description "Deprecated";
    }
    leaf next-hop-address {
      type inet:ipv4-address;
      description "Deprecated";
    }
    leaf link-state {
      type Tp-link-state;
      description "Deprecated";
    }
    leaf available-bandwidth {
      type uint64;
      description "Deprecated";
    }
  }

  grouping MPLS-TE-TP-LINK-SUMMARY-INFO {
    description "Deprecated";
    leaf links {
      type uint32;
      description "Deprecated";
    }
  }

  grouping MPLS-TE-TP-DETAIL-LINK-INFO {
    description "Deprecated";
    leaf link-id {
      type uint32;
      description "Deprecated";
    }
    leaf interface {
      type string;
      description "Deprecated";
    }
    leaf next-hop-address {
      type inet:ipv4-address;
      description "Deprecated";
    }
    leaf link-state {
      type Tp-link-state;
      description "Deprecated";
    }
    leaf ls-ps {
      type uint32;
      description "Deprecated";
    }
    leaf reserved-bandwidth {
      type uint64;
      description "Deprecated";
    }
    leaf available-bandwidth {
      type uint64;
      description "Deprecated";
    }
    leaf unsupported-linecard {
      type boolean;
      description "Deprecated";
    }
  }
}
