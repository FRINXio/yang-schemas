module Cisco-IOS-XR-lib-keychain-act {

    namespace "http://cisco.com/ns/yang/Cisco-IOS-XR-lib-keychain-act";
    
    prefix "lib-keychain-act";
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR action package configuration.

     Copyright (c) 2017 by Cisco Systems, Inc.
     All rights reserved.";
    
    revision "2017-04-17" {
        description
            "IOS XR 6.3.1 revision.";
    }

    grouping MASTER-KEY {
        leaf old-key {
            description "key already added/key to be replaced";
            type string;
            mandatory true;
        }
        leaf new-key {
            description "New master key to be added ";
            type string;
            mandatory true;
        }
    }

    rpc master-key-add {
        description "To add a new master key";
        input {
          leaf new-key {
            description "New master key to be added";
            type string;    
          }
        }
    }

    rpc master-key-delete {
        description "Remove Master key";
    }
    
    rpc master-key-update {
        description "To update master key";
        input {
            uses MASTER-KEY;
        }
    }
 }
