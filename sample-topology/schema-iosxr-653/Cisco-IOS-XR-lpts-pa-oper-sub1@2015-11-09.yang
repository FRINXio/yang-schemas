submodule Cisco-IOS-XR-lpts-pa-oper-sub1 {

  belongs-to Cisco-IOS-XR-lpts-pa-oper {
    prefix Cisco-IOS-XR-lpts-pa-oper;
  }

  /*** LINKAGE (IMPORTS / INCLUDES) ***/

  import ietf-yang-types { prefix "yang"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lpts-pa package operational data.

     Copyright (c) 2013-2018 by Cisco Systems, Inc.
     All rights reserved.";

  revision "2015-11-09" {
    description
      "IOS XR 6.0 revision.";
  }


  grouping CLIENT-ENTRY {
    description "Client Structure";
    leaf flags {
      type uint32;
      description "Client flags";
    }
    leaf open-flags {
      type uint32;
      description "Open flags";
    }
    leaf location {
      type uint32;
      description "Rack/slot/instance";
    }
    leaf client-id {
      type uint32;
      description "Client ID";
    }
    leaf times {
      type yang:hex-string;
      description "Transaction statisitics";
    }
  }

  grouping TIMESPEC-ENTRY {
    description "Creation or Update Time";
    leaf tv-sec {
      type uint32;
      description "Time Sec";
    }
    leaf tv-nsec {
      type uint32;
      description "Time Nanosec";
    }
  }

  grouping BINDING-ENTRY {
    description "LPTS Binding Entry";

    container ctime {
      description "Creation Time";
      uses TIMESPEC-ENTRY;
    }

    container utime {
      description "Update Time";
      uses TIMESPEC-ENTRY;
    }
    leaf location {
      type uint32;
      description "Rack/slot/instance";
    }
    leaf client-id {
      type uint32;
      description "Client ID";
    }
    leaf vid {
      type uint32;
      description "VR/VRF ID";
    }
    leaf cookie {
      type uint32;
      description "Cookie";
    }
    leaf l3protocol {
      type uint32;
      description "Layer 3 protocol";
    }
    leaf l4protocol {
      type uint32;
      description "Layer 4 protocol";
    }
    leaf smask {
      type uint32;
      description "Filter operation";
    }
    leaf ifs {
      type uint32;
      description "Ifhandle";
    }
    leaf ptype {
      type uint32;
      description "Packet type";
    }
    leaf local-ip {
      type yang:hex-string;
      description "Local address";
    }
    leaf remote-ip {
      type yang:hex-string;
      description "Remote address";
    }
    leaf local-len {
      type uint8;
      description "Local address length";
    }
    leaf remote-len {
      type uint8;
      description "Remote address length";
    }
    leaf local-port {
      type uint16;
      description "Local port";
    }
    leaf remote-port {
      type uint16;
      description "Remote port";
    }
    leaf packet-misc {
      type uint32;
      description "L5 info";
    }
    leaf scope {
      type uint32;
      description "Scope";
    }
    leaf client-flags {
      type uint32;
      description "Client flags";
    }
    leaf min-ttl {
      type uint8;
      description "Minimum TTL";
    }
    leaf lazy-bindq-delay {
      type uint32;
      description " lazy binding queue delay";
    }
    leaf ptq-delay {
      type uint32;
      description " pending transactions queue delay";
    }
  }
}
