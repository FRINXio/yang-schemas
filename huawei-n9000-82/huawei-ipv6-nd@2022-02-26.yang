/*
Copyright (C) 2019-2022 Huawei Technologies Co., Ltd. All rights reserved.
*/
module huawei-ipv6-nd {
  yang-version 1;
  namespace "urn:huawei:yang:huawei-ipv6-nd";
  prefix ipv6-nd;
  import huawei-ifm {
    prefix ifm;
  }
  import huawei-pub-type {
    prefix pub-type;
  }
  import ietf-inet-types {
    prefix inet;
  }
  import huawei-extension {
    prefix ext;
  }
  import huawei-ip {
    prefix ip;
  }
  import huawei-network-instance {
    prefix ni;
  }
  import huawei-ethernet {
    prefix ethernet;
  }
  import huawei-bd {
    prefix bd;
  }
  import ietf-yang-types {
    prefix yang;
  }
  organization
    "Huawei Technologies Co., Ltd.";
  contact
    "Huawei Industrial Base
     Bantian, Longgang
     Shenzhen 518129
     People's Republic of China
     Website: http://www.huawei.com
     Email: support@huawei.com";
  description
    "ND management.";
  revision 2022-02-26 {
    description
      "Add the display nodes for anti-attack, multicast-suppress, ND dual, ND neighbors.";
    reference
      "Huawei private.";
  }
  revision 2022-01-20 {
    description
      "Add some containers for anti-attack, multicast-suppress and static neighbors.";
    reference
      "Huawei private.";
  }
  revision 2021-07-16 {
    description
      "Leaf min-interval is added under container if-property;
       leaf proxy-reply is added under container instance;
       leaf mismatch-discard is added under container instance.";
    reference
      "Huawei private.";
  }
  revision 2021-02-02 {
    description
      "Containers dns-server-addresses and dns-search-suffixs are added.";
    reference
      "Huawei private.";
  }
  revision 2020-10-15 {
    description
      "ND rate limit and drop statistics are added;
       add some leaf nodes for the if-property and the proxys container;
       add some containers for the static-neighbor and ra-property container;
       add strict-prefix-learn container.";
    reference
      "Huawei private.";
  }
  revision 2020-03-26 {
    description
      "Leaf ns-send-rate-limit is added.";
    reference
      "Huawei private.";
  }
  revision 2020-02-29 {
    description
      "Default value of stale-time is deleted.";
    reference
      "Huawei private.";
  }
  revision 2020-02-26 {
    description
      "Default value.";
    reference
      "Huawei private.";
  }
  revision 2019-12-30 {
    description
      "Init revision.";
    reference
      "Huawei private.";
  }

  typedef nd-flag {
    type enumeration {
      enum "false" {
        value 0;
        description
          "NO.";
      }
      enum "true" {
        value 1;
        description
          "YES.";
      }
    }
    description
      "Description of nd-flag.";
  }
  typedef nd-switch-state {
    type enumeration {
      enum "off" {
        value 0;
        description
          "Off.";
      }
      enum "on" {
        value 1;
        description
          "On.";
      }
    }
    description
      "The state of the switch.";
  }
  typedef nd-ngb-state {
    type enumeration {
      enum "incomplete" {
        value 0;
        description
          "Address resolution is being performed on the entry.";
      }
      enum "reachable" {
        value 1;
        description
          "The neighbor is known to have been reachable recently.";
      }
      enum "stale" {
        value 2;
        description
          "The neighbor is no longer known to be reachable, but until traffic is sent to the neighbor no attempt should be made to verify its reachability.";
      }
      enum "delay" {
        value 3;
        description
          "The neighbor is no longer known to be reachable, and traffic has recently been sent to the neighbor. Rather than probe the neighbor immediately, however,
            delay sending probes for a short while in order to give upper-layer protocols a chance to provide reachability confirmation.";
      }
      enum "probe" {
        value 4;
        description
          "The neighbor is no longer known to be reachable, and unicast neighbor solicitation probes are being sent to verify reachability.";
      }
    }
    description
        "The neighbor unreachability detection state.";
    reference
        "RFC 4861: Neighbor Discovery for IP version 6 (IPv6) Section 7.3.2";
  }
  typedef nd-route-preference {
    type enumeration {
      enum "medium" {
        value 0;
        description
          "Preference medium.";
      }
      enum "high" {
        value 1;
        description
          "Preference high.";
      }
      enum "low" {
        value 3;
        description
          "Preference low.";
      }
    }
    description
      "The RA router preference level.";
  }
  typedef nd-nb-type {
    type enumeration {
      enum "remote" {
        value 0;
        description
          "Remote pushed.";
      }
      enum "static" {
        value 1;
        description
          "Statically configured.";
      }
      enum "dynamic" {
        value 2;
        description
          "Dynamically resolved.";
      }
    }
    description
      "The origin of neighbor entry.";
  }
  typedef nd-pkt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
    }
    description
      "The ND packet type value.";
  }
  typedef nd-pkt-evt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
      enum "NDMISS" {
        value 4;
        description
          "ND miss.";
      }
    }
    description
      "The ND packet type or event value.";
  }
  typedef nd-tgt-pkt-type {
    type enumeration {
      enum "NS" {
        value 2;
        description
          "Neighbor solicitation packet.";
      }
      enum "NA" {
        value 3;
        description
          "Neighbor advertisement packet.";
      }
    }
    description
      "The type value of ND packet that supports the target address.";
  }
  typedef nd-detection-mode {
    type enumeration {
      enum "monitor" {
        value 1;
        description
          "Monitor mode.";
      }
      enum "filter" {
        value 2;
        description
          "Filter mode.";
      }
    }
    description
      "The detection mode for ND attack entries.";
  }
  typedef nd-proxy-type {
    type enumeration {
      enum "dynamic" {
        value 1;
        description
	  "ND proxy entries generated by the local device.";
      }
      enum "evpn" {
        value 2;
        description
          "ND proxy entries sent by a remote device.";
      }
    }
    description
      "The type for ND proxy entries.";
  }
  grouping nd-ip-rate-limits-type {
    description
      "Rate limits for receiving ND packets or ND miss based on specified source IP address.";
    container ip-rate-limits {
      description
        "List of rate limits for receiving ND packets or ND miss based on specified source IP address.";
      list ip-rate-limit {
        key "packet-type ipv6-addr";
        description
          "Configure the rate limit for receiving ND packets or ND miss based on specified source IP address.";
        leaf packet-type {
          type nd-pkt-evt-type;
          description
            "ND packet type or ND miss.";
        }
        leaf ipv6-addr {
          type inet:ipv6-address-no-zone;
          description
            "Source IPv6 address, the address cannot be a multicast address, that is, cannot start with FFXX or ffXX, X represents hexadecimal character. When the type is NDMISS, the source address cannot be the unspecified address.";
        }
        leaf value {
          type uint16 {
            range "0..5000";
          }
          units "pps";
          mandatory true;
          description
            "Rate limit of receiving ND packet or ND miss.";
        }
      }
    }
  }
  container ipv6-nd {
    description
      "ND management.";
    container global {
      description
        "Configure global configuration of ND.";
      leaf ns-send-rate-limit {
        type uint16 {
          range "1..1000";
        }
        units "pps";
        default "550";
        description
          "Rate limit of sending NS packet.";
      }
      leaf na-send-rate-limit {
        type uint16 {
          range "1..10240";
        }
        units "pps";
        default "5000";
        description
          "Rate limit of sending NA packet.";
      }
      leaf rs-send-rate-limit {
        type uint16 {
          range "1..1000";
        }
        units "pps";
        default "550";
        description
          "Rate limit of sending RS packet.";
      }
      leaf ra-send-rate-limit {
        type uint16 {
          range "1..1000";
        }
        units "pps";
        default "550";
        description
          "Rate limit of sending RA packet.";
      }
      leaf dad-detect {
        type nd-flag;
        default "true";
        description
          "The switch of DAD enhanced detection.";
      }
      leaf mac-check-flag {
        type nd-flag;
        default "false";
        description
          "Enable IPv6 ND MAC check.";
      }
      leaf auto-detect-flag {
        type nd-switch-state;
        default "on";
        description
          "To enable the automatic detection of ND entries.";
      }
      leaf prefix-strict-flag {
        type nd-switch-state;
        default "on";
        description
          "ND prefix learning strict.";
      }
      leaf pre-detect-flag {
        type nd-switch-state;
        default "off";
        description
          "To determine whether to enable pre-detection.";
      }
      leaf hop-limit {
        type uint8 {
          range "1..255";
        }
        default "64";
        description
          "IPv6 packet hoplimit.";
      }
      leaf stale-time {
        type uint32 {
          range "60..172800";
        }
        units "s";
        default "1200";
        description
          "Aging time of the global stale state.";
      }
      leaf rsa-calculate-rate-limit {
        type uint32 {
          range "0..100";
          ext:value-meaning {
            ext:item  "0" {
              ext:meaning "disabling the function of rsa calculation limit";
            }
          }
        }
        default "0";
        description
          "Rate limit for RSA option calculation.";
      }
      leaf log-trap-time {
        type uint32 {
          range "60..3600";
        }
        units "s";
        default "600";
        description
          "The interval for sending speed-limit logs and alarms.";
      }
      leaf rs-receive-rate-limit {
        type uint16 {
          range "1..5000";
        }
        units "pps";
        ext:dynamic-default;
        description
          "Rate limit of receiving RS packet.";
      }
      leaf ra-receive-rate-limit {
        type uint16 {
          range "1..5000";
        }
        units "pps";
        ext:dynamic-default;
        description
          "Rate limit of receiving RA packet.";
      }
      leaf ns-receive-rate-limit {
        type uint16 {
          range "1..5000";
        }
        units "pps";
        ext:dynamic-default;
        description
          "Rate limit of receiving NS packet.";
      }
      leaf na-receive-rate-limit {
        type uint16 {
          range "1..5000";
        }
        units "pps";
        ext:dynamic-default;
        description
          "Rate limit of receiving NA packet.";
      }
      leaf miss-receive-rate-limit {
        type uint16 {
          range "1..5000";
        }
        units "pps";
        ext:dynamic-default;
        description
          "Rate limit of receiving ND miss.";
      }
      leaf dad-detect-rate-limit {
        type uint16 {
          range "1..100";
        }
        units "pps";
        default "50";
        description
          "Rate limit of sending DAD detect packet.";
      }
      leaf dad-detect-attempts {
        type uint16 {
          range "1..5";
        }
        default "3";
        description
          "Number of attempts to resolve address conflicts.";
      }
    }    
    container m-lag-global {
      description
      "Configure M-LAG global configuration of ND.";
      leaf ipv6-neighbor-backup-rate {
        type uint32 {
          range "1..2000";
        }
        description
          "Specifies the number of IPv6 neighbor entries synchronized per second through M-LAG.";
        ext:dynamic-default;
      }
    }
    container ipv6-neighbors {
      config false;
      description
        "List of information about neighbor entry query.";
      list ipv6-neighbor {
        key "if-name ipv6-addr";
        description
          "Statistics of query neighbor entries which can be static, or dynamic.";
        leaf if-name {
          type leafref {
            path "/ifm:ifm/ifm:interfaces/ifm:interface/ifm:name";
          }
          description
            "Interface name.";
        }
        leaf ipv6-addr {
          type inet:ipv6-address-no-zone;
          description
            "IPv6 address of a neighbor entry.";
        }
        leaf slot-id {
          type string {
            length "1..24";
          }
          description
            "Slot ID.";
          ext:support-filter "true";
        }
        leaf mac-addr {
          type pub-type:mac-address;
          description
            "MAC address.";
        }
        leaf vpn-name {
          type leafref {
            path "/ni:network-instance/ni:instances/ni:instance/ni:name";
          }
          description
            "VPN name.";
          ext:support-filter "true";
        }
        leaf vlan-id {
          type uint32 {
            range "1..4094";
          }
          description
            "VLAN ID.";
          ext:support-filter "true";
        }
        leaf state {
          type nd-ngb-state;
          description
            "Status of a neighbor entry.";
        }
        leaf static-flag {
          type nd-nb-type;
          description
            "Type of a neighbor entry. The available options are static, dynamic or remote.";
        }
        leaf age {
          type uint32 {
            range "0..4294967293";
          }
          units "min";
          description
            "Time when a neighbor entry is established.";
        }
        leaf is-router {
          type nd-flag;
          description
            "Is a router.";
        }
        leaf cevid {
          type uint32 {
            range "1..4094";
          }
          description
            "Inner VLAN tag. If this parameter is not set, the value of the VLAN ID is considered to be 0. If this parameter is set, it indicates that the ND entry is in the associated VLAN.";
        }
        leaf strict-flag {
          type boolean;
          description
            "Enable/disable strict security mode.";
        }
        leaf nickname {
          type uint32 {
            range "1..65535";
          }
          description
            "Nickname which uniquely identifies an RB on a TRILL network.";
        }
        leaf bd-id {
          type uint32 {
            range "1..16777215";
          }
          description
            "Bridge-domain ID.";
        }
        leaf vni {
          type uint32 {
            range "1..16777215";
          }
          description
            "Vxlan VNI.";
        }
        leaf source-addr {
          type inet:ip-address-no-zone;
          description
            "Tunnel SourceIPAddr.";
        }
        leaf peer-addr {
          type inet:ip-address-no-zone;
          description
            "Tunnel PeerIPAddr.";
        }
      }
    }
    container nd-pkt-stats {
      config false;
      description
        "Statistics of ND packets.";
      container ns-stats {
        description
          "Statistics of NS packets.";
        container ns-global {
          description
            "Statistics of global NS packets.";
          leaf send-total {
            type uint32;
            units "packet";
            description
              "Number of sent NS packets.";
          }
          leaf send-dip-ucast {
            type uint32;
            units "packet";
            description
              "Number of sent NS packets with the destination address as a unicast address.";
          }
          leaf send-dip-mcast {
            type uint32;
            units "packet";
            description
              "Number of sent NS packets with the destination address as a multicast address.";
          }
          leaf send-target-linklocal {
            type uint32;
            units "packet";
            description
              "Number of sent NS packets with the target address as a link-local address.";
          }
          leaf send-target-global {
            type uint32;
            units "packet";
            description
              "Number of sent NS packets with the target address as a global address.";
          }
          leaf recv-total {
            type uint32;
            units "packet";
            description
              "Number of received NS packets.";
          }
          leaf recv-valid-total {
            type uint32;
            units "packet";
            description
              "Number of received valid NS packets.";
          }
          leaf recv-dip-ucast {
            type uint32;
            units "packet";
            description
              "Number of received NS packets with the destination address as a unicast address.";
          }
          leaf recv-dip-mcast {
            type uint32;
            units "packet";
            description
              "Number of NS packets with the destination address as a multicast address.";
          }
          leaf recv-target-linklocal {
            type uint32;
            units "packet";
            description
              "Number of NS packets with the target address as a link-local address.";
          }
          leaf recv-target-global {
            type uint32;
            units "packet";
            description
              "Number of NS packets with the target address as a global address.";
          }
          leaf drop-total {
            type uint32;
            units "packet";
            description
              "Number of discarded NS packets.";
          }
          leaf drop-checksum-err {
            type uint32;
            units "packet";
            description
              "Number of NS packets discarded due to checksum errors.";
          }
          leaf drop-bad-len {
            type uint32;
            units "packet";
            description
              "Number of NS packets discarded due to bad packet length.";
          }
          leaf drop-bad-code {
            type uint32;
            units "packet";
            description
              "Number of NS packets discarded due to bad code.";
          }
          leaf drop-bad-hoplimit {
            type uint32;
            units "packet";
            description
              "Number of NS packets discarded due to bad hoplimit.";
          }
          leaf drop-bad-src-mac {
            type uint32;
            units "packet";
            description
              "Number of NS packets discarded due to bad source MAC addresses.";
          }
          leaf drop-bad-dst-mac {
            type uint32;
            units "packet";
            description
              "Number of NS packets discarded due to bad destination MAC addresses.";
          }
          leaf drop-bad-tgt-mac {
            type uint32;
            units "packet";
            description
              "Number of NS packets discarded due to bad target MAC addresses.";
          }
          leaf drop-bad-src-ip {
            type uint32;
            units "packet";
            description
              "Number of NS packets discarded due to bad source IP addresses.";
          }
          leaf drop-bad-dst-ip {
            type uint32;
            units "packet";
            description
              "Number of NS packets discarded due to bad destination IP addresses.";
          }
          leaf drop-bad-tgt-ip {
            type uint32;
            units "packet";
            description
              "Number of NS packets discarded due to bad target IP addresses.";
          }
          leaf drop-bad-option {
            type uint32;
            units "packet";
            description
              "Number of NS packets discarded due to bad options.";
          }
          leaf drop-local-addr {
            type uint32;
            units "packet";
            description
              "Number of NS packets discarded because the source address is the local address.";
          }        
          leaf drop-mac-check {
            type uint32;
            units "packet";
            description
              "Number of NS packets discarded due to source MAC address consistency check errors.";
          }
          leaf drop-rate-limit {
            type uint32;
            units "packet";
            description
              "Number of NS packets discarded due to global rate limit.";
          }
          leaf drop-src-mac-attack {
            type uint32;
            units "packet";
            description
              "Number of NS packets discarded due to source MAC address attacks.";
          }
          leaf drop-src-mac-rate-limit {
            type uint32;
            units "packet";
            description
              "Number of NS packets discarded due to source MAC rate limit.";
          }
          leaf drop-src-ip-rate-limit {
            type uint32;
            units "packet";
            description
              "Number of NS packets discarded due to source IP rate limit.";
          }
          leaf drop-if-src-ip-rate-limit {
            type uint32;
            units "packet";
            description
              "Number of NS packets discarded due to interface source IP rate limit.";
          }
          leaf drop-if-rate-limit {
            type uint32;
            units "packet";
            description
              "Number of NS packets discarded due to interface rate limit.";
          }
          leaf drop-lr-rate-limit {
            type uint32;
            units "packet";
            description
              "Number of NS packets discarded due to LR rate limit.";
          }
          leaf send-sip-unspecified {
            type uint32;
            units "packet";
            description
              "Number of sent NS packets with the source address as an unspecified address.";
          }
          leaf recv-sip-unspecified {
            type uint32;
            units "packet";
            description
              "Number of received NS packets with the source address as an unspecified address.";
          }
          leaf drop-dst-ip-rate-limit {
            type uint32;
            units "packet";
            description
              "Number of NS packets discarded due to destination IP rate limit.";
          }
          leaf drop-tgt-ip-rate-limit {
            type uint32;
            units "packet";
            description
              "Number of NS packets discarded due to target IP rate limit.";
          }
        }
        container ns-slots {
          config false;
          description
            "List of NS packets in these slots.";
          list ns-slot {
            key "slot-id";
            description
              "Statistics of NS packets in the slot.";
            leaf slot-id {
              type string {
                length "1..24";
              }
              description
                "Slot ID.";
            }          
            leaf send-total {
              type uint32;
              units "packet";
              description
                "Number of sent NS packets.";
            }
            leaf send-dip-ucast {
              type uint32;
              units "packet";
              description
                "Number of sent NS packets with the destination address as a unicast address.";
            }
            leaf send-dip-mcast {
              type uint32;
              units "packet";
              description
                "Number of sent NS packets with the destination address as a multicast address.";
            }
            leaf send-target-linklocal {
              type uint32;
              units "packet";
              description
                "Number of sent NS packets with the target address as a link-local address.";
            }
            leaf send-target-global {
              type uint32;
              units "packet";
              description
                "Number of sent NS packets with the target address as a global address.";
            }
            leaf recv-total {
              type uint32;
              units "packet";
              description
                "Number of received NS packets.";
            }
            leaf recv-valid-total {
              type uint32;
              units "packet";
              description
                "Number of received valid NS packets.";
            }
            leaf recv-dip-ucast {
              type uint32;
              units "packet";
              description
                "Number of received NS packets with the destination address as a unicast address.";
            }
            leaf recv-dip-mcast {
              type uint32;
              units "packet";
              description
                "Number of NS packets with the destination address as a multicast address.";
            }
            leaf recv-target-linklocal {
              type uint32;
              units "packet";
              description
                "Number of NS packets with the destination address as a link-local address.";
            }
            leaf recv-target-global {
              type uint32;
              units "packet";
              description
                "Number of NS packets with the destination address as a global address.";
            }
            leaf drop-total {
              type uint32;
              units "packet";
              description
                "Number of discarded NS packets.";
            }
            leaf drop-checksum-err {
              type uint32;
              units "packet";
              description
                "Number of NS packets discarded due to checksum errors.";
            }
            leaf drop-bad-len {
              type uint32;
              units "packet";
              description
                "Number of NS packets discarded due to bad packet length.";
            }
            leaf drop-bad-code {
              type uint32;
              units "packet";
              description
                "Number of NS packets discarded due to bad code.";
            }
            leaf drop-bad-hoplimit {
              type uint32;
              units "packet";
              description
                "Number of NS packets discarded due to bad hoplimit.";
            }
            leaf drop-bad-src-mac {
              type uint32;
              units "packet";
              description
                "Number of NS packets discarded due to bad source MAC addresses.";
            }
            leaf drop-bad-dst-mac {
              type uint32;
              units "packet";
              description
                "Number of NS packets discarded due to bad destination MAC addresses.";
            }
            leaf drop-bad-tgt-mac {
              type uint32;
              units "packet";
              description
                "Number of NS packets discarded due to bad target MAC addresses.";
            }
            leaf drop-bad-src-ip {
              type uint32;
              units "packet";
              description
                "Number of NS packets discarded due to bad source IP addresses.";
            }
            leaf drop-bad-dst-ip {
              type uint32;
              units "packet";
              description
                "Number of NS packets discarded due to bad destination IP addresses.";
            }
            leaf drop-bad-tgt-ip {
              type uint32;
              units "packet";
              description
                "Number of NS packets discarded due to bad target IP addresses.";
            }
            leaf drop-bad-option {
              type uint32;
              units "packet";
              description
                "Number of NS packets discarded due to bad options.";
            }
            leaf drop-local-addr {
              type uint32;
              units "packet";
              description
                "Number of NS packets discarded because the source address is the local address.";
            }        
            leaf drop-mac-check {
              type uint32;
              units "packet";
              description
                "Number of NS packets discarded due to source MAC address consistency check errors.";
            }
            leaf drop-rate-limit {
              type uint32;
              units "packet";
              description
                "Number of NS packets discarded due to global rate limit.";
            }
            leaf drop-src-mac-attack {
              type uint32;
              units "packet";
              description
                "Number of NS packets discarded due to source MAC address attacks.";
            }
            leaf drop-src-mac-rate-limit {
              type uint32;
              units "packet";
              description
                "Number of NS packets discarded due to source MAC rate limit.";
            }
            leaf drop-src-ip-rate-limit {
              type uint32;
              units "packet";
              description
                "Number of NS packets discarded due to source IP rate limit.";
            }
            leaf drop-if-src-ip-rate-limit {
              type uint32;
              units "packet";
              description
                "Number of NS packets discarded due to interface source IP rate limit.";
            }
            leaf drop-if-rate-limit {
              type uint32;
              units "packet";
              description
                "Number of NS packets discarded due to interface rate limit.";
            }
            leaf drop-lr-rate-limit {
              type uint32;
              units "packet";
              description
                "Number of NS packets discarded due to LR rate limit.";
            }
            leaf send-sip-unspecified {
              type uint32;
              units "packet";
              description
                "Number of sent NS packets with the source address as an unspecified address.";
            }
            leaf recv-sip-unspecified {
              type uint32;
              units "packet";
              description
                "Number of received NS packets with the source address as an unspecified address.";
            }
            leaf drop-dst-ip-rate-limit {
              type uint32;
              units "packet";
              description
                "Number of NS packets discarded due to destination IP rate limit.";
            }
            leaf drop-tgt-ip-rate-limit {
              type uint32;
              units "packet";
              description
                "Number of NS packets discarded due to target IP rate limit.";
            }
          }        
        }
        container ns-ifs {
          config false;
          description
            "List of NS packets in these interfaces.";
          list ns-if {
            key "if-name";
            description
              "Statistics of NS packets in the interface.";
            leaf if-name {
              type leafref {
                path "/ifm:ifm/ifm:interfaces/ifm:interface/ifm:name";
              }
              description
                "Interface name.";
            }          
            leaf send-total {
              type uint32;
              units "packet";
              description
                "Number of sent NS packets.";
            }
            leaf send-dip-ucast {
              type uint32;
              units "packet";
              description
                "Number of sent NS packets with the destination address as a unicast address.";
            }
            leaf send-dip-mcast {
              type uint32;
              units "packet";
              description
                "Number of sent NS packets with the destination address as a multicast address.";
            }
            leaf send-target-linklocal {
              type uint32;
              units "packet";
              description
                "Number of sent NS packets with the target address as a link-local address.";
            }
            leaf send-target-global {
              type uint32;
              units "packet";
              description
                "Number of sent NS packets with the target address as a global address.";
            }
            leaf recv-total {
              type uint32;
              units "packet";
              description
                "Number of received NS packets.";
            }
            leaf recv-valid-total {
              type uint32;
              units "packet";
              description
                "Number of received valid NS packets.";
            }
            leaf recv-dip-ucast {
              type uint32;
              units "packet";
              description
                "Number of received NS packets with the destination address as a unicast address.";
            }
            leaf recv-dip-mcast {
              type uint32;
              units "packet";
              description
                "Number of NS packets with the destination address as a multicast address.";
            }
            leaf recv-target-linklocal {
              type uint32;
              units "packet";
              description
                "Number of NS packets with the destination address as a link-local address.";
            }
            leaf recv-target-global {
              type uint32;
              units "packet";
              description
                "Number of NS packets with the destination address as a global address.";
            }
            leaf drop-total {
              type uint32;
              units "packet";
              description
                "Number of discarded NS packets.";
            }
            leaf drop-checksum-err {
              type uint32;
              units "packet";
              description
                "Number of NS packets discarded due to checksum errors.";
            }
            leaf drop-bad-len {
              type uint32;
              units "packet";
              description
                "Number of NS packets discarded due to bad packet length.";
            }
            leaf drop-bad-code {
              type uint32;
              units "packet";
              description
                "Number of NS packets discarded due to bad code.";
            }
            leaf drop-bad-hoplimit {
              type uint32;
              units "packet";
              description
                "Number of NS packets discarded due to bad hoplimit.";
            }
            leaf drop-bad-src-mac {
              type uint32;
              units "packet";
              description
                "Number of NS packets discarded due to bad source MAC addresses.";
            }
            leaf drop-bad-dst-mac {
              type uint32;
              units "packet";
              description
                "Number of NS packets discarded due to bad destination MAC addresses.";
            }
            leaf drop-bad-tgt-mac {
              type uint32;
              units "packet";
              description
                "Number of NS packets discarded due to bad target MAC addresses.";
            }
            leaf drop-bad-src-ip {
              type uint32;
              units "packet";
              description
                "Number of NS packets discarded due to bad source IP addresses.";
            }
            leaf drop-bad-dst-ip {
              type uint32;
              units "packet";
              description
                "Number of NS packets discarded due to bad destination IP addresses.";
            }
            leaf drop-bad-tgt-ip {
              type uint32;
              units "packet";
              description
                "Number of NS packets discarded due to bad target IP addresses.";
            }
            leaf drop-bad-option {
              type uint32;
              units "packet";
              description
                "Number of NS packets discarded due to bad options.";
            }
            leaf drop-local-addr {
              type uint32;
              units "packet";
              description
                "Number of NS packets discarded because the source address is the local address.";
            }        
            leaf drop-mac-check {
              type uint32;
              units "packet";
              description
                "Number of NS packets discarded due to source MAC address consistency check errors.";
            }
            leaf drop-rate-limit {
              type uint32;
              units "packet";
              description
                "Number of NS packets discarded due to global rate limit.";
            }
            leaf drop-src-mac-attack {
              type uint32;
              units "packet";
              description
                "Number of NS packets discarded due to source MAC address attacks.";
            }
            leaf drop-src-mac-rate-limit {
              type uint32;
              units "packet";
              description
                "Number of NS packets discarded due to source MAC rate limit.";
            }
            leaf drop-src-ip-rate-limit {
              type uint32;
              units "packet";
              description
                "Number of NS packets discarded due to source IP rate limit.";
            }
            leaf drop-if-src-ip-rate-limit {
              type uint32;
              units "packet";
              description
                "Number of NS packets discarded due to interface source IP rate limit.";
            }
            leaf drop-if-rate-limit {
              type uint32;
              units "packet";
              description
                "Number of NS packets discarded due to interface rate limit.";
            }
            leaf drop-lr-rate-limit {
              type uint32;
              units "packet";
              description
                "Number of NS packets discarded due to LR rate limit.";
            }
            leaf send-sip-unspecified {
              type uint32;
              units "packet";
              description
                "Number of sent NS packets with the source address as an unspecified address.";
            }
            leaf recv-sip-unspecified {
              type uint32;
              units "packet";
              description
                "Number of received NS packets with the source address as an unspecified address.";
            }
            leaf drop-dst-ip-rate-limit {
              type uint32;
              units "packet";
              description
                "Number of NS packets discarded due to destination IP rate limit.";
            }
            leaf drop-tgt-ip-rate-limit {
              type uint32;
              units "packet";
              description
                "Number of NS packets discarded due to target IP rate limit.";
            }
          }        
        }
      }
      container na-stats {
        description
          "Statistics of NA packets.";
        container na-global {
          description
            "Statistics of global NA packets.";
          leaf send-total {
            type uint32;
            units "packet";
            description
              "Number of sent NA packets.";
          }
          leaf send-dip-ucast {
            type uint32;
            units "packet";
            description
              "Number of sent NA packets with the destination address as a unicast address.";
          }
          leaf send-dip-mcast {
            type uint32;
            units "packet";
            description
              "Number of sent NA packets with the destination address as a multicast address.";
          }
          leaf send-target-linklocal {
            type uint32;
            units "packet";
            description
              "Number of sent NA packets with the target address as a link-local address.";
          }
          leaf send-target-global {
            type uint32;
            units "packet";
            description
              "Number of sent NA packets with the target address as a global address.";
          }
          leaf recv-total {
            type uint32;
            units "packet";
            description
              "Number of received NA packets.";
          }
          leaf recv-valid-total {
            type uint32;
            units "packet";
            description
              "Number of received valid NA packets.";
          }
          leaf recv-dip-ucast {
            type uint32;
            units "packet";
            description
              "Number of received NA packets with the destination address as a unicast address.";
          }
          leaf recv-dip-mcast {
            type uint32;
            units "packet";
            description
              "Number of NA packets with the destination address as a multicast address.";
          }
          leaf recv-target-linklocal {
            type uint32;
            units "packet";
            description
              "Number of NA packets with the destination address as a link-local address.";
          }
          leaf recv-target-global {
            type uint32;
            units "packet";
            description
              "Number of NA packets with the destination address as a global address.";
          }
          leaf drop-total {
            type uint32;
            units "packet";
            description
              "Number of discarded NA packets.";
          }
          leaf drop-checksum-err {
            type uint32;
            units "packet";
            description
              "Number of NA packets discarded due to checksum errors.";
          }
          leaf drop-bad-len {
            type uint32;
            units "packet";
            description
              "Number of NA packets discarded due to bad packet length.";
          }
          leaf drop-bad-code {
            type uint32;
            units "packet";
            description
              "Number of NA packets discarded due to bad code.";
          }
          leaf drop-bad-hoplimit {
            type uint32;
            units "packet";
            description
              "Number of NA packets discarded due to bad hoplimit.";
          }
          leaf drop-bad-src-mac {
            type uint32;
            units "packet";
            description
              "Number of NA packets discarded due to bad source MAC addresses.";
          }
          leaf drop-bad-dst-mac {
            type uint32;
            units "packet";
            description
              "Number of NA packets discarded due to bad destination MAC addresses.";
          }
          leaf drop-bad-tgt-mac {
            type uint32;
            units "packet";
            description
              "Number of NA packets discarded due to bad target MAC addresses.";
          }
          leaf drop-bad-src-ip {
            type uint32;
            units "packet";
            description
              "Number of NA packets discarded due to bad source IP addresses.";
          }
          leaf drop-bad-dst-ip {
            type uint32;
            units "packet";
            description
              "Number of NA packets discarded due to bad destination IP addresses.";
          }
          leaf drop-bad-tgt-ip {
            type uint32;
            units "packet";
            description
              "Number of NA packets discarded due to bad target IP addresses.";
          }
          leaf drop-bad-option {
            type uint32;
            units "packet";
            description
              "Number of NA packets discarded due to bad options.";
          }
          leaf drop-local-addr {
            type uint32;
            units "packet";
            description
              "Number of NA packets discarded because the source address is the local address.";
          }        
          leaf drop-mac-check {
            type uint32;
            units "packet";
            description
              "Number of NA packets discarded due to source MAC address consistency check errors.";
          }
          leaf drop-rate-limit {
            type uint32;
            units "packet";
            description
              "Number of NA packets discarded due to global rate limit.";
          }
          leaf drop-src-mac-attack {
            type uint32;
            units "packet";
            description
              "Number of NA packets discarded due to source MAC address attacks.";
          }
          leaf drop-src-mac-rate-limit {
            type uint32;
            units "packet";
            description
              "Number of NA packets discarded due to source MAC rate limit.";
          }
          leaf drop-src-ip-rate-limit {
            type uint32;
            units "packet";
            description
              "Number of NA packets discarded due to source IP rate limit.";
          }
          leaf drop-if-src-ip-rate-limit {
            type uint32;
            units "packet";
            description
              "Number of NA packets discarded due to interface source IP rate limit.";
          }
          leaf drop-if-rate-limit {
            type uint32;
            units "packet";
            description
              "Number of NA packets discarded due to interface rate limit.";
          }
          leaf drop-lr-rate-limit {
            type uint32;
            units "packet";
            description
              "Number of NA packets discarded due to LR rate limit.";
          }
          leaf drop-dst-ip-rate-limit {
            type uint32;
            units "packet";
            description
              "Number of NA packets discarded due to destination IP rate limit.";
          }
          leaf drop-tgt-ip-rate-limit {
            type uint32;
            units "packet";
            description
              "Number of NA packets discarded due to target IP rate limit.";
          }
        }
        container na-slots {
          description
            "List of NA packets in these slots.";
          list na-slot {
            key "slot-id";
            description
              "Statistics of NA packets in the slot.";
            leaf slot-id {
              type string {
                length "1..24";
              }
              description
                "Slot ID.";
            }        
            leaf send-total {
              type uint32;
              units "packet";
              description
                "Number of send NA packets.";
            }
            leaf send-dip-ucast {
              type uint32;
              units "packet";
              description
                "Number of send NA packets with the destination address as a unicast address.";
            }
            leaf send-dip-mcast {
              type uint32;
              units "packet";
              description
                "Number of send NA packets with the destination address as a multicast address.";
            }
            leaf send-target-linklocal {
              type uint32;
              units "packet";
              description
                "Number of send NA packets with the target address as a link-local address.";
            }
            leaf send-target-global {
              type uint32;
              units "packet";
              description
                "Number of send NA packets with the target address as a global address.";
            }
            leaf recv-total {
              type uint32;
              units "packet";
              description
                "Number of received NA packets.";
            }
            leaf recv-valid-total {
              type uint32;
              units "packet";
              description
                "Number of received valid NA packets.";
            }
            leaf recv-dip-ucast {
              type uint32;
              units "packet";
              description
                "Number of received NA packets with the destination address as a unicast address.";
            }
            leaf recv-dip-mcast {
              type uint32;
              units "packet";
              description
                "Number of NA packets with the destination address as a multicast address.";
            }
            leaf recv-target-linklocal {
              type uint32;
              units "packet";
              description
                "Number of NA packets with the destination address as a link-local address.";
            }
            leaf recv-target-global {
              type uint32;
              units "packet";
              description
                "Number of NA packets with the destination address as a global address.";
            }
            leaf drop-total {
              type uint32;
              units "packet";
              description
                "Number of discarded NA packets.";
            }
            leaf drop-checksum-err {
              type uint32;
              units "packet";
              description
                "Number of NA packets discarded due to checksum errors.";
            }
            leaf drop-bad-len {
              type uint32;
              units "packet";
              description
                "Number of NA packets discarded due to bad packet length.";
            }
            leaf drop-bad-code {
              type uint32;
              units "packet";
              description
                "Number of NA packets discarded due to bad code.";
            }
            leaf drop-bad-hoplimit {
              type uint32;
              units "packet";
              description
                "Number of NA packets discarded due to bad hoplimit.";
            }
            leaf drop-bad-src-mac {
              type uint32;
              units "packet";
              description
                "Number of NA packets discarded due to bad source MAC addresses.";
            }
            leaf drop-bad-dst-mac {
              type uint32;
              units "packet";
              description
                "Number of NA packets discarded due to bad destination MAC addresses.";
            }
            leaf drop-bad-tgt-mac {
              type uint32;
              units "packet";
              description
                "Number of NA packets discarded due to bad target MAC addresses.";
            }
            leaf drop-bad-src-ip {
              type uint32;
              units "packet";
              description
                "Number of NA packets discarded due to bad source IP addresses.";
            }
            leaf drop-bad-dst-ip {
              type uint32;
              units "packet";
              description
                "Number of NA packets discarded due to bad destination IP addresses.";
            }
            leaf drop-bad-tgt-ip {
              type uint32;
              units "packet";
              description
                "Number of NA packets discarded due to bad target IP addresses.";
            }
            leaf drop-bad-option {
              type uint32;
              units "packet";
              description
                "Number of NA packets discarded due to bad options.";
            }
            leaf drop-local-addr {
              type uint32;
              units "packet";
              description
                "Number of NA packets discarded because the source address is the local address.";
            }        
            leaf drop-mac-check {
              type uint32;
              units "packet";
              description
                "Number of NA packets discarded due to source MAC address consistency check errors.";
            }
            leaf drop-rate-limit {
              type uint32;
              units "packet";
              description
                "Number of NA packets discarded due to global rate limit.";
            }
            leaf drop-src-mac-attack {
              type uint32;
              units "packet";
              description
                "Number of NA packets discarded due to source MAC address attacks.";
            }
            leaf drop-src-mac-rate-limit {
              type uint32;
              units "packet";
              description
                "Number of NA packets discarded due to source MAC rate limit.";
            }
            leaf drop-src-ip-rate-limit {
              type uint32;
              units "packet";
              description
                "Number of NA packets discarded due to source IP rate limit.";
            }
            leaf drop-if-src-ip-rate-limit {
              type uint32;
              units "packet";
              description
                "Number of NA packets discarded due to interface source IP rate limit.";
            }
            leaf drop-if-rate-limit {
              type uint32;
              units "packet";
              description
                "Number of NA packets discarded due to interface rate limit.";
            }
            leaf drop-lr-rate-limit {
              type uint32;
              units "packet";
              description
                "Number of NA packets discarded due to LR rate limit.";
            }
            leaf drop-dst-ip-rate-limit {
              type uint32;
              units "packet";
              description
                "Number of NA packets discarded due to destination IP rate limit.";
            }
            leaf drop-tgt-ip-rate-limit {
              type uint32;
              units "packet";
              description
                "Number of NA packets discarded due to target IP rate limit.";
            }
          }        
        }
        container na-ifs {
          description
            "List of NA packets in these interfaces.";
          list na-if {
            key "if-name";
            description
              "Statistics of NA packets in the interface.";
            leaf if-name {
              type leafref {
                path "/ifm:ifm/ifm:interfaces/ifm:interface/ifm:name";
              }
              description
                "Interface name.";
            }              
            leaf send-total {
              type uint32;
              units "packet";
              description
                "Number of send NA packets.";
            }
            leaf send-dip-ucast {
              type uint32;
              units "packet";
              description
                "Number of send NA packets with the destination address as a unicast address.";
            }
            leaf send-dip-mcast {
              type uint32;
              units "packet";
              description
                "Number of send NA packets with the destination address as a multicast address.";
            }
            leaf send-target-linklocal {
              type uint32;
              units "packet";
              description
                "Number of send NA packets with the target address as a link-local address.";
            }
            leaf send-target-global {
              type uint32;
              units "packet";
              description
                "Number of send NA packets with the target address as a global address.";
            }
            leaf recv-total {
              type uint32;
              units "packet";
              description
                "Number of received NA packets.";
            }
            leaf recv-valid-total {
              type uint32;
              units "packet";
              description
                "Number of received valid NA packets.";
            }
            leaf recv-dip-ucast {
              type uint32;
              units "packet";
              description
                "Number of received NA packets with the destination address as a unicast address.";
            }
            leaf recv-dip-mcast {
              type uint32;
              units "packet";
              description
                "Number of NA packets with the destination address as a multicast address.";
            }
            leaf recv-target-linklocal {
              type uint32;
              units "packet";
              description
                "Number of NA packets with the destination address as a link-local address.";
            }
            leaf recv-target-global {
              type uint32;
              units "packet";
              description
                "Number of NA packets with the destination address as a global address.";
            }
            leaf drop-total {
              type uint32;
              units "packet";
              description
                "Number of discarded NA packets.";
            }
            leaf drop-checksum-err {
              type uint32;
              units "packet";
              description
                "Number of NA packets discarded due to checksum errors.";
            }
            leaf drop-bad-len {
              type uint32;
              units "packet";
              description
                "Number of NA packets discarded due to bad packet length.";
            }
            leaf drop-bad-code {
              type uint32;
              units "packet";
              description
                "Number of NA packets discarded due to bad code.";
            }
            leaf drop-bad-hoplimit {
              type uint32;
              units "packet";
              description
                "Number of NA packets discarded due to bad hoplimit.";
            }
            leaf drop-bad-src-mac {
              type uint32;
              units "packet";
              description
                "Number of NA packets discarded due to bad source MAC addresses.";
            }
            leaf drop-bad-dst-mac {
              type uint32;
              units "packet";
              description
                "Number of NA packets discarded due to bad destination MAC addresses.";
            }
            leaf drop-bad-tgt-mac {
              type uint32;
              units "packet";
              description
                "Number of NA packets discarded due to bad target MAC addresses.";
            }
            leaf drop-bad-src-ip {
              type uint32;
              units "packet";
              description
                "Number of NA packets discarded due to bad source IP addresses.";
            }
            leaf drop-bad-dst-ip {
              type uint32;
              units "packet";
              description
                "Number of NA packets discarded due to bad destination IP addresses.";
            }
            leaf drop-bad-tgt-ip {
              type uint32;
              units "packet";
              description
                "Number of NA packets discarded due to bad target IP addresses.";
            }
            leaf drop-bad-option {
              type uint32;
              units "packet";
              description
                "Number of NA packets discarded due to bad options.";
            }
            leaf drop-local-addr {
              type uint32;
              units "packet";
              description
                "Number of NA packets discarded because the source address is the local address.";
            }        
            leaf drop-mac-check {
              type uint32;
              units "packet";
              description
                "Number of NA packets discarded due to source MAC address consistency check errors.";
            }
            leaf drop-rate-limit {
              type uint32;
              units "packet";
              description
                "Number of NA packets discarded due to global rate limit.";
            }
            leaf drop-src-mac-attack {
              type uint32;
              units "packet";
              description
                "Number of NA packets discarded due to source MAC address attacks.";
            }
            leaf drop-src-mac-rate-limit {
              type uint32;
              units "packet";
              description
                "Number of NA packets discarded due to source MAC rate limit.";
            }
            leaf drop-src-ip-rate-limit {
              type uint32;
              units "packet";
              description
                "Number of NA packets discarded due to source IP rate limit.";
            }
            leaf drop-if-src-ip-rate-limit {
              type uint32;
              units "packet";
              description
                "Number of NA packets discarded due to interface source IP rate limit.";
            }
            leaf drop-if-rate-limit {
              type uint32;
              units "packet";
              description
                "Number of NA packets discarded due to interface rate limit.";
            }
            leaf drop-lr-rate-limit {
              type uint32;
              units "packet";
              description
                "Number of NA packets discarded due to LR rate limit.";
            }
            leaf drop-dst-ip-rate-limit {
              type uint32;
              units "packet";
              description
                "Number of NA packets discarded due to destination IP rate limit.";
            }
            leaf drop-tgt-ip-rate-limit {
              type uint32;
              units "packet";
              description
                "Number of NA packets discarded due to target IP rate limit.";
            }
          }        
        }
      }
      container rs-stats {
        description
          "Statistics of RS packets.";
        container rs-global {
          description
            "Statistics of global RS packets.";
          leaf send-total {
            type uint32;
            units "packet";
            description
              "Number of send RS packets.";
          }
          leaf send-dip-mcast {
            type uint32;
            units "packet";
            description
              "Number of send RS packets with the destination address as a multicast address.";
          }
          leaf recv-total {
            type uint32;
            units "packet";
            description
              "Number of received RS packets.";
          }
          leaf recv-valid-total {
            type uint32;
            units "packet";
            description
              "Number of received valid RS packets.";
          }
          leaf recv-dip-ucast {
            type uint32;
            units "packet";
            description
              "Number of received RS packets with the destination address as a unicast address.";
          }
          leaf recv-dip-mcast {
            type uint32;
            units "packet";
            description
              "Number of RS packets with the destination address as a multicast address.";
          }
          leaf drop-total {
            type uint32;
            units "packet";
            description
              "Number of discarded RS packets.";
          }
          leaf drop-checksum-err {
            type uint32;
            units "packet";
            description
              "Number of RS packets discarded due to checksum errors.";
          }
          leaf drop-bad-len {
            type uint32;
            units "packet";
            description
              "Number of RS packets discarded due to bad packet length.";
          }
          leaf drop-bad-code {
            type uint32;
            units "packet";
            description
              "Number of RS packets discarded due to bad code.";
          }
          leaf drop-bad-hoplimit {
            type uint32;
            units "packet";
            description
              "Number of RS packets discarded due to bad hoplimit.";
          }
          leaf drop-bad-src-mac {
            type uint32;
            units "packet";
            description
              "Number of RS packets discarded due to bad source MAC addresses.";
          }
          leaf drop-bad-dst-mac {
            type uint32;
            units "packet";
            description
              "Number of RS packets discarded due to bad destination MAC addresses.";
          }
          leaf drop-bad-tgt-mac {
            type uint32;
            units "packet";
            description
              "Number of RS packets discarded due to bad target MAC addresses.";
          }
          leaf drop-bad-src-ip {
            type uint32;
            units "packet";
            description
              "Number of RS packets discarded due to bad source IP addresses.";
          }
          leaf drop-bad-dst-ip {
            type uint32;
            units "packet";
            description
              "Number of RS packets discarded due to bad destination IP addresses.";
          }
          leaf drop-bad-option {
            type uint32;
            units "packet";
            description
              "Number of RS packets discarded due to bad options.";
          }
          leaf drop-local-addr {
            type uint32;
            units "packet";
            description
              "Number of RS packets discarded because the source address is the local address.";
          }        
          leaf drop-mac-check {
            type uint32;
            units "packet";
            description
              "Number of RS packets discarded due to source MAC address consistency check errors.";
          }
          leaf drop-rate-limit {
            type uint32;
            units "packet";
            description
              "Number of RS packets discarded due to global rate limit.";
          }
          leaf drop-src-mac-attack {
            type uint32;
            units "packet";
            description
              "Number of RS packets discarded due to source MAC address attacks.";
          }
          leaf drop-src-mac-rate-limit {
            type uint32;
            units "packet";
            description
              "Number of RS packets discarded due to source MAC rate limit.";
          }
          leaf drop-src-ip-rate-limit {
            type uint32;
            units "packet";
            description
              "Number of RS packets discarded due to source IP rate limit.";
          }
          leaf drop-if-src-ip-rate-limit {
            type uint32;
            units "packet";
            description
              "Number of RS packets discarded due to interface source IP rate limit.";
          }
          leaf drop-if-rate-limit {
            type uint32;
            units "packet";
            description
              "Number of RS packets discarded due to interface rate limit.";
          }
          leaf drop-lr-rate-limit {
            type uint32;
            units "packet";
            description
              "Number of RS packets discarded due to LR rate limit.";
          }
          leaf drop-dst-ip-rate-limit {
            type uint32;
            units "packet";
            description
              "Number of RS packets discarded due to destination IP rate limit.";
          }
        }
        container rs-slots {
          description
            "List of RS packets in these slots.";
          list rs-slot {
            key "slot-id";
            description
              "Statistics of RS packets in the slot.";
            leaf slot-id {
              type string {
                length "1..24";
              }
              description
                "Slot ID.";
            }        
            leaf send-total {
              type uint32;
              units "packet";
              description
                "Number of send RS packets.";
            }
            leaf send-dip-mcast {
              type uint32;
              units "packet";
              description
                "Number of send RS packets with the destination address as a multicast address.";
            }
            leaf recv-total {
              type uint32;
              units "packet";
              description
                "Number of received RS packets.";
            }
            leaf recv-valid-total {
              type uint32;
              units "packet";
              description
                "Number of received valid RS packets.";
            }
            leaf recv-dip-ucast {
              type uint32;
              units "packet";
              description
                "Number of received RS packets with the destination address as a unicast address.";
            }
            leaf recv-dip-mcast {
              type uint32;
              units "packet";
              description
                "Number of RS packets with the destination address as a multicast address.";
            }
            leaf drop-total {
              type uint32;
              units "packet";
              description
                "Number of discarded RS packets.";
            }
            leaf drop-checksum-err {
              type uint32;
              units "packet";
              description
                "Number of RS packets discarded due to checksum errors.";
            }
            leaf drop-bad-len {
              type uint32;
              units "packet";
              description
                "Number of RS packets discarded due to bad packet length.";
            }
            leaf drop-bad-code {
              type uint32;
              units "packet";
              description
                "Number of RS packets discarded due to bad code.";
            }
            leaf drop-bad-hoplimit {
              type uint32;
              units "packet";
              description
                "Number of RS packets discarded due to bad hoplimit.";
            }
            leaf drop-bad-src-mac {
              type uint32;
              units "packet";
              description
                "Number of RS packets discarded due to bad source MAC addresses.";
            }
            leaf drop-bad-dst-mac {
              type uint32;
              units "packet";
              description
                "Number of RS packets discarded due to bad destination MAC addresses.";
            }
            leaf drop-bad-tgt-mac {
              type uint32;
              units "packet";
              description
                "Number of RS packets discarded due to bad target MAC addresses.";
            }
            leaf drop-bad-src-ip {
              type uint32;
              units "packet";
              description
                "Number of RS packets discarded due to bad source IP addresses.";
            }
            leaf drop-bad-dst-ip {
              type uint32;
              units "packet";
              description
                "Number of RS packets discarded due to bad destination IP addresses.";
            }
            leaf drop-bad-option {
              type uint32;
              units "packet";
              description
                "Number of RS packets discarded due to bad options.";
            }
            leaf drop-local-addr {
              type uint32;
              units "packet";
              description
                "Number of RS packets discarded because the source address is the local address.";
            }        
            leaf drop-mac-check {
              type uint32;
              units "packet";
              description
                "Number of RS packets discarded due to source MAC address consistency check errors.";
            }
            leaf drop-rate-limit {
              type uint32;
              units "packet";
              description
                "Number of RS packets discarded due to global rate limit.";
            }
            leaf drop-src-mac-attack {
              type uint32;
              units "packet";
              description
                "Number of RS packets discarded due to source MAC address attacks.";
            }
            leaf drop-src-mac-rate-limit {
              type uint32;
              units "packet";
              description
                "Number of RS packets discarded due to source MAC rate limit.";
            }
            leaf drop-src-ip-rate-limit {
              type uint32;
              units "packet";
              description
                "Number of RS packets discarded due to source IP rate limit.";
            }
            leaf drop-if-src-ip-rate-limit {
              type uint32;
              units "packet";
              description
                "Number of RS packets discarded due to interface source IP rate limit.";
            }
            leaf drop-if-rate-limit {
              type uint32;
              units "packet";
              description
                "Number of RS packets discarded due to interface rate limit.";
            }
            leaf drop-lr-rate-limit {
              type uint32;
              units "packet";
              description
                "Number of RS packets discarded due to LR rate limit.";
            }
            leaf drop-dst-ip-rate-limit {
              type uint32;
              units "packet";
              description
                "Number of RS packets discarded due to destination IP rate limit.";
            }
          }        
        }
        container rs-ifs {
          description
            "List of RS packets in these interfaces.";
          list rs-if {
            key "if-name";
            description
              "Statistics of RS packets in the interface.";
            leaf if-name {
              type leafref {
                path "/ifm:ifm/ifm:interfaces/ifm:interface/ifm:name";
              }
              description
                "Interface name.";
            }          
            leaf send-total {
              type uint32;
              units "packet";
              description
                "Number of send RS packets.";
            }
            leaf send-dip-mcast {
              type uint32;
              units "packet";
              description
                "Number of send RS packets with the destination address as a multicast address.";
            }
            leaf recv-total {
              type uint32;
              units "packet";
              description
                "Number of received RS packets.";
            }
            leaf recv-valid-total {
              type uint32;
              units "packet";
              description
                "Number of received valid RS packets.";
            }
            leaf recv-dip-ucast {
              type uint32;
              units "packet";
              description
                "Number of received RS packets with the destination address as a unicast address.";
            }
            leaf recv-dip-mcast {
              type uint32;
              units "packet";
              description
                "Number of RS packets with the destination address as a multicast address.";
            }
            leaf drop-total {
              type uint32;
              units "packet";
              description
                "Number of discarded RS packets.";
            }
            leaf drop-checksum-err {
              type uint32;
              units "packet";
              description
                "Number of RS packets discarded due to checksum errors.";
            }
            leaf drop-bad-len {
              type uint32;
              units "packet";
              description
                "Number of RS packets discarded due to bad packet length.";
            }
            leaf drop-bad-code {
              type uint32;
              units "packet";
              description
                "Number of RS packets discarded due to bad code.";
            }
            leaf drop-bad-hoplimit {
              type uint32;
              units "packet";
              description
                "Number of RS packets discarded due to bad hoplimit.";
            }
            leaf drop-bad-src-mac {
              type uint32;
              units "packet";
              description
                "Number of RS packets discarded due to bad source MAC addresses.";
            }
            leaf drop-bad-dst-mac {
              type uint32;
              units "packet";
              description
                "Number of RS packets discarded due to bad destination MAC addresses.";
            }
            leaf drop-bad-tgt-mac {
              type uint32;
              units "packet";
              description
                "Number of RS packets discarded due to bad target MAC addresses.";
            }
            leaf drop-bad-src-ip {
              type uint32;
              units "packet";
              description
                "Number of RS packets discarded due to bad source IP addresses.";
            }
            leaf drop-bad-dst-ip {
              type uint32;
              units "packet";
              description
                "Number of RS packets discarded due to bad destination IP addresses.";
            }
            leaf drop-bad-option {
              type uint32;
              units "packet";
              description
                "Number of RS packets discarded due to bad options.";
            }
            leaf drop-local-addr {
              type uint32;
              units "packet";
              description
                "Number of RS packets discarded because the source address is the local address.";
            }        
            leaf drop-mac-check {
              type uint32;
              units "packet";
              description
                "Number of RS packets discarded due to source MAC address consistency check errors.";
            }
            leaf drop-rate-limit {
              type uint32;
              units "packet";
              description
                "Number of RS packets discarded due to global rate limit.";
            }
            leaf drop-src-mac-attack {
              type uint32;
              units "packet";
              description
                "Number of RS packets discarded due to source MAC address attacks.";
            }
            leaf drop-src-mac-rate-limit {
              type uint32;
              units "packet";
              description
                "Number of RS packets discarded due to source MAC rate limit.";
            }
            leaf drop-src-ip-rate-limit {
              type uint32;
              units "packet";
              description
                "Number of RS packets discarded due to source IP rate limit.";
            }
            leaf drop-if-src-ip-rate-limit {
              type uint32;
              units "packet";
              description
                "Number of RS packets discarded due to interface source IP rate limit.";
            }
            leaf drop-if-rate-limit {
              type uint32;
              units "packet";
              description
                "Number of RS packets discarded due to interface rate limit.";
            }
            leaf drop-lr-rate-limit {
              type uint32;
              units "packet";
              description
                "Number of RS packets discarded due to LR rate limit.";
            }
            leaf drop-dst-ip-rate-limit {
              type uint32;
              units "packet";
              description
                "Number of RS packets discarded due to destination IP rate limit.";
            }
          }        
        }
      }
      container ra-stats {
        description
          "Statistics of RA packets.";
        container ra-global {
          description
            "Statistics of global RA packets.";
          leaf send-total {
            type uint32;
            units "packet";
            description
              "Number of send RA packets.";
          }
          leaf send-dip-ucast {
            type uint32;
            units "packet";
            description
              "Number of send RA packets with the destination address as a unicast address.";
          }
          leaf send-dip-mcast {
            type uint32;
            units "packet";
            description
              "Number of send RA packets with the destination address as a multicast address.";
          }
          leaf recv-total {
            type uint32;
            units "packet";
            description
              "Number of received RA packets.";
          }
          leaf recv-valid-total {
            type uint32;
            units "packet";
            description
              "Number of received valid RA packets.";
          }
          leaf recv-dip-ucast {
            type uint32;
            units "packet";
            description
              "Number of received RA packets with the destination address as a unicast address.";
          }
          leaf recv-dip-mcast {
            type uint32;
            units "packet";
            description
              "Number of RA packets with the destination address as a multicast address.";
          }
          leaf drop-total {
            type uint32;
            units "packet";
            description
              "Number of discarded RA packets.";
          }
          leaf drop-checksum-err {
            type uint32;
            units "packet";
            description
              "Number of RA packets discarded due to checksum errors.";
          }
          leaf drop-bad-len {
            type uint32;
            units "packet";
            description
              "Number of RA packets discarded due to bad packet length.";
          }
          leaf drop-bad-code {
            type uint32;
            units "packet";
            description
              "Number of RA packets discarded due to bad code.";
          }
          leaf drop-bad-hoplimit {
            type uint32;
            units "packet";
            description
              "Number of RA packets discarded due to bad hoplimit.";
          }
          leaf drop-bad-src-mac {
            type uint32;
            units "packet";
            description
              "Number of RA packets discarded due to bad source MAC addresses.";
          }
          leaf drop-bad-dst-mac {
            type uint32;
            units "packet";
            description
              "Number of RA packets discarded due to bad destination MAC addresses.";
          }
          leaf drop-bad-tgt-mac {
            type uint32;
            units "packet";
            description
              "Number of RA packets discarded due to bad target MAC addresses.";
          }
          leaf drop-bad-src-ip {
            type uint32;
            units "packet";
            description
              "Number of RA packets discarded due to bad source IP addresses.";
          }
          leaf drop-bad-dst-ip {
            type uint32;
            units "packet";
            description
              "Number of RA packets discarded due to bad destination IP addresses.";
          }
          leaf drop-bad-option {
            type uint32;
            units "packet";
            description
              "Number of RA packets discarded due to bad options.";
          }
          leaf drop-local-addr {
            type uint32;
            units "packet";
            description
              "Number of RA packets discarded because the source address is the local address.";
          }        
          leaf drop-mac-check {
            type uint32;
            units "packet";
            description
              "Number of RA packets discarded due to source MAC address consistency check errors.";
          }
          leaf drop-rate-limit {
            type uint32;
            units "packet";
            description
              "Number of RA packets discarded due to global rate limit.";
          }
          leaf drop-src-mac-attack {
            type uint32;
            units "packet";
            description
              "Number of RA packets discarded due to source MAC address attacks.";
          }
          leaf drop-src-mac-rate-limit {
            type uint32;
            units "packet";
            description
              "Number of RA packets discarded due to source MAC rate limit.";
          }
          leaf drop-src-ip-rate-limit {
            type uint32;
            units "packet";
            description
              "Number of RA packets discarded due to source IP rate limit.";
          }
          leaf drop-if-src-ip-rate-limit {
            type uint32;
            units "packet";
            description
              "Number of RA packets discarded due to interface source IP rate limit.";
          }
          leaf drop-if-rate-limit {
            type uint32;
            units "packet";
            description
              "Number of RA packets discarded due to interface rate limit.";
          }
          leaf drop-lr-rate-limit {
            type uint32;
            units "packet";
            description
              "Number of RA packets discarded due to LR rate limit.";
          }
          leaf drop-dst-ip-rate-limit {
            type uint32;
            units "packet";
            description
              "Number of RA packets discarded due to destination IP rate limit.";
          }
        }
        container ra-slots {
          description
            "List of RA packets in these slots.";
          list ra-slot {
            key "slot-id";
            description
              "Statistics of RA packets in the slot.";
            leaf slot-id {
              type string {
                length "1..24";
              }
              description
                "Slot ID.";
            }        
            leaf send-total {
              type uint32;
              units "packet";
              description
                "Number of send RA packets.";
            }
            leaf send-dip-ucast {
              type uint32;
              units "packet";
              description
                "Number of send RA packets with the destination address as a unicast address.";
            }
            leaf send-dip-mcast {
              type uint32;
              units "packet";
              description
                "Number of send RA packets with the destination address as a multicast address.";
            }
            leaf recv-total {
              type uint32;
              units "packet";
              description
                "Number of received RA packets.";
            }
            leaf recv-valid-total {
              type uint32;
              units "packet";
              description
                "Number of received valid RA packets.";
            }
            leaf recv-dip-ucast {
              type uint32;
              units "packet";
              description
                "Number of received RA packets with the destination address as a unicast address.";
            }
            leaf recv-dip-mcast {
              type uint32;
              units "packet";
              description
                "Number of RA packets with the destination address as a multicast address.";
            }
            leaf drop-total {
              type uint32;
              units "packet";
              description
                "Number of discarded RA packets.";
            }
            leaf drop-checksum-err {
              type uint32;
              units "packet";
              description
                "Number of RA packets discarded due to checksum errors.";
            }
            leaf drop-bad-len {
              type uint32;
              units "packet";
              description
                "Number of RA packets discarded due to bad packet length.";
            }
            leaf drop-bad-code {
              type uint32;
              units "packet";
              description
                "Number of RA packets discarded due to bad code.";
            }
            leaf drop-bad-hoplimit {
              type uint32;
              units "packet";
              description
                "Number of RA packets discarded due to bad hoplimit.";
            }
            leaf drop-bad-src-mac {
              type uint32;
              units "packet";
              description
                "Number of RA packets discarded due to bad source MAC addresses.";
            }
            leaf drop-bad-dst-mac {
              type uint32;
              units "packet";
              description
                "Number of RA packets discarded due to bad destination MAC addresses.";
            }
            leaf drop-bad-tgt-mac {
              type uint32;
              units "packet";
              description
                "Number of RA packets discarded due to bad target MAC addresses.";
            }
            leaf drop-bad-src-ip {
              type uint32;
              units "packet";
              description
                "Number of RA packets discarded due to bad source IP addresses.";
            }
            leaf drop-bad-dst-ip {
              type uint32;
              units "packet";
              description
                "Number of RA packets discarded due to bad destination IP addresses.";
            }
            leaf drop-bad-option {
              type uint32;
              units "packet";
              description
                "Number of RA packets discarded due to bad options.";
            }
            leaf drop-local-addr {
              type uint32;
              units "packet";
              description
                "Number of RA packets discarded because the source address is the local address.";
            }        
            leaf drop-mac-check {
              type uint32;
              units "packet";
              description
                "Number of RA packets discarded due to source MAC address consistency check errors.";
            }
            leaf drop-rate-limit {
              type uint32;
              units "packet";
              description
                "Number of RA packets discarded due to global rate limit.";
            }
            leaf drop-src-mac-attack {
              type uint32;
              units "packet";
              description
                "Number of RA packets discarded due to source MAC address attacks.";
            }
            leaf drop-src-mac-rate-limit {
              type uint32;
              units "packet";
              description
                "Number of RA packets discarded due to source MAC rate limit.";
            }
            leaf drop-src-ip-rate-limit {
              type uint32;
              units "packet";
              description
                "Number of RA packets discarded due to source IP rate limit.";
            }
            leaf drop-if-src-ip-rate-limit {
              type uint32;
              units "packet";
              description
                "Number of RA packets discarded due to interface source IP rate limit.";
            }
            leaf drop-if-rate-limit {
              type uint32;
              units "packet";
              description
                "Number of RA packets discarded due to interface rate limit.";
            }
            leaf drop-lr-rate-limit {
              type uint32;
              units "packet";
              description
                "Number of RA packets discarded due to LR rate limit.";
            }
            leaf drop-dst-ip-rate-limit {
              type uint32;
              units "packet";
              description
                "Number of RA packets discarded due to destination IP rate limit.";
            }
          }        
        }
        container ra-ifs {
          description
            "List of RA packets in these interfaces.";
          list ra-if {
            key "if-name";
            description
              "Statistics of RA packets in the interface.";
            leaf if-name {
              type leafref {
                path "/ifm:ifm/ifm:interfaces/ifm:interface/ifm:name";
              }
              description
                "Interface name.";
            }          
            leaf send-total {
              type uint32;
              units "packet";
              description
                "Number of send RA packets.";
            }
            leaf send-dip-ucast {
              type uint32;
              units "packet";
              description
                "Number of send RA packets with the destination address as a unicast address.";
            }
            leaf send-dip-mcast {
              type uint32;
              units "packet";
              description
                "Number of send RA packets with the destination address as a multicast address.";
            }
            leaf recv-total {
              type uint32;
              units "packet";
              description
                "Number of received RA packets.";
            }
            leaf recv-valid-total {
              type uint32;
              units "packet";
              description
                "Number of received valid RA packets.";
            }
            leaf recv-dip-ucast {
              type uint32;
              units "packet";
              description
                "Number of received RA packets with the destination address as a unicast address.";
            }
            leaf recv-dip-mcast {
              type uint32;
              units "packet";
              description
                "Number of RA packets with the destination address as a multicast address.";
            }
            leaf drop-total {
              type uint32;
              units "packet";
              description
                "Number of discarded RA packets.";
            }
            leaf drop-checksum-err {
              type uint32;
              units "packet";
              description
                "Number of RA packets discarded due to checksum errors.";
            }
            leaf drop-bad-len {
              type uint32;
              units "packet";
              description
                "Number of RA packets discarded due to bad packet length.";
            }
            leaf drop-bad-code {
              type uint32;
              units "packet";
              description
                "Number of RA packets discarded due to bad code.";
            }
            leaf drop-bad-hoplimit {
              type uint32;
              units "packet";
              description
                "Number of RA packets discarded due to bad hoplimit.";
            }
            leaf drop-bad-src-mac {
              type uint32;
              units "packet";
              description
                "Number of RA packets discarded due to bad source MAC addresses.";
            }
            leaf drop-bad-dst-mac {
              type uint32;
              units "packet";
              description
                "Number of RA packets discarded due to bad destination MAC addresses.";
            }
            leaf drop-bad-tgt-mac {
              type uint32;
              units "packet";
              description
                "Number of RA packets discarded due to bad target MAC addresses.";
            }
            leaf drop-bad-src-ip {
              type uint32;
              units "packet";
              description
                "Number of RA packets discarded due to bad source IP addresses.";
            }
            leaf drop-bad-dst-ip {
              type uint32;
              units "packet";
              description
                "Number of RA packets discarded due to bad destination IP addresses.";
            }
            leaf drop-bad-option {
              type uint32;
              units "packet";
              description
                "Number of RA packets discarded due to bad options.";
            }
            leaf drop-local-addr {
              type uint32;
              units "packet";
              description
                "Number of RA packets discarded because the source address is the local address.";
            }        
            leaf drop-mac-check {
              type uint32;
              units "packet";
              description
                "Number of RA packets discarded due to source MAC address consistency check errors.";
            }
            leaf drop-rate-limit {
              type uint32;
              units "packet";
              description
                "Number of RA packets discarded due to global rate limit.";
            }
            leaf drop-src-mac-attack {
              type uint32;
              units "packet";
              description
                "Number of RA packets discarded due to source MAC address attacks.";
            }
            leaf drop-src-mac-rate-limit {
              type uint32;
              units "packet";
              description
                "Number of RA packets discarded due to source MAC rate limit.";
            }
            leaf drop-src-ip-rate-limit {
              type uint32;
              units "packet";
              description
                "Number of RA packets discarded due to source IP rate limit.";
            }
            leaf drop-if-src-ip-rate-limit {
              type uint32;
              units "packet";
              description
                "Number of RA packets discarded due to interface source IP rate limit.";
            }
            leaf drop-if-rate-limit {
              type uint32;
              units "packet";
              description
                "Number of RA packets discarded due to interface rate limit.";
            }
            leaf drop-lr-rate-limit {
              type uint32;
              units "packet";
              description
                "Number of RA packets discarded due to LR rate limit.";
            }
            leaf drop-dst-ip-rate-limit {
              type uint32;
              units "packet";
              description
                "Number of RA packets discarded due to destination IP rate limit.";
            }
          }
        }
      }
      container ndmiss-stats {
        description
          "Statistics of ND miss packets.";
        container ndmiss-global {
          description
            "Statistics of global ND miss packets.";
          leaf recv-total {
            type uint32;
            units "packet";
            description
              "Number of received ND miss packets.";
          }
          leaf recv-valid-total {
            type uint32;
            units "packet";
            description
              "Number of received valid ND miss packets.";
          }
          leaf drop-total {
            type uint32;
            units "packet";
            description
              "Number of discarded ND miss packets.";
          }
          leaf drop-rate-limit {
            type uint32;
            units "packet";
            description
              "Number of ND miss packets discarded due to global rate limit.";
          }
          leaf drop-if-rate-limit {
            type uint32;
            units "packet";
            description
              "Number of ND miss discarded due to interface rate limit.";
          }
          leaf drop-lr-rate-limit {
            type uint32;
            units "packet";
            description
              "Number of ND miss discarded due to LR rate limit.";
          }
          leaf drop-src-ip-rate-limit {
            type uint32;
            units "packet";
            description
              "Number of ND miss discarded due to source IP rate limit.";
          }
          leaf drop-if-src-ip-rate-limit {
            type uint32;
            units "packet";
            description
              "Number of ND miss discarded due to interface source IP rate limit.";
          }
        }
        container ndmiss-slots {
          description
            "List of ND miss packets in these slots.";
          list ndmiss-slot {
            key "slot-id";
            description
              "Statistics of ND miss packets in the slot.";
            leaf slot-id {
              type string {
                length "1..24";
              }
              description
                "Slot ID.";
            }        
            leaf recv-total {
              type uint32;

              units "packet";

              description
                "Number of received ND miss packets.";
            }
            leaf recv-valid-total {
              type uint32;
              units "packet";
              description
                "Number of received valid ND miss packets.";
            }
            leaf drop-total {
              type uint32;
              units "packet";
              description
                "Number of discarded ND miss packets.";
            }
            leaf drop-rate-limit {
              type uint32;
              units "packet";
              description
                "Number of ND miss packets discarded due to global rate limit.";
            }
            leaf drop-if-rate-limit {
              type uint32;
              units "packet";
              description
                "Number of ND miss discarded due to interface rate limit.";
            }
            leaf drop-lr-rate-limit {
              type uint32;
              units "packet";
              description
                "Number of ND miss discarded due to LR rate limit.";
            }
            leaf drop-src-ip-rate-limit {
              type uint32;
              units "packet";
              description
                "Number of ND miss discarded due to source IP rate limit.";
            }
            leaf drop-if-src-ip-rate-limit {
              type uint32;
              units "packet";
              description
                "Number of ND miss discarded due to interface source IP rate limit.";
            }
          }        
        }
        container ndmiss-ifs {
          description
            "List of ND miss packets in these interfaces.";
          list ndmiss-if {
            key "if-name";
            description
              "Statistics of ND miss packets in the interface.";
            leaf if-name {
              type leafref {
                path "/ifm:ifm/ifm:interfaces/ifm:interface/ifm:name";
              }
              description
                "Interface name.";
            }          
            leaf recv-total {
              type uint32;
              units "packet";
              description
                "Number of received ND miss packets.";
            }
            leaf recv-valid-total {
              type uint32;
              units "packet";
              description
                "Number of received valid ND miss packets.";
            }
            leaf drop-total {
              type uint32;
              units "packet";
              description
                "Number of discarded ND miss packets.";
            }
            leaf drop-rate-limit {
              type uint32;
              units "packet";
              description
                "Number of ND miss packets discarded due to global rate limit.";
            }
            leaf drop-if-rate-limit {
              type uint32;
              units "packet";
              description
                "Number of ND miss discarded due to interface rate limit.";
            }
            leaf drop-lr-rate-limit {
              type uint32;
              units "packet";
              description
                "Number of ND miss discarded due to LR rate limit.";
            }
            leaf drop-src-ip-rate-limit {
              type uint32;
              units "packet";
              description
                "Number of ND miss discarded due to source IP rate limit.";
            }
            leaf drop-if-src-ip-rate-limit {
              type uint32;
              units "packet";
              description
                "Number of ND miss discarded due to interface source IP rate limit.";
            }
          }
        }
      }
      container proxy-packet-stats {
        config false;
        description
          "Statistics of ND proxy packets.";
        container proxy-packet-global {
          description
            "Statistics of global ND proxy packets.";
          leaf ns-recv-total {
            type uint32;
            units "packet";
            description
              "Number of received NS packets.";
          }
          leaf ns-recv-unicast {
            type uint32;
            units "packet";
            description
              "Number of received NS messages with a unicast address as the destination address.";
          }
          leaf ns-recv-multicast {
            type uint32;
            units "packet";
            description
              "Number of received NS messages with a multicast address as the destination address.";
          }
          leaf ns-drop-total {
            type uint32;
            units "packet";
            description
              "Number of discarded ND proxy packets.";
          }
          leaf ns-drop-no-router {
            type uint32;
            units "packet";
            description
              "Number of NS messages discarded due to lack of routes.";
          }
          leaf ns-drop-no-entry {
            type uint32;
            units "packet";
            description
              "Number of NS messages discarded due to lack of ND entries.";
          }
          leaf ns-drop-rate-limit {
            type uint32;
            units "packet";
            description
              "Number of NS messages discarded due to rate limit.";
          }
          leaf ns-drop-other {
            type uint32;
            units "packet";
            description
              "Number of NS messages discarded due to other reasons.";
          }
          leaf na-send-total {
            type uint32;
            units "packet";
            description
              "Number of send NA packets.";
          }
          leaf na-send-anyway {
            type uint32;
            units "packet";
            description
              "Number of NA messages sent in any proxy ND mode.";
          }
          leaf na-send-route {
            type uint32;
            units "packet";
            description
              "Number of NA messages sent in routed proxy ND mode.";
          }
          leaf na-send-inner-vlan {
            type uint32;
            units "packet";
            description
              "Number of NA messages sent in inner-VLAN proxy ND mode.";
          }
          leaf na-send-intra-vlan {
            type uint32;
            units "packet";
            description
              "Number of NA messages sent in intra-VLAN proxy ND mode.";
          }
          leaf na-send-local {
            type uint32;
            units "packet";
            description
              "Number of NA messages sent in local proxy ND mode.";
          }
        }
        container proxy-packet-slots {
          description
            "List of statistics for ND proxy packets in different slots.";
          list proxy-packet-slot {
            key "slot-id";
            description
              "Statistics of ND proxy packets in the slot.";
            leaf slot-id {
              type string {
                length "1..24";
              }
              description
                "Slot ID.";
            }
            leaf ns-recv-total {
              type uint32;
              units "packet";
              description
                "Number of received NS packets.";
            }
            leaf ns-recv-unicast {
              type uint32;
              units "packet";
              description
                "Number of received NS messages with a unicast address as the destination address.";
            }
            leaf ns-recv-multicast {
              type uint32;
              units "packet";
              description
                "Number of received NS messages with a multicast address as the destination address.";
            }
            leaf ns-drop-total {
              type uint32;
              units "packet";
              description
                "Number of discarded ND proxy packets.";
            }
            leaf ns-drop-no-router {
              type uint32;
              units "packet";
              description
                "Number of NS messages discarded due to lack of routes.";
            }
            leaf ns-drop-no-entry {
              type uint32;
              units "packet";
              description
                "Number of NS messages discarded due to lack of ND entries.";
            }
            leaf ns-drop-rate-limit {
              type uint32;
              units "packet";
              description
                "Number of NS messages discarded due to rate limit.";
            }
            leaf ns-drop-other {
              type uint32;
              units "packet";
              description
                "Number of NS messages discarded due to other reasons.";
            }
            leaf na-send-total {
              type uint32;
              units "packet";
              description
                "Number of send NA packets.";
            }
            leaf na-send-anyway {
              type uint32;
              units "packet";
              description
                "Number of NA messages sent in any proxy ND mode.";
            }
            leaf na-send-route {
              type uint32;
              units "packet";
              description
                "Number of NA messages sent in routed proxy ND mode.";
            }
            leaf na-send-inner-vlan {
              type uint32;
              units "packet";
              description
                "Number of NA messages sent in inner-VLAN proxy ND mode.";
            }
            leaf na-send-intra-vlan {
              type uint32;
              units "packet";
              description
                "Number of NA messages sent in intra-VLAN proxy ND mode.";
            }
            leaf na-send-local {
              type uint32;
              units "packet";
              description
                "Number of NA messages sent in local proxy ND mode.";
            }
          }
        }
        container proxy-packet-ifs {
          description
            "List of statistics for ND proxy packets in different interfaces.";
          list proxy-packet-if {
            key "if-name";
            description
              "Statistics of ND proxy packets in the interface.";
            leaf if-name {
              type leafref {
                path "/ifm:ifm/ifm:interfaces/ifm:interface/ifm:name";
              }
              description
                "Interface name.";
            }
            leaf ns-recv-total {
              type uint32;
              units "packet";
              description
                "Number of received NS packets.";
            }
            leaf ns-recv-unicast {
              type uint32;
              units "packet";
              description
                "Number of received NS messages with a unicast address as the destination address.";
            }
            leaf ns-recv-multicast {
              type uint32;
              units "packet";
              description
                "Number of received NS messages with a multicast address as the destination address.";
            }
            leaf ns-drop-total {
              type uint32;
              units "packet";
              description
                "Number of discarded ND proxy packets.";
            }
            leaf ns-drop-no-router {
              type uint32;
              units "packet";
              description
                "Number of NS messages discarded due to lack of routes.";
            }
            leaf ns-drop-no-entry {
              type uint32;
              units "packet";
              description
                "Number of NS messages discarded due to lack of ND entries.";
            }
            leaf ns-drop-rate-limit {
              type uint32;
              units "packet";
              description
                "Number of NS messages discarded due to rate limit.";
            }
            leaf ns-drop-other {
              type uint32;
              units "packet";
              description
                "Number of NS messages discarded due to other reasons.";
            }
            leaf na-send-total {
              type uint32;
              units "packet";
              description
                "Number of send NA packets.";
            }
            leaf na-send-anyway {
              type uint32;
              units "packet";
              description
                "Number of NA messages sent in any proxy ND mode.";
            }
            leaf na-send-route {
              type uint32;
              units "packet";
              description
                "Number of NA messages sent in routed proxy ND mode.";
            }
            leaf na-send-inner-vlan {
              type uint32;
              units "packet";
              description
                "Number of NA messages sent in inner-VLAN proxy ND mode.";
            }
            leaf na-send-intra-vlan {
              type uint32;
              units "packet";
              description
                "Number of NA messages sent in intra-VLAN proxy ND mode.";
            }
            leaf na-send-local {
              type uint32;
              units "packet";
              description
                "Number of NA messages sent in local proxy ND mode.";
            }
          }
        }
      }
    }
    container anti-attack {
      description
        "Configure ND anti-attack for global.";
      container source-mac-receive {
        description
          "Configure the ND anti-attack based on packet source MAC address.";
        container every-mac-rate-limits {
          description
            "List of rate limits for receiving ND packets based on every source MAC address.";
          list every-mac-rate-limit {
            key "packet-type";
            description
              "Configure the rate limit for receiving ND packets based on every source MAC address.";
            leaf packet-type {
              type nd-pkt-type;
              description
                "ND packet type.";
            }
            leaf value {
              type uint16 {
                range "0..5000";
              }
              units "pps";
              mandatory true;
              description
                "Rate limit of receiving ND packet.";
            }
          }
        }
        container mac-rate-limits {
          description
            "List of rate limits for receiving ND packets based on specified source MAC address.";
          list mac-rate-limit {
            key "packet-type mac-addr";
            description
              "Configure the rate limit for receiving ND packets based on specified source MAC address.";
            leaf packet-type {
              type nd-pkt-type;
              description
                "ND packet type.";
            }
            leaf mac-addr {
              type pub-type:mac-address {
                pattern '[0-9a-fA-F][0|2|4|6|8|aA|cC|eE][0-9a-fA-F]{2}(-[0-9a-fA-F]{4}){2}';
              }
              description
                "Source MAC address.";
            }
            leaf value {
              type uint16 {
                range "0..5000";
              }
              units "pps";
              mandatory true;
              description
                "Rate limit of receiving ND packet.";
            }
          }
        }
        container attack-detection {
          description
            "Configure ND attack detection.";
          container detection-configuration {
            description
              "Configure ND attack detection based on source MAC address.";
            leaf detect-mode {
              type nd-detection-mode;
              default "monitor";
              description
                "Detection mode of source MAC attack entries.";
            }
            leaf aging-time {
              type uint32 {
                range "60..6000";
              }
              units "s";
              default "300";
              description
                "Aging time of source MAC attack entries.";
            }
            leaf max-detect-number {
              type uint32 {
                range "10..2048";
              }
              default "1024";
              description
                "Number of detection MAC addresses.";
            }
            leaf max-entry-number {
              type uint32 {
                range "10..2048";
              }
              default "1024";
              description
                "Number of attack MAC addresses.";
            }
            leaf threshold {
              type uint32 {
                range "1..5000";
              }
              default "30";
              description
                "Attack detection threshold for ND messages with fixed source MAC addresses.";
            }
          }
          container exclude-mac-lists {
            description
              "List of protected MAC address.";
            list exclude-mac-list {
              key "exclude-mac-addr";
              description
                "Configure the protected MAC address, the device does not filter out ND attack messages sent from this MAC address.";
              leaf exclude-mac-addr {
                type pub-type:mac-address;
                description
                  "Protected MAC address.";
              }
            }
          }
          container dropped-packet-stats {
            config false;
            description
              "List of statistics for dropped ND attack messages with fixed source MAC addresses.";
            list dropped-packet-stat {
              key "if-name mac-address";
              description
                "Statistics of dropped ND attack messages with fixed source MAC addresses.";
              leaf if-name {
                type leafref {
                  path "/ifm:ifm/ifm:interfaces/ifm:interface/ifm:name";
                }
                description
                  "Interface name.";
              }
              leaf mac-address {
                type pub-type:mac-address;
                description
                  "Source MAC address.";
              }
              leaf dropped-ns {
                type uint32;
                description
                  "Number of dropped NS packets.";
              }
              leaf dropped-na {
                type uint32;
                description
                  "Number of dropped NA packets.";
              }
              leaf dropped-rs {
                type uint32;
                description
                  "Number of dropped RS packets.";
              }
              leaf dropped-ra {
                type uint32;
                description
                  "Number of dropped RA packets.";
              }
            }
          }
          container source-mac-states {
            config false;
            description
              "List of information about ND attack entries with fixed source MAC addresses.";
            list source-mac-state {
              key "if-name mac-address";
              description
                "Statistics of ND attack entries with fixed source MAC addresses.";
              leaf if-name {
                type leafref {
                  path "/ifm:ifm/ifm:interfaces/ifm:interface/ifm:name";
                }
                description
                  "Interface name.";
              }
              leaf mac-address {
                type pub-type:mac-address;
                description
                  "Source MAC address.";
              }
              leaf expire-time {
                type uint32;
                units "s";
                description
                  "Expire time.";
              }
            }
          }
        }
      }
      container source-ip-receive {
        description
          "Configure the ND anti-attack based on packet or miss source IP address.";
        container every-ip-rate-limits {
          description
            "List of rate limits for receiving ND packets or ND miss based on every source IP address.";
          list every-ip-rate-limit {
            key "packet-type";
            description
              "Configure the rate limit for receiving ND packets or ND miss based on every source IP address.";
            leaf packet-type {
              type nd-pkt-evt-type;
              description
                "ND packet type or ND miss.";
            }
            leaf value {
              type uint16 {
                range "0..5000";
              }
              units "pps";
              mandatory true;
              description
                "Rate limit of receiving ND packet or ND miss.";
            }
          }
        }
        uses nd-ip-rate-limits-type;
      }
      container destination-ip-receive {
        description
          "Configure the ND anti-attack based on packet destination IP address.";
        container every-ip-rate-limits {
          description
            "List of rate limits for receiving ND packets based on every destination IP address.";
          list every-ip-rate-limit {
            key "packet-type";
            description
              "Configure the rate limit for receiving ND packets based on every destination IP address.";
            leaf packet-type {
              type nd-pkt-type;
              description
                "ND packet type.";
            }
            leaf value {
              type uint16 {
                range "0..5000";
              }
              units "pps";
              mandatory true;
              description
                "Rate limit of receiving ND packet.";
            }
          }
        }
        container ip-rate-limits {
          description
            "List of rate limits for receiving ND packets based on specified destination IP address.";
          list ip-rate-limit {
            key "packet-type ipv6-addr";
            description
              "Configure the rate limit for receiving ND packets based on specified destination IP address.";
            leaf packet-type {
              type nd-pkt-type;
              description
                "ND packet type.";
            }
            leaf ipv6-addr {
              type inet:ipv6-address-no-zone;
              description
                "Destination IPv6 address, the address cannot be the unspecified address.";
            }
            leaf value {
              type uint16 {
                range "0..5000";
              }
              units "pps";
              mandatory true;
              description
                "Rate limit of receiving ND packet.";
            }
          }
        }
      }
      container target-ip-receive {
        description
          "Configure the ND anti-attack based on packet target IP address.";
        container every-ip-rate-limits {
          description
            "List of rate limits for receiving ND packets based on every target IP address.";
          list every-ip-rate-limit {
            key "packet-type";
            description
              "Configure the rate limit for receiving ND packets based on every target IP address.";
            leaf packet-type {
              type nd-tgt-pkt-type;
              description
                "ND packet type.";
            }
            leaf value {
              type uint16 {
                range "0..5000";
              }
              units "pps";
              mandatory true;
              description
                "Rate limit of receiving ND packet.";
            }
          }
        }
        container ip-rate-limits {
          description
            "List of rate limits for receiving ND packets based on specified target IP address.";
          list ip-rate-limit {
            key "packet-type ipv6-addr";
            description
              "Configure the rate limit for receiving ND packets based on specified target IP address.";
            leaf packet-type {
              type nd-tgt-pkt-type;
              description
                "ND packet type.";
            }
            leaf ipv6-addr {
              type inet:ipv6-address-no-zone;
              description
                "Target IPv6 address, the address cannot be the unspecified address or a multicast address.";
            }
            leaf value {
              type uint16 {
                range "0..5000";
              }
              units "pps";
              mandatory true;
              description
                "Rate limit of receiving ND packet.";
            }
          }
        }
      }
    }
    container send-rate-limit{
      description
        "Configure ND send rate limit for global.";
      container multicast-rate-limits {
        description
          "List of ND multicast packet sending rate limits.";
        list multicast-rate-limit {
          key "packet-type";
          description
            "Configure the rate limit of sending ND multicast packet.";
          leaf packet-type {
            type nd-pkt-type;
            description
              "ND packet type.";
          }
          leaf value {
            type uint16 {
              range "1..10240";
            }
            units "pps";
            must "((../packet-type = 'NA') and (../value <= 10240)) or (not(../packet-type = 'NA') and (../value <= 1000))";
            mandatory true;
            description
              "Rate limit of sending ND multicast packet, when the packet type is NS, RS or RA, the maximum value is 1000.";
          }
        }
      }
    }
    container anti-attack-records {
      config false;
      description
        "Statistics of query anti-attack record.";
      container packet-records {
        description
          "List of query packet anti-attack record.";
        list packet-record {
          key "if-name record-index";
          description
            "Statistics of query packet anti-attack record.";
          leaf if-name {
            type leafref {
              path "/ifm:ifm/ifm:interfaces/ifm:interface/ifm:name";
            }
            description
              "Interface name.";
          }
          leaf record-index {
            type uint32;
            description
              "Record index.";
          }
          leaf packet-type {
            type nd-pkt-type;
            description
              "ND packet type.";
          }
          leaf source-address {
            type inet:ipv6-address-no-zone;
            description
              "Source IPv6 address of a packet.";
          }
          leaf dest-address {
            type inet:ipv6-address-no-zone;
            description
              "Destination IPv6 address of a packet.";
          }
          leaf target-address {
            type inet:ipv6-address-no-zone;
            description
              "Target IPv6 address of a packet.";
          }
          leaf source-mac {
            type pub-type:mac-address;
            description
              "Source MAC address of a packet.";
          }
          leaf dest-mac {
            type pub-type:mac-address;
            description
              "Destination MAC address of a packet.";
          }
          leaf pe-vlan {
            type uint32 {
              range "1..4094";
            }
            description
              "Outer VLAN tag.";
          }
          leaf ce-vlan {
            type uint32 {
              range "1..4094";
            }
            description
              "Inner VLAN tag.";
          }
          leaf attack-times {
            type uint32;
            description
              "Attacked times.";
          }
          leaf last-attack-time {
            type yang:date-and-time;
              description
                "Last attacked time.";
          }
          leaf dropped-reason {
            type string {
              length "1..63";
            }
            description
              "Dropped reason.";
          }
        }
      }
      container miss-records {
        description
          "List of query miss anti-attack record.";
        list miss-record {
          key "if-name target-address";
          description
            "Statistics of query miss anti-attack record.";
          leaf if-name {
            type leafref {
              path "/ifm:ifm/ifm:interfaces/ifm:interface/ifm:name";
            }
            description
              "Interface name.";
          }
          leaf target-address {
            type inet:ipv6-address-no-zone;
            description
              "Target IPv6 address of a miss message.";
          }
          leaf source-address {
            type inet:ipv6-address-no-zone;
            description
              "Source IPv6 address of a miss message.";
          }
        }
      }
    }
    container ipv6-neighbor-stats {
      config false;
      description
        "Statistics of IPv6 neighbors.";
      container entry-stats {
        description
          "Statistics of all ND entries.";
        container global-stats {
          description
            "Statistics of global ND entries.";
          leaf dynamic-entries {
            type uint32;
            description
              "Number of dynamic entries.";
          }
          leaf static-entries {
            type uint32;
            description
              "Number of static entries.";
          }
          leaf remote-entries {
            type uint32;
            description
              "Number of remote entries.";
          }
          leaf incomplete-dynamic-entries {
            type uint32;
            description
              "Number of dynamic entries in the incomplete state.";
          }
          leaf incomplete-static-entries {
            type uint32;
            description
              "Number of static entries in the incomplete state.";
          }
          leaf incomplete-remote-entries {
            type uint32;
            description
              "Number of remote entries in the incomplete state.";
          }
          leaf reach-dynamic-entries {
            type uint32;
            description
              "Number of dynamic entries in the reach state.";
          }
          leaf reach-static-entries {
            type uint32;
            description
              "Number of static entries in the reach state.";
          }
          leaf reach-remote-entries {
            type uint32;
            description
              "Number of remote entries in the reach state.";
          }
          leaf stale-dynamic-entries {
            type uint32;
            description
              "Number of dynamic entries in the stale state.";
          }
          leaf delay-dynamic-entries {
            type uint32;
            description
              "Number of dynamic entries in the delay state.";
          }
          leaf probe-dynamic-entries {
            type uint32;
            description
              "Number of dynamic entries in the probe state.";
          }
        }
        container interface-stats {
          description
            "List of statistics about ND entries on different interfaces.";
          list interface-stat {
            key "if-name";
            description
              "Statistics of ND entries on the interface.";
            leaf if-name {
              type leafref {
                path "/ifm:ifm/ifm:interfaces/ifm:interface/ifm:name";
              }
              description
                "Interface name.";
            }
            leaf dynamic-entries {
              type uint32;
              description
                "Number of dynamic entries.";
            }
            leaf static-entries {
              type uint32;
              description
                "Number of static entries.";
            }
            leaf remote-entries {
              type uint32;
              description
                "Number of remote entries.";
            }
            leaf incomplete-dynamic-entries {
              type uint32;
              description
                "Number of dynamic entries in the incomplete state.";
            }
            leaf incomplete-static-entries {
              type uint32;
              description
                "Number of static entries in the incomplete state.";
            }
            leaf incomplete-remote-entries {
              type uint32;
              description
                "Number of remote entries in the incomplete state.";
            }
            leaf reach-dynamic-entries {
              type uint32;
              description
                "Number of dynamic entries in the reach state.";
            }
            leaf reach-static-entries {
              type uint32;
              description
                "Number of static entries in the reach state.";
            }
            leaf reach-remote-entries {
              type uint32;
              description
                "Number of remote entries in the reach state.";
            }
            leaf stale-dynamic-entries {
              type uint32;
              description
                "Number of dynamic entries in the stale state.";
            }
            leaf delay-dynamic-entries {
              type uint32;
              description
                "Number of dynamic entries in the delay state.";
            }
            leaf probe-dynamic-entries {
              type uint32;
              description
                "Number of dynamic entries in the probe state.";
            }
          }
        }
        container slot-stats {
          description
            "List of statistics about ND entries on different slots.";
          list slot-stat {
            key "slot-id";
            description
              "Statistics of ND entries on the slot.";
            leaf slot-id {
              type string {
                length "1..24";
              }
              description
                "Slot ID.";
            }
            leaf dynamic-entries {
              type uint32;
              description
                "Number of dynamic entries.";
            }
            leaf static-entries {
              type uint32;
              description
                "Number of static entries.";
            }
            leaf remote-entries {
              type uint32;
              description
                "Number of remote entries.";
            }
            leaf incomplete-dynamic-entries {
              type uint32;
              description
                "Number of dynamic entries in the incomplete state.";
            }
            leaf incomplete-static-entries {
              type uint32;
              description
                "Number of static entries in the incomplete state.";
            }
            leaf incomplete-remote-entries {
              type uint32;
              description
                "Number of remote entries in the incomplete state.";
            }
            leaf reach-dynamic-entries {
              type uint32;
              description
                "Number of dynamic entries in the reach state.";
            }
            leaf reach-static-entries {
              type uint32;
              description
                "Number of static entries in the reach state.";
            }
            leaf reach-remote-entries {
              type uint32;
              description
                "Number of remote entries in the reach state.";
            }
            leaf stale-dynamic-entries {
              type uint32;
              description
                "Number of dynamic entries in the stale state.";
            }
            leaf delay-dynamic-entries {
              type uint32;
              description
                "Number of dynamic entries in the delay state.";
            }
            leaf probe-dynamic-entries {
              type uint32;
              description
                "Number of dynamic entries in the probe state.";
            }
          }
        }
      }
      container static-entry-stats {
        description
          "Statistics of static ND entries.";
        leaf max-entries {
          type uint32;
          description
            "Maximum number of static ND entries on each board.";
        }
        leaf configured-entries {
          type uint32;
          description
            "Number of static ND entries configured on all boards.";
        }
      }
      container free-resource-stats {
        description
          "List of available ND resources on the slots.";
        list free-resource-stat {
          key "slot-id";
          description
            "Statistics of available ND resources on a specified slot.";
            leaf slot-id {
              type string {
                length "1..24";
              }
              description
                "Slot ID.";
            }
          leaf physical-resource {
            type uint32;
            description
              "Number of available ND resources on physical interface.";
          }
          leaf physical-qinq-resource {
            type uint32;
            description
              "Number of available ND resources on physical sub-interface which QinQ VLAN tag termination is configured.";
          }
          leaf ve-resource {
            type uint32;
            description
              "Number of available ND resources on VE interface.";
          }
          leaf ve-qinq-resource {
            type uint32;
            description
              "Number of available ND resources on VE sub-interface which QinQ VLAN tag termination is configured.";
          }
          leaf trunk-resource {
            type uint32;
            description
              "Number of available ND resources on Eth-Trunk interface.";
          }
          leaf trunk-qinq-resource {
            type uint32;
            description
              "Number of available ND resources on Eth-Trunk sub-interface which QinQ VLAN tag termination is configured.";
          }
          leaf global-ve-resource {
            type uint32;
            description
              "Number of available ND resources on global VE interface.";
          }
          leaf global-ve-qinq-resource {
            type uint32;
            description
              "Number of available ND resources on global VE sub-interface which QinQ VLAN tag termination is configured.";
          }
          leaf vlanif-resource {
            type uint32;
            description
              "Number of available ND resources on VLANIF interface.";
          }
          leaf bdif-resource {
            type uint32;
            description
              "Number of available ND resources on BDIF interface.";
          }
        }
      }
    }
    container multicast-suppress-info {
      config false;
      description
        "Statistics of multicast-suppress configurations.";
      container multicast-suppress-records {
        description
          "List of infomation about ND multicast-suppress in all BDs.";
        list multicast-suppress-record {
          key "bd-id ipv6-addr";
          description
            "Statistics of ND multicast-suppress in a specified BD.";
          leaf bd-id {
            type uint32;
            description
              "Bridge-domain ID.";
          }
          leaf ipv6-addr {
            type inet:ipv6-address-no-zone;
            description
              "IPv6 address.";
          }
          leaf mac-address {
            type pub-type:mac-address;
            description
              "MAC address.";
          }
          leaf lifetime {
            type uint32;
            units "s";
            description
              "The lifetime of a proxy ND entry.";
          }
          leaf type {
            type nd-proxy-type;
            description
              "Type of a proxy ND entry.";
          }
          leaf r-flag {
            type boolean;
            description
              "R flag of an NA message.";
          }
          leaf o-flag {
            type boolean;
            description
              "O flag of an NA message.";
          }
        }
      }
    }
    container nd-dual-stats {
      config false;
      description
        "Statistics of ND dual packets.";
      container global-packet-stats {
        description
          "Statistics of global ND dual packets.";
        leaf packet-number {
          type uint32;
          description
            "Number of cached ND packets on the device.";
        }
        leaf packet-limit {
          type uint32;
          description
            "Upper limit of the number of ND packets cached on the device.";
        }
        leaf discarded-number {
          type uint32;
          description
            "Number of ND packets discarded on the device.";
        }
      }
      container interface-packet-stats {
        description
          "List of statistics about ND dual packets on different interfaces.";
        list interface-packet-stat {
          key "if-name";
          description
            "Statistics of ND dual packet on the interface.";
          leaf if-name {
            type leafref {
              path "/ifm:ifm/ifm:interfaces/ifm:interface/ifm:name";
            }
            description
              "Interface name.";
          }
        leaf packet-number {
          type uint32;
          description
            "Number of ND packets cached on the interface.";
        }
          leaf packet-limit {
            type uint32;
            description
              "Upper limit of the number of ND packets cached on the interface.";
          }
          leaf discarded-number {
            type uint32;
            description
              "Number of ND packets discarded on the interface.";
          }
        }
      }
      container packet-records {
        description
          "List of ND dual packet records.";
        list packet-record {
          key "if-name source-address target-address";
          description
            "Statistics of ND dual packet record.";
          leaf if-name {
            type leafref {
              path "/ifm:ifm/ifm:interfaces/ifm:interface/ifm:name";
            }
            description
              "Interface name.";
          }
          leaf source-address {
            type inet:ipv6-address-no-zone;
            description
              "Source IPv6 address of a packet.";
          }
          leaf target-address {
            type inet:ipv6-address-no-zone;
            description
              "Target IPv6 address of a packet.";
          }
          leaf dest-address {
            type inet:ipv6-address-no-zone;
            description
              "Destination IPv6 address of a packet.";
          }
          leaf packet-type {
            type nd-tgt-pkt-type;
            description
              "ND packet type.";
          }
          leaf source-mac {
            type pub-type:mac-address;
            description
              "Source MAC address of a packet.";
          }
          leaf dest-mac {
            type pub-type:mac-address;
            description
              "Destination MAC address of a packet.";
          }
          leaf pe-vid {
            type uint16 {
              range "1..4094";
            }
            description
              "Outer VLAN tag.";
          }
          leaf ce-vid {
            type uint16 {
              range "1..4094";
            }
            description
              "Inner VLAN tag.";
          }
        }
      }
    }
  }
  rpc nd-pkt-clear-all {
    description
      "To clear all ND statistics.";
    ext:node-ref "/ipv6-nd:ipv6-nd/ipv6-nd:nd-pkt-stats";
  }

  rpc ipv6-neighbor-clear {
    description
      "To clear IPv6 dynamic neighbors.";
    ext:node-ref "/ipv6-nd:ipv6-nd/ipv6-nd:ipv6-neighbors";
    input {
      choice clear-type {
        description
          "IPv6 neighbor clear type.";
        case if-ip {
          description
            "Clear by specified Interface name or Interface name and IPv6 address.";
          leaf if-name {
            type leafref {
              path "/ifm:ifm/ifm:interfaces/ifm:interface/ifm:name";
            }
            mandatory true;
            description
              "Interface name.";
          }
          leaf ipv6-addr {
            type inet:ipv6-address-no-zone;
            description
              "IPv6 address.";
          }
        }
      }
    }
  }

  rpc anti-attack-packet-record-clear {
    description
      "To clear packet anti-attack records.";
    ext:node-ref "/ipv6-nd:ipv6-nd/ipv6-nd:anti-attack-records/ipv6-nd:packet-records";
    input {
      leaf if-name {
        type leafref {
          path "/ifm:ifm/ifm:interfaces/ifm:interface/ifm:name";
        }
        description
          "Interface name.";
      }
    }
  }
  rpc anti-attack-miss-record-clear {
    description
      "To clear miss anti-attack records.";
    ext:node-ref "/ipv6-nd:ipv6-nd/ipv6-nd:anti-attack-records/ipv6-nd:miss-records";
    input {
      leaf if-name {
        type leafref {
          path "/ifm:ifm/ifm:interfaces/ifm:interface/ifm:name";
        }
        description
          "Interface name.";
      }
    }
  }
  rpc nd-dual-pkt-clear {
    description
      "To clear infomation about ND dual packets.";
    ext:node-ref "/ipv6-nd:ipv6-nd/ipv6-nd:nd-dual-stats";
    input {
      leaf if-name {
        type leafref {
          path "/ifm:ifm/ifm:interfaces/ifm:interface/ifm:name";
        }
        description
          "Interface name.";
      }
    }
  }
  rpc dynamic-proxy-nd-clear {
    description
      "To clear dynamic proxy ND entries.";
    ext:node-ref "/ipv6-nd:ipv6-nd/ipv6-nd:multicast-suppress-info/ipv6-nd:multicast-suppress-records/ipv6-nd:multicast-suppress-record";
    input {
      leaf bd-id {
        type uint32 {
          range "1..16777215";
        }
        description
          "Bridge-domain ID.";
      }
    }
  }
  rpc nd-proxy-stat-clear {
    description
      "To clear statistics about proxy ND.";
    ext:node-ref "/ipv6-nd:ipv6-nd/ipv6-nd:nd-pkt-stats/ipv6-nd:proxy-packet-stats";
  }
  rpc source-mac-stat-clear {
    description
      "To clear statistics about dropped ND attack messages with fixed source MAC addresses.";
    ext:node-ref "/ipv6-nd:ipv6-nd/ipv6-nd:anti-attack/ipv6-nd:source-mac-receive/ipv6-nd:dropped-packet-stats/ipv6-nd:dropped-packet-stat";
    input {
      leaf if-name {
        type leafref {
          path "/ifm:ifm/ifm:interfaces/ifm:interface/ifm:name";
        }
        description
          "Interface name.";
      }
    }
  }

  augment "/bd:bd/bd:instances/bd:instance" {
    description
      "List of Bridge-Domain Neighbor Multicast-Suppress Information.";
    container nd-bd-property {
      must "not(unicast-forward = 'true' and proxy-reply = 'true')";
      description
        "Configure Bridge-Domain neighbor multicast-suppress information.";
      leaf unicast-forward {
        type boolean;
        default "false";
        description
          "Enable/disable Bridge-Domain unicast forward.";
      }
      leaf proxy-reply {
        type boolean;
        default "false";
        description
          "Enable/disable Bridge-Domain proxy reply.";
      }
      leaf mismatch-discard {
        when "../unicast-forward='true' or ../proxy-reply='true'";
        type boolean;
        default "false";
        description
          "Enable/disable Bridge-Domain mismatch discard.";
      }
      leaf collect-host-flag {
        type boolean;
        default "false";
        description
          "Enable/disable host Information collecting.";
      }
      leaf dynamic-limit {
        type uint32 {
          range "0..16384";
        }
        default "256";
        description
          "Dynamic IPv6 neighbor cache entries.";
      }
      leaf router-flag {
        type boolean;
        default "true";
        description
          "Enable/disable R flag of NA packet.";
      }
      leaf dynamic-expire-time {
        type uint32 {
          range "60..86400";
        }
        units "s";
        default "900";
        description
          "Dynamic expire time.";
      }
      leaf unknown-options-unicast {
        when "../proxy-reply='true'";
        type boolean;
        default "false";
        description
          "Enable/disable processing of unrecognized options in NS messages.";
      }
    }
  }
  augment "/ifm:ifm/ifm:interfaces/ifm:interface/ip:ipv6" {
    when "../ifm:type!='Tunnel' and ../ifm:type!='LoopBack' and ../ifm:type!='ServiceIf' and ../ifm:type!='Virtual-if'";
    description
      "All configurations of the ND under the interface.";
    container nd-collection {
      description
        "Configure ND interface configurations.";
      container if-property {
        description
          "Configure ND interface configurations.";
        leaf retrans-timer {
          when "../../../../ifm:type!='Serial'";
          type uint32 {
            range "1000..4294967295";
          }
          units "ms";
          default "1000";
          description
            "To set the retransmission timer of a router.";
        }
        leaf nud-reach-time {
          when "../../../../ifm:type!='Ip-Trunk' and ../../../../ifm:type!='Pos' and ../../../../ifm:type!='Mp-group' and ../../../../ifm:type!='Serial'";
          type uint32 {
            range "1..3600000";
          }
          units "ms";
          default "1200000";
          description
            "To set the reachable time of a neighbor.";
        }
        leaf attempts-value {
          when "../../../../ifm:type!='Serial'";
          type uint32 {
            range "0..600";
          }
          default "1";
          description
            "To set the number of sent NS messages during DAD.";
        }
        leaf ns-mcast-flag {
          when "../../../../ethernet:ethernet/ethernet:l3-sub-interface/ethernet:dot1q-termination or ../../../../ethernet:ethernet/ethernet:l3-sub-interface/ethernet:qinq-termination";
          type nd-switch-state;
          default "off";
          description
            "Flag of enabling multicast.";
        }
        leaf max-dyn-nb-num {
          when "../../../../ifm:type!='Ip-Trunk' and ../../../../ifm:type!='Pos' and ../../../../ifm:type!='Mp-group' and ../../../../ifm:type!='Serial'";
          type uint64 {
            range "0..147456";
          }
          default "0";
          description
            "The maximum of limitation of dynamic neighbor.";
        }
        leaf dad-timeout {
          when "../../../../ethernet:ethernet/ethernet:l3-sub-interface/ethernet:dot1q-termination or ../../../../ethernet:ethernet/ethernet:l3-sub-interface/ethernet:qinq-termination";
          type uint32 {
            range "1..60";
          }
          units "s";
          default "1";
          description
            "Timeout of DAD.";
        }
        leaf nud-attempts {
          when "../../../../ifm:type!='Ip-Trunk' and ../../../../ifm:type!='Pos' and ../../../../ifm:type!='Mp-group' and ../../../../ifm:type!='Serial'";
          type uint8 {
            range "1..10";
          }
          default "3";
          description
            "ND entries NUD attempts.";
        }
        leaf na-glean {
          when "../../../../ifm:type!='Ip-Trunk' and ../../../../ifm:type!='Pos' and ../../../../ifm:type!='Mp-group' and ../../../../ifm:type!='Serial'";
          type nd-switch-state;
          default "off";
          description
            "Flag of generating NB when receiving NA packet.";
        }
        leaf ma-flag {
          when "../../../../ifm:type!='MEth' and ../../../../ifm:type!='Serial'";
          type nd-switch-state;
          default "off";
          description
            "Flag of obtaining the routable address through state-based automatic configuration.";
        }
        leaf o-flag {
          when "../../../../ifm:type!='MEth' and ../../../../ifm:type!='Serial'";
          type nd-switch-state;
          default "off";
          description
            "Flag of setting state-based automatic configuration.";
        }
        leaf ra-halt-flag {
          when "../../../../ifm:type!='MEth'";
          type nd-switch-state;
          default "on";
          description
            "To suppress the advertisement of RA packets.";
        }
        leaf max-interval {
          when "../../../../ifm:type!='MEth'";
          type uint32 {
            range "4..1800";
          }
          units "s";
          default "600";
          description
            "The maximum interval between periodic RA packets sent on this interface.";
        }
        leaf min-interval {
          when "../../../../ifm:type!='MEth'";
          type uint32 {
            range "3..1350";
          }
          units "s";
          must "../max-interval >= ../min-interval and ../min-interval <= 0.75 * ../max-interval";
          description
            "The minimum interval between periodic RA packets sent on this interface.";
        }
        leaf ra-lifetime {
          when "../../../../ifm:type!='MEth'";
          type uint32 {
            range "0|4..9000";
          }
          units "s";
          must "../ra-lifetime = 0 or (../ra-lifetime != 0 and ../ra-lifetime >= ../max-interval)";
          description
            "TTL of RA packets. If the value is 0, it implies that this node is not a router. And the value from 1 to 3 is invalid.";
        }
        leaf ra-preference {
          when "../../../../ifm:type!='MEth'";
          type nd-route-preference;
          default "medium";
          description
            "RA router preference.";
        }
        leaf ra-prefix-flag {
          when "../../../../ifm:type!='MEth'";
          type nd-switch-state;
          default "on";
          description
            "Flag of RA packet carry prefix information.";
        }
        leaf ra-mtu-flag {
          when "../../../../ifm:type!='MEth'";
          type nd-switch-state;
          default "on";
          description
            "Flag of RA packet carry MTU option.";
        }
        leaf strict-flag {
          when "../../../../ifm:type!='Mp-group' and ../../../../ifm:type!='Serial'";
          type boolean;
          default "false";
          description
            "Enable/disable strict security mode.";
        }
        leaf ts-fuzz-factor {
          when "../../../../ifm:type!='Serial'";
          type uint16 {
            range "0..1000";
          }
          units "s";
          default "1";
          description
            "Fuzz factor for timestamp option.";
        }
        leaf ts-clock-drift {
          when "../../../../ifm:type!='Serial'";
          type uint8 {
            range "0..100";
          }
          default "1";
          description
            "Drift for timestamp option.";
        }
        leaf ts-delta {
          when "../../../../ifm:type!='Serial'";
          type uint16 {
            range "0..1000";
          }
          units "s";
          default "300";
          description
            "Delta for timestamp option.";
        }
        leaf rsa-min-key-len {
          when "../../../../ifm:type!='Serial'";
          type uint16 {
            range "384..4096";
          }
          units "bit";
          must "(../rsa-min-key-len<=../rsa-max-key-len)";
          default "512";
          description
            "The minimum length of acceptable RSA key pair.";
        }
        leaf rsa-max-key-len {
          when "../../../../ifm:type!='Serial'";
          type uint16 {
            range "384..4096";
          }
          units "bit";
          default "2048";
          description
            "The maximum length of acceptable RSA key pair.";
        }
        leaf stale-time {
          when "../../../../ifm:type!='Ip-Trunk' and ../../../../ifm:type!='Pos' and ../../../../ifm:type!='Mp-group' and ../../../../ifm:type!='Serial'";
          type uint32 {
            range "60..172800";
          }
          units "s";
          description
            "Aging time of the stale state.";
        }
        leaf collect-host-flag {
          when "../../../../ifm:type='Vbdif'";
          type nd-switch-state;
          default "off";
          description
            "Flag of collecting host Information.";
        }
        leaf generate-rd-enable {
          when "../../../../ifm:type='Vbdif'";
          type nd-switch-state;
          default "off";
          description
            "Flag of generating redirect ND table.";
        }
        leaf nud-interval {
          when "../../../../ifm:type!='Ip-Trunk' and ../../../../ifm:type!='Pos' and ../../../../ifm:type!='Mp-group' and ../../../../ifm:type!='Serial'";
          type uint32 {
            range "1000..4294967295";
          }
          units "ms";
          default "5000";
          description
            "ND entries NUD interval.";
        }
        leaf hop-limit {
          type uint8 {
            range "0..255";
          }
          description
            "IPv6 packet hop limit.";
        }
        leaf link-down-trigger-del-flag {
          when "../../../../ifm:type='Vlanif'";
          type nd-switch-state;
          default "off";
          description
            "Flag of link down trigger fast deletion of ND entries.";
        }
      }
      container proxys {
        when "../../../ifm:type!='MEth' and ../../../ifm:type!='Ip-Trunk' and ../../../ifm:type!='Serial' and ../../../ifm:type!='Pos' and ../../../ifm:type!='Mp-group'";
        description
          "Configure list of ND proxy.";
        leaf route-proxy {
          when "../../../../ifm:type!='PW-VE'";
          type nd-switch-state;
          default "off";
          description
            "Router proxy.";
        }
        leaf inner-vlan-proxy {
          when "(../../../../ifm:class='sub-interface' and ../../../../ifm:type!='PW-VE') or ../../../../ifm:type='Vlanif'";
          type nd-switch-state;
          default "off";
          description
            "InnerVLAN proxy.";
        }
        leaf inter-vlan-proxy {
          when "(../../../../ifm:class='sub-interface' and ../../../../ifm:type!='PW-VE') or ../../../../ifm:type='Vlanif'";
          type nd-switch-state;
          default "off";
          description
            "InterVLAN proxy.";
        }
        leaf anyway-proxy {
          type nd-switch-state;
          default "off";
          description
            "Anyway proxy.";
        }
        leaf local-proxy {
          when "../../../../ifm:type='Vbdif'";
          type nd-switch-state;
          default "off";
          description
            "Local proxy.";
        }
      }
      container anti-attack {
        when "../../../ifm:type!='Serial'";
        description
          "Configure ND anti-attack for interface.";
        container receive-rate-limits {
          description
            "List of rate limits for receiving ND packets.";
          list receive-rate-limit {
            key "type";
            description
              "Configure the rate limit for receiving ND packet or ND miss.";
            leaf type {
              type nd-pkt-evt-type;
              description
                "ND packet type or ND miss.";
            }
            leaf value {
              type uint16 {
                range "0..5000";
              }
              units "pps";
              mandatory true;
              description
                "Rate limit of receiving ND packet or ND miss.";
            }
          }
        }
        container source-ip-receive {
          description
            "Configure the ND anti-attack based on packet or miss source IP address.";
          uses nd-ip-rate-limits-type;
        }
      }
      container static-neighbor {
        description
          "Configure static neighbor entry.";
        container common-ifs {
          when "../../../../ifm:type!='Vlanif' and ../../../../ifm:type!='Vbdif'";
          description
            "List of static neighbor entry on common interface.";
          list common-if {
            key "ipv6-addr";
            description
              "Configure static neighbor entry on common interface.";
            leaf ipv6-addr {
              type inet:ipv6-address-no-zone;
              description
                "IPv6 address of a static neighbor entry.";
            }
            leaf mac-addr {
              type pub-type:mac-address;
              mandatory true;
              description
                "MAC address.";
            }
          }
        }
        container dot1q-termination-ifs {
          when "../../../../ethernet:ethernet/ethernet:l3-sub-interface/ethernet:dot1q-termination";
          description
            "List of static neighbor entry on dot1q termination interface.";
          list dot1q-termination-if {
            key "ipv6-addr";
            description
              "Configure static neighbor entry on dot1q termination interface.";
            leaf ipv6-addr {
              type inet:ipv6-address-no-zone;
              description
                "IPv6 address of a static neighbor entry.";
            }
            leaf mac-addr {
              type pub-type:mac-address {
                pattern '[0-9a-fA-F][0|2|4|6|8|aA|cC|eE][0-9a-fA-F]{2}(-[0-9a-fA-F]{4}){2}';
              }
              mandatory true;
              description
                "MAC address.";
            }
            leaf pe-vlan {
              type uint16 {
                range "1..4094";
              }
              mandatory true;
              description
                "Outer VLAN tag.";
            }
          }
        }
        container qinq-termination-ifs {
          when "../../../../ethernet:ethernet/ethernet:l3-sub-interface/ethernet:qinq-termination";
          description
            "List of static neighbor entry on qinq termination interface.";
          list qinq-termination-if {
            key "ipv6-addr";
            description
              "Configure static neighbor entry on qinq termination interface.";
            leaf ipv6-addr {
              type inet:ipv6-address-no-zone;
              description
                "IPv6 address of a static neighbor entry.";
            }
            leaf mac-addr {
              type pub-type:mac-address {
                pattern '[0-9a-fA-F][0|2|4|6|8|aA|cC|eE][0-9a-fA-F]{2}(-[0-9a-fA-F]{4}){2}';
              }
              mandatory true;
              description
                "MAC address.";
            }
            leaf pe-vlan {
              type uint16 {
                range "1..4094";
              }
              mandatory true;
              description
                "Outer VLAN tag.";
            }
            leaf ce-vlan {
              type uint16 {
                range "1..4094";
              }
              mandatory true;
              description
                "Inner VLAN tag.";
            }
          }
        }
        container vlan-ifs {
          when "../../../../ifm:type='Vlanif'";
          description
            "List of static neighbor entry on VLAN interface.";
          list vlan-if {
            key "ipv6-addr";
            description
              "Configure static neighbor entry on VLAN interface.";
            leaf ipv6-addr {
              type inet:ipv6-address-no-zone;
              description
                "IPv6 address of a static neighbor entry.";
            }
            leaf mac-addr {
              type pub-type:mac-address {
                pattern '[0-9a-fA-F][0|2|4|6|8|aA|cC|eE][0-9a-fA-F]{2}(-[0-9a-fA-F]{4}){2}';
              }
              mandatory true;
              description
                "MAC address.";
            }
            leaf vlan-id {
              type uint16 {
                range "1..4094";
              }
              mandatory true;
              description
                "VLAN ID.";
              ext:support-filter "true";
            }
            leaf port-name {
              type leafref {
                path "/ifm:ifm/ifm:interfaces/ifm:interface/ifm:name";
              }
              mandatory true;
              description
                "Port name.";
            }
          }
        }
        container vbd-ifs {
          when "../../../../ifm:type='Vbdif'";
          description
            "List of static neighbor entry on VBDIF interface.";
          list vbd-if {
            key "ipv6-addr";
            description
              "Configure static neighbor entry on VBDIF interface.";
            leaf ipv6-addr {
              type inet:ipv6-address-no-zone;
              description
                "IPv6 address of a static neighbor entry.";
            }
            choice neighbor-access-type {
              mandatory true;
              description
                "Access type of static neighbor.";
              case vbdif-common {
                description
                  "Common static neighbor without any access type.";
                leaf mac-addr {
                  type pub-type:mac-address;
                  mandatory true;
                  description
                    "MAC address.";
                }
              }
              case evc-untag {
                description
                  "Static neighbor with untag access type.";
                leaf untag-mac-addr {
                  type pub-type:mac-address;
                  mandatory true;
                  description
                    "MAC address.";
                }
                leaf untag-port-name {
                  type leafref {
                    path "/ifm:ifm/ifm:interfaces/ifm:interface/ifm:name";
                  }
                  mandatory true;
                  description
                    "Port name.";
                }
              }
              case evc-dot1q {
                description
                  "Static neighbor with dot1q access type.";
                leaf dot1q-mac-addr {
                  type pub-type:mac-address;
                  mandatory true;
                  description
                    "MAC address.";
                }
                leaf dot1q-port-name {
                  type leafref {
                    path "/ifm:ifm/ifm:interfaces/ifm:interface/ifm:name";
                  }
                  mandatory true;
                  description
                    "Port name.";
                }
                leaf vlan-id {
                  type uint16 {
                    range "1..4094";
                  }
                  mandatory true;
                  description
                    "VLAN ID.";
                }
              }
              case evc-qinq {
                description
                  "Static neighbor with QinQ access type.";
                leaf qinq-mac-addr {
                  type pub-type:mac-address;
                  mandatory true;
                  description
                    "MAC address.";
                }
                leaf qinq-port-name {
                  type leafref {
                    path "/ifm:ifm/ifm:interfaces/ifm:interface/ifm:name";
                  }
                  mandatory true;
                  description
                    "Port name.";
                }
                leaf pe-vid {
                  type uint16 {
                    range "1..4094";
                  }
                  mandatory true;
                  description
                    "Outer VLAN tag.";
                }
                leaf ce-vid {
                  type uint16 {
                    range "1..4094";
                  }
                  mandatory true;
                  description
                    "Inner VLAN tag.";
                }
              }
              case vxlan {
                description
                  "Static neighbor with VXLAN access type.";
                leaf vxlan-mac-addr {
                  type pub-type:mac-address;
                  mandatory true;
                  description
                    "MAC address.";
                }
                leaf vni {
                  type uint32 {
                    range "1..16777215";
                  }
                  mandatory true;
                  description
                    "VXLAN VNI.";
                }
                leaf source-addr {
                  type inet:ipv4-address-no-zone;
                  mandatory true;
                  description
                    "VXLAN tunnel source IP address.";
                }
                leaf peer-addr {
                  type inet:ipv4-address-no-zone;
                  mandatory true;
                  description
                    "VXLAN tunnel peer IP address.";
                }
              }
              case vxlan6 {
                description
                  "Static neighbor with VXLAN6 access type.";
                leaf vxlan6-mac-addr {
                  type pub-type:mac-address;
                  mandatory true;
                  description
                    "MAC address.";
                }
                leaf vni6 {
                  type uint32 {
                    range "1..16777215";
                  }
                  mandatory true;
                  description
                    "VXLAN6 VNI.";
                }
                leaf source-ipv6-addr {
                  type inet:ipv6-address-no-zone;
                  mandatory true;
                  description
                    "VXLAN6 tunnel source IPv6 address.";
                }
                leaf peer-ipv6-addr {
                  type inet:ipv6-address-no-zone;
                  mandatory true;
                  description
                    "VXLAN6 tunnel peer IPv6 address.";
                }
              }
            }
          }
        }
      }
      container send-rate-limit{
        when "../../../ifm:type!='Serial'";
        description
          "Configure ND send rate limit for interface.";
        container packet-rate-limits {
          description
            "List of ND packet sending rate limits.";
          list packet-rate-limit {
            key "packet-type";
            description
              "Configure the rate limit of sending ND packet.";
            leaf packet-type {
              type nd-pkt-type;
              must "not((../packet-type = 'RA') and (../../../../../../ifm:type='MEth'))";
              description
                "ND packet type.";
            }
            leaf value {
              type uint16 {
                range "1..10240";
              }
              units "pps";
              must "((../packet-type = 'NA') and (../value <= 10240)) or (not(../packet-type = 'NA') and (../value <= 1000))";
              mandatory true;
              description
                "Rate limit of sending ND packet, when the packet type is NS, RS or RA, the maximum value is 1000.";
            }
          }
        }
        container multicast-rate-limits {
          description
            "List of ND multicast packet sending rate limits.";
          list multicast-rate-limit {
            key "packet-type";
            description
              "Configure the rate limit of sending ND multicast packet.";
            leaf packet-type {
              type nd-pkt-type;
              must "not((../packet-type = 'RA') and (../../../../../../ifm:type='MEth'))";
              description
                "ND packet type.";
            }
            leaf value {
              type uint16 {
                range "1..10240";
              }
              units "pps";
              must "((../packet-type = 'NA') and (../value <= 10240)) or (not(../packet-type = 'NA') and (../value <= 1000))";
              mandatory true;
              description
                "Rate limit of sending ND multicast packet, when the packet type is NS, RS or RA, the maximum value is 1000.";
            }
          }
        }
      }
      container ra-property {
        when "../../../ifm:type!='MEth'";
        description
          "Configure ND RA configurations under the interface.";
        container ra-control {
          description
            "Configure ND RA configurations.";
          leaf unicast-send {
            type nd-switch-state;
            default "off";
            description
              "Flag of Sending RA unicast packet when receive a RS packet.";
          }
        }
        container ra-routes {
          description
            "List of RA route information option.";
          list ra-route {
            key "prefix-addr prefix-len";
            description
              "Configure RA route information option.";
            leaf prefix-addr {
              type inet:ipv6-address-no-zone;
              description
                "The IPv6 prefix address of RA route information.";
            }
            leaf prefix-len {
              type uint32 {
               range "0..128";
              }
              description
                "The prefix length of RA route information.";
            }
            leaf lifetime {
              type uint32;
              units "s";
              mandatory true;
              description
                "The lifetime of RA route information.";
            }
            leaf preference {
              type nd-route-preference;
              default "medium";
              description
                "The preference of RA route information.";
            }
          }
        }
        container dns-server-addresses {
          description
            "List of DNS server address.";
          list dns-server-address {
            key "ipv6-address";
            description
              "Configure the DNS server address.";
            leaf ipv6-address {
              type inet:ipv6-address-no-zone;
              description
                "Address of IPv6 recursive DNS server. The address cannot be a multicast address or an unspecified address.";
            }
            leaf lifetime {
              type uint32 {
                range "1..max";
              }
              units "s";
              description
                "The maximum time over which this RDNSS address may be used for name resolution.";
            }
          }
        }
        container dns-search-suffixes {
          description
            "List of DNS search list.";
          list dns-search-suffix {
            key "suffix-name";
            description
              "Configure DNS suffix name.";
            leaf suffix-name {
              type string {
                length "1..63";
              }
              ext:case-sensitivity lower-or-upper;
              description
                "Domain name of DNS search list.";
            }
            leaf lifetime {
              type uint32 {
                range "1..max";
              }
              units "s";
              description
                "The maximum time over which this DNSSL domain name may be used for name resolution.";
            }
          }
        }
      }
      container strict-prefix-learn {
        when "../../../ifm:type!='Vlanif' and ../../../ifm:type!='Vbdif' and ../../../ifm:type!='Global-VE'";
        description
          "Configure strict prefix learning of interface.";
        leaf switch {
          type nd-switch-state;
          description
            "ND prefix learning strict.";
        }
      }
    }
  }
  augment "/ifm:ifm/ifm:interfaces/ifm:interface" {
    description
      "List of ND configurations under ifm interface.";
      container nd-dyn-nb-limit {
        description
          "Configure the maximum of limitation of dynamic neighbor.";
        container vlan-limits {
          description
            "List of the maximum of limitation of dynamic neighbor based on VLAN.";
          list vlan-limit {
            key "vlan-id";
            description
              "Configure the maximum of limitation of dynamic neighbor based on VLAN.";
            leaf vlan-id {
              type uint16 {
                range "1..4094";
              }
              description
                "VLAN ID.";
            }
            leaf max-dyn-nb-num {
              type uint32 {
                range "0..147456";
              }
              mandatory true;
              description
                "The maximum of limitation of dynamic neighbor.";
            }
         }
       }
    }
  }
  ext:task-name "nd";
}
