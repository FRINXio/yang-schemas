/*
Copyright (C) 2019-2022 Huawei Technologies Co., Ltd. All rights reserved.
*/
module huawei-macm-notification {
  yang-version 1;
  namespace "urn:huawei:yang:huawei-macm-notification";
  prefix macm-notification;
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of macm-notification.";
  revision 2022-01-10 {
    description
      "Added sticky MAC alarm notification.";
    reference
      "Huawei private.";
  }
  revision 2020-03-30 {
    description
      "The modifications in the schema file are synchronized to the YANG file.";
    reference
      "Huawei private.";
  }
  revision 2019-07-08 {
    description
      "Initial revision.";
    reference
      "Huawei private.";
  }
  notification lr-mac-exceed {
    description
      "The number of MAC routes on the device exceeded the maximum value.";
    leaf vstm-cur-mac-num {
      type uint32;
      description
        "Current MAC route number of the device.";
    }
    leaf vstm-max-mac-num {
      type uint32;
      description
        "Maximum number of MAC addresses.";
    }
  }
  notification lr-mac-exceed-clear {
    description
      "The number of MAC routes on the device fell below the maximum value.";
    leaf vstm-cur-mac-num {
      type uint32;
      description
        "Current MAC route number of the device.";
    }
    leaf vstm-max-mac-num {
      type uint32;
      description
        "Maximum number of MAC addresses.";
    }
  }
  notification evpn-local-stickymac-conflict-alm {
    description
      "Local sticky mac-addresses were conflicted in an EVPN instance.";
    leaf evpn-instance-name {
      type string {
        length "1..31";
      }
      description
        "The name of the EVPN instance with sticky MAC addresses conflicting.";
    }
    leaf bd-id {
      type uint32;
      description
        "The Bd with sticky MAC addresses conflicting.";
    }
  }
  notification evpn-local-stickymac-conflict-alm-clear {
    description
      "Local sticky mac-addresses confliction resolved.";
    leaf evpn-instance-name {
      type string {
        length "1..31";
      }
      description
        "The name of the EVPN instance which sticky MAC addresses conflicting has been resumed.";
    }
    leaf bd-id {
      type uint32;
      description
        "The Bd which sticky MAC addresses conflicting has been resumed.";
    }
  }
  ext:task-name "vstm";
}
