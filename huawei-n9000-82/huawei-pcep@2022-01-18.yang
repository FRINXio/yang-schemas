/*
Copyright (C) 2020-2022 Huawei Technologies Co., Ltd. All rights reserved.
*/
module huawei-pcep {
  namespace "urn:huawei:yang:huawei-pcep";
  prefix pcep;
  import huawei-extension {
    prefix ext;
  }
  organization
    "Huawei Technologies Co., Ltd.";
  contact
    "Huawei Industrial Base
     Bantian, Longgang
     Shenzhen 518129
     People's Republic of China
     Website: http://www.huawei.com
     Email: support@huawei.com";
  description
    "Path Computation Element Communication (PCEP).";
  revision 2022-01-18 {
    description
      "Added micro-isolation CAR.";
    reference
      "Huawei private.";
  }
  revision 2020-07-10 {
    description
      "Initial revision.";
    reference
      "Huawei private.";
  }
  ext:task-name "pce";
  container pcep {
    description
      "PCEP configuration.";
    container session-car {
      description
        "Configure session CAR.";
      container ipv4 {
        must 'cir<=pir';
        must 'cbs<=pbs';
        description
          "Configure PCEP IPv4 session CAR.";
        leaf enable {
          type boolean;
          default "true";
          description
            "Enable/disable PCEP IPv4 session CAR.";
        }
        leaf cir {
          type uint32 {
            range "1..1000000";
          }
          units "kbit/s";
          default "9";
          description
            "Session CAR CIR value.";
        }
        leaf cbs {
          type uint32 {
            range "1..9000000";
          }
          units "Byte";
          default "1758";
          description
            "Session CAR CBS value.";
        }
        leaf pir {
          type uint32 {
            range "1..1000000";
          }
          units "kbit/s";
          default "2400";
          description
            "Session CAR PIR value.";
        }
        leaf pbs {
          type uint32 {
            range "1..9000000";
          }
          units "Byte";
          default "450000";
          description
            "Session CAR PBS value.";
        }
      }
    }
    container micro-isolation-car {
      description
        "Configure PCEP micro-isolation CAR.";
      container ipv4{
        must 'cir<=pir';
        must 'cbs<=pbs';
        description
          "Configure PCEP IPv4 micro-isolation CAR.";
        leaf enable {
          type boolean;
          default "true";
          description
            "Enable/disable PCEP IPv4 micro-isolation CAR.";
        }
        leaf cir {
          type uint32 {
            range "1..1000000";
          }
          units "kbit/s";
          default "9";
          description
            "Micro-isolation CAR CIR value.";
        }
        leaf cbs {
          type uint32 {
            range "1..9000000";
          }
          units "Byte";
          default "1758";
          description
            "Micro-isolation CAR CBS value.";
        }
        leaf pir {
          type uint32 {
            range "1..1000000";
          }
          units "kbit/s";
          default "2400";
          description
            "Micro-isolation CAR PIR value.";
        }
        leaf pbs {
          type uint32 {
            range "1..9000000";
          }
          units "Byte";
          default "450000";
          description
            "Micro-isolation CAR PBS value.";
        }
      }
    }
  }
}
