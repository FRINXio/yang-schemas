/*
Copyright (C) 2021 Huawei Technologies Co., Ltd. All rights reserved.
*/
module huawei-ietf-hardware-deviations-NE9000 {
  namespace "urn:huawei:yang:huawei-ietf-hardware-deviations-NE9000";
  prefix hw-devs-NE9000;

  import ietf-hardware {
    prefix hw;
  }

  organization
    "Huawei Technologies Co., Ltd.";
  contact
    "Huawei Industrial Base
     Bantian, Longgang
     Shenzhen 518129
     People's Republic of China
     Website: http://www.huawei.com
     Email: support@huawei.com";
  description
    "This module defines deviation statements for ietf-hardware module.";

  revision 2021-05-07 {
    description
      "Initial revision.";
    reference "Huawei private.";
  }

  deviation "/hw:hardware/hw:component/hw:state" {
    deviate not-supported;
  }
  deviation "/hw:hardware/hw:component/hw:sensor-data" {
    deviate not-supported;
  }
  deviation "/hw:hardware-state-change" {
    deviate not-supported;
  }
  deviation "/hw:hardware-state-oper-enabled" {
    deviate not-supported;
  }
  deviation "/hw:hardware-state-oper-disabled" {
    deviate not-supported;
  }
  deviation "/hw:hardware" {
    deviate replace {
      config false;
    }
  }
  deviation "/hw:hardware/hw:component" {
    deviate replace {
      config false;
    }
  }
  deviation "/hw:hardware/hw:component/hw:name" {
    deviate replace {
      config false;
    }
  }
}
