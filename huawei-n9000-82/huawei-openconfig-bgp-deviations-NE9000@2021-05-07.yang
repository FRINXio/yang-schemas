/*
Copyright (C) 2021 Huawei Technologies Co., Ltd. All rights reserved.
*/
module huawei-openconfig-bgp-deviations-NE9000 {
  namespace "urn:huawei:yang:huawei-openconfig-bgp-deviations-NE9000";
  prefix oc-bgp-devs-NE9000;

  import openconfig-bgp {
    prefix oc-bgp;
  }

  organization
    "Huawei Technologies Co., Ltd.";
  contact
    "Huawei Industrial Base
     Bantian, Longgang
     Shenzhen 518129
     People's Republic of China
     Website: http://www.huawei.com
     Email: support@huawei.com";
  description
    "This module defines deviation statements for openconfig-bgp module.";

  revision 2021-05-07 {
    description
      "Initial revision.";
    reference "Huawei private.";
  }

  deviation "/oc-bgp:bgp" {
    deviate not-supported;
  }
}
