/*
Copyright (C) 2021 Huawei Technologies Co., Ltd. All rights reserved.
*/
module huawei-oc-platform-linecard-deviations-NE9000 {
  namespace "urn:huawei:yang:huawei-oc-platform-linecard-deviations-NE9000";
  prefix oc-linecard-devs-NE9000;

  import openconfig-platform-linecard {
    prefix oc-linecard;
  }
  import openconfig-platform {
    prefix oc-platform;
  }

  organization
    "Huawei Technologies Co., Ltd.";
  contact
    "Huawei Industrial Base
     Bantian, Longgang
     Shenzhen 518129
     People's Republic of China
     Website: http://www.huawei.com
     Email: support@huawei.com";
  description
    "This module defines deviation statements for openconfig-platform-linecard module.";

  revision 2021-05-07 {
    description
      "Initial revision.";
    reference "Huawei private.";
  }

  deviation "/oc-platform:components/oc-platform:component/oc-linecard:linecard/oc-linecard:config" {
    deviate replace {
      config false;
    }
  }
}
