module casa-policy {
	yang-version 1;
  
	namespace "urn:casa:params:xml:ns:yang:casa-policy"; 
	prefix "policy";
	
	import ietf-inet-types { 
		prefix inet;
	}
	
	import ietf-yang-types { 
		prefix yang;
	}
	
	organization "Casa Systems Inc";

	contact 
	"Casa Systems Inc.
	 100 Old River Road, Suite 100
	 Andover, MA 01810
	 TEL: +1 978 688 6706
	 FAX: +1 978 688 6584
	 E-mail: support@casa-systems.com";
	
	description
		"CASA vBNG Policy Manager Configuration";

	revision "2019-06-10" {
		description "Initial version";
	}

	typedef Rate-Units-Type {
		type string {
		  pattern "(bps)|(kbps)|(mbps)|(gbps)";
		}
		description "Supported units for police rate or peak-rate.
					 bps  - units in Bits/Sec
					 kbps - units in KiloBits/Sec
					 mbps - units in MegaBits/Sec
					 gbps - units in GigaBits/Sec";
	}

	typedef Protocol-Type {
		type string {
		  pattern 
			"(([1-9]|[1-9][0-9]|1[0-9][0-9]|2[0-4][0-9]|25[0-5])|"+
			"(all)|(tcp)|(udp)|(telnet)|(icmp)|(finger)|(ftp)|(http)|"+
			"(igmp)|(imap)|(ntp)|(rtelnet)|(rtsp)|(smtp)|(snmp)|(ssh)|"+
			"(sunrpc)|(telnets)|(tftp)|(time))";
		}
		description "Numeric value or range or string representation.
					 Should be single value or range 0..255.";
	}
  
	typedef Ip-bundle-Id-Type {
		type string {
			pattern "([1-9]|1[0-6])|(([1-9]|1[0-6]).([1-9]|[1-9][0-9]|[1-9][0-9][0-9]|10[0-2][0-3]))";
		}
		description "ip bundle ip, <1-16> or <X.Y>, where X=1-16, Y=1-1023";
	}  
	grouping  policy-map-event-group {
		container account-logoff-match-all{
			list class-type-control-subscriber-do-all{
				key class-name;
				max-elements 1;						
				leaf class-name {
					type string;
				}
				list action{
					key id;
					leaf id {
						type uint16;
					}
					leaf activate-dynamic-template-name{
						type string;  
					}								
					leaf deactivate-dynamic-template-name {
						type string;  
					}	
					leaf disconnect {
						type boolean;  
					}
				}
			}								
		}	
		container account-logon-match-all{
			list class-type-control-subscriber-do-all{					
				key class-name;
				max-elements 1;						
				leaf class-name {
					type string;
				}
				list action{
					key id;
					leaf id {
						type uint16;
					}
					leaf activate-dynamic-template-name{
						type string;  
					}								
					leaf deactivate-dynamic-template-name {
						type string;  
					}	
				}
			}
		}						
			
		container session-activate-match-all{
			list class-type-control-subscriber-do-all{						
				key class-name;
				max-elements 1;						
				leaf class-name {
					type string;
				}
				list action{
					key id;
					leaf id {
						type uint16;
					}
					leaf authenticate-aaa-list-default{
						type boolean;  
					}								
					leaf authorize-default-format{ 
						type string;  
					}	
				}
			}								
		}		
		container session-start-match-all{
			list class-type-control-subscriber-do-all{						
				key class-name;
				max-elements 1;						
				leaf class-name {
					type string;
				}
				list action{
					key id;
					leaf id {
						type uint16;
					}
					container authorize{
						list default-format{
							key format-name;	
							leaf format-name{
								type string;  
							}	
							leaf password{
								type string;  
							}	
						
						}	
						container identifier-source-address-mac{
							leaf password{
								type string;  
							}													
						}	
					}									
					leaf activate-dynamic-template-name {
						type string;  
					}	
				}
			}	
		}	
	}  
	
	grouping policy-map-type-pbr-group{
		leaf drop {
			type boolean;
		}					
		leaf http-redirect {
			type string;
		}
		container redirect  {
			list nexthop{ 
				key address;
				leaf address{
					type inet:ip-address; 
				}
				leaf gw-vrf-name {
					type string;
				}			
			}							
		}	
		leaf set-dscp {
			type uint8 {
				range "0..63";
			}
		}
		leaf transmit {
			type boolean;
		}		
	}
	
	grouping policy-map-type-qos-group{	
		container policy {
			container committed-rate
			{
				description "Committed Information Rate";
				leaf rate {
					type uint32 {
						range "1..4294967295";
					}        
				}
				leaf unit {
					type Rate-Units-Type;
				}                
			}

			leaf burst-size {
				type uint32 {
					range "1..4294967295";
				}
			}

			container peak-rate
			{
				description "Peak Information Rate";
				leaf rate {
					type uint32 {
						range "1..4294967295";
					}        
				}
				leaf unit {
					type Rate-Units-Type;
				}                
			}

			leaf peak-burst {
				description "Excess Burst size";
				type uint32 {
					range "1..4294967295";
				}
			}
		}
		
		leaf priority-level{
			type uint8 {
				range "0..7";
			}
		}	
		leaf set-dscp {
			type uint8 {
				range "0..63";
			}
		}	
	}
 
	grouping class-map-rule-group {
		description "Class-map rule";
		leaf protocol {
			type Protocol-Type;
			description "protocol number.";
		}
		leaf inner-vlan {
			type uint16 {
				range "1..4094";
			}
			must "../outer-vlan" {
				description "outer vlan must be set.";
			}
			description "inner vlan id.";
		}
		leaf outer-vlan {
			type uint16 {
				range "1..4094";
			}
			description "outer vlan id.";
		}		
		leaf vlan {
			type uint16 {
				range "1..4094";
			}
			description "vlan id.";
		}
		leaf dscp {
			type uint16 {
				range "0..63";
			}
		}		
		leaf access-group {
			type string;
			description "access list name.";
		}
		leaf src-mac-addr {
			type yang:mac-address;
			description "source mac address.";
		}
		leaf dest-mac-addr {
			type yang:mac-address;
			description "destination mac address.";
		}
	}
	
	grouping class-map-type-control-group{
		leaf match-dhcpv4 {
			type boolean;			
		}
		leaf match-dhcpv6 {
			type boolean;			
		}
		leaf match-ppp {
			type boolean;			
		}	
	}
	
	grouping route-map-config-group{
		container continue {
			description "Continue on a different entry within the route-map";
			leaf enable {
			  type string;  
			}
			leaf continue-id{
				type uint16;
				description "Route-map entry sequence number";
			}			
		}
		leaf description {
			type string;  
		}
		container match {
			container ipv4 {
				container address {
					leaf access-list {
						type string;
						description "ip access-list name";
					}
					leaf prefix-list {
						type string;
						description "ip prefix-list name";
					}
				}
				container next-hop {
					leaf access-list {
						type string;
						description "ip access-list name";
					}
					leaf prefix-list {
						type string;
						description "ip prefix-list name";
					}
				}
			}	
			container ipv6 {
				container address {
					leaf access-list {
						type string;
						description "ip access-list name";
					}
					leaf prefix-list {
						type string;
						description "ip prefix-list name";
					}
				}
				container next-hop {
					leaf access-list {
						type string;
						description "ip access-list name";
					}
				}
			}
			leaf as-path {
				type string;
				description "BGP AS path list";
			}
			container community {
				description "BGP community list";
				leaf community-list {
					type string;
					description "Community-list name";
				}	
				leaf exact-match {
					type boolean;				 
				}
			}
			container extcommunity {
				description "BGP extcommunity list";
				leaf excommunity-list {
					type string;
					description "Community-list name";  
				}	
				leaf exact-match {
					type boolean; 	
				}
			}
			leaf metric {
				type uint32;
				description "metric of route";
			}
			leaf route-type {
				type enumeration {
					enum type-1 {
						description "OSPF External Type 1";
					}
					enum type-2 {
						description "OSPF External Type 2";
					}
				}		
			}
			leaf tag {
				type uint32;
				description "tag of route";
			}
			container interface {
				description "The first hop interface of route";
				leaf interface-name {
					type string;  
				}
				leaf gige {
					type string;  
				}
				leaf ip-bundle {
					type Ip-bundle-Id-Type;  
				}		
				leaf loopback {
					type uint8;
				}
				leaf null0 {
					type boolean;
					description "null interface (black hole)";
				}
				leaf trunk {
					type uint16;
				}	
				leaf vlan {
					type string;
				}	
				leaf xgige {
					type string;
				}
			}		
			leaf origin {
				description "BGP origin code";
				type enumeration {
					enum egp {
						description "remote EGP";
					}
					enum igp {
						description "local IGP";
					}				
					enum incomplete {
						description "unknown heritage";
					}
				} 		
			}
		}  
		container set {
			leaf atomic-aggregate{
				type boolean;
				description "BGP atomic aggregate attribute";
			}	
			leaf comm-list-delete{
				type string;
				description "Set BGP community list for deletion";
			}
			container community {
				description "BGP community attribute";
				leaf community-list {
					type string;
					description "Community-list name, can be used in the following format:
					            1) AA:NN        - community number in aa:nn format;
					            2) internet     - Internet (well-known community);
					            3) local-AS     - Do not send outside local AS (well-known community);
					            4) no-advertise - Do not advertise to any peer (well-known community);
					            5) no-export    - Do not export to next AS (well-known community). ";
				}	
				leaf additive {
					type boolean;				 
				}
			}
			container extcommunity{
				leaf rt-excommunity-list{
					type string;
					description "Route Target extended community, in aa:nn format.";
				}
				leaf soo-excommunity-list{
					type string;
					description "Site-of-Origin extended community, in aa:nn format."; 
				}
			}
			leaf local-preference{
				type uint32;
				description "BGP local preference path attribute";
			}
			leaf metric {
				type uint32;
				description "Metric value for destination routing protocol";
			}
			leaf metric-type {
				type enumeration {
					enum type-1 {
						description "OSPF External Type 1";
					}
					enum type-2 {
						description "OSPF External Type 2";
					}
				}
				description "Type of metric for destination routing protocol";
			}
			leaf tag {
				type uint32;
				description "Tag value for destination routing protocol";
			}
			leaf origin {
				description "BGP origin code";
				type enumeration {
					enum egp {
						description "remote EGP";
					}
					enum igp {
						description "local IGP";
					}				
					enum incomplete {
						description "unknown heritage";
					}
				} 		
			}
			leaf weight {
				type uint16;
				description "BGP weight for routing table";
			}
			leaf as-path-prepend {
				type string;
				description "AS number list prepended to the as-path";  
			}
			container ipv4-next-hop {
				description "Next-hop to output packet";
				leaf blackhole {
					type boolean;
					description "set true to drop all the packets that match the ACL";
				}
				list ip-address {
					key address;
					leaf address {		
						type inet:ipv4-address; 					
					}		
					leaf vrf {		
						type string; 					
					}	
				}
			}	
			container ipv6-next-hop {
				description "Next-hop to output packet";
				leaf blackhole {
					type boolean;
					description "set true to drop all the packets that match the ACL";  
				}
				leaf local {
					type inet:ipv6-address;
					description "IPv6 local address";
				}
				list ip-address {
					key address;
					leaf address {		
						type inet:ipv6-address;				
					}		
					leaf vrf {		
						type string; 					
					}	
				}
			}
			leaf mpls-label {
				type boolean;  
			}
		}
	}		
	grouping route-maps-group {
		container route-maps {
			list route-map {
				key route-map-name;
				leaf route-map-name {
					type string;  
				}
				list sequence {
					key seq-id;
					leaf seq-id {
						type uint16 {
							range "1..65535";
						}						
					}
					leaf action {
						type enumeration {
							enum deny;				
							enum permit;				
						}
					}			
					uses route-map-config-group;		
				}
			}			
		}	
	}
	
	grouping  policy-maps-group{
		container policy-maps{
			description "Policy-maps configuration.";	
			
			list policy-map {
				key "policy-map-name";
				description "Name of policy-map..";		
					
				leaf policy-map-name {
					type string;
				}
				leaf class {
					type string;
				}
				
			}			
			
			container type {
				list control-subscriber {
					key "policy-map-name";
						description "Subscriber control policy-map.";
					leaf policy-map-name {
					  type string;
					}
					uses policy-map-event-group;
				}
				
				list pbr {
					key "policy-map-name";
						description "PBR policy-map.";
					leaf policy-map-name {
						type string;
					}
					list class-name-pbr{
						key "class-name";							
						leaf class-name {
							type string;
						}						
						uses policy-map-type-pbr-group;	
					}
					container class-default {				
						uses policy-map-type-pbr-group;	
					}						
				}
				
				list qos {
					key "policy-map-name";
					description "QoS policy-map.";
					leaf policy-map-name {
						type string;
					}
					list class-name-qos{
						key "class-name";							
						leaf class-name {
							type string;
						}						
						uses policy-map-type-qos-group;	
					}						
					container class-default{					
						uses policy-map-type-qos-group;
					}						
				}					
			}
		}
	}
	grouping class-maps-group {
		container class-maps {
			description "Class-maps configuration.";
			list class-map {
				key "class-map-name";		
				leaf class-map-name {
					type string;
				}
				leaf match-acl-name {
					type string;
				}
				
				leaf set-dscp {
					type uint8 {
						range "0..63";
					}
				}		
			}
			container type-control {			
				list match-all {
					key "class-map-name";					
					leaf class-map-name {
						type string;
					}
					uses class-map-type-control-group;
				}
				list match-any {
					key "class-map-name";					
					leaf class-map-name {
						type string;
					}
					uses class-map-type-control-group;
				}				
			}		
			container type-qos {
				list match-all {
					key "class-map-name";				
					leaf class-map-name {
						type string;
					}
					uses class-map-rule-group;
				}
				list match-any {
					key "class-map-name";				
					leaf class-map-name {
						type string;
					}
					uses class-map-rule-group;
				}							
			}				
		}
	}
  
	container casa-policy {
		description "Global Policy Manager configuration.";

		uses route-maps-group;
		uses policy-maps-group;
		uses class-maps-group;
	}
}
