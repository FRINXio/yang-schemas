submodule Cisco-IOS-XR-Ethernet-SPAN-oper-sub3 {

  belongs-to Cisco-IOS-XR-Ethernet-SPAN-oper {
    prefix Cisco-IOS-XR-Ethernet-SPAN-oper;
  }

  /*** LINKAGE (IMPORTS / INCLUDES) ***/

  import ietf-inet-types { prefix "inet"; }

  import Cisco-IOS-XR-types { prefix "xr"; }

  include Cisco-IOS-XR-Ethernet-SPAN-oper-sub1 {
    revision-date 2015-11-09;
  }

  include Cisco-IOS-XR-Ethernet-SPAN-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR Ethernet-SPAN package operational data.

     Copyright (c) 2013-2018 by Cisco Systems, Inc.
     All rights reserved.";

  revision "2015-11-09" {
    description
      "IOS XR 6.0 revision.";
  }

  typedef Destination-name-string {
    type string;
    description "Destination name string";
  }

  grouping INJECT-INTERFACE-DATA {
    description "Inject interface data";
    leaf name {
      type string;
      description "Interface Name";
    }
  }

  grouping DESTINATION-NEXT-HOP-IPV6-ADDRESS-DATA {
    description "Destination Next-hop IPv6 Address Data";
    leaf ipv6-address {
      type inet:ipv6-address;
      description "IPv6 address";
    }
    leaf vrf-name {
      type Destination-name-string;
      description "VRF name";
    }
    leaf address-is-reachable {
      type boolean;
      description "Address is reachable";
    }
  }

  grouping DESTINATION-NEXT-HOP-IPV4-ADDRESS-DATA {
    description "Destination Next-hop IPv4 Address Data";
    leaf ipv4-address {
      type inet:ipv4-address;
      description "IPv4 address";
    }
    leaf vrf-name {
      type Destination-name-string;
      description "VRF name";
    }
    leaf address-is-reachable {
      type boolean;
      description "Address is reachable";
    }
  }

  grouping DESTINATION-PSEUDOWIRE-DATA {
    description "Destination Pseudowire Data";
    leaf pseudowire-name {
      type Destination-name-string;
      description "Pseudowire Name";
    }
    leaf pseudowire-is-up {
      type boolean;
      description "Pseudowire State";
    }
  }

  grouping DESTINATION-INTERFACE-DATA {
    description "Destination Interface Data";
    leaf interface-name {
      type Destination-name-string;
      description "Interface Name";
    }
    leaf interface-state {
      type Im-state-enum;
      description "Interface State";
    }
  }

  grouping DESTINATION-STATE {
    description "Destination state";

    container interface-data {
      when "../destination-class = 'interface-class'" {
        description "../DestinationClass = 'InterfaceClass'";
      }
      description "Interface data";
      uses DESTINATION-INTERFACE-DATA;
    }

    container pseudowire-data {
      when "../destination-class = 'pseudowire-class'" {
        description "../DestinationClass = 'PseudowireClass'";
      }
      description "Pseudowire data";
      uses DESTINATION-PSEUDOWIRE-DATA;
    }

    container next-hop-ipv4-data {
      when "../destination-class = 'next-hop-ipv4-class'" {
        description "../DestinationClass = 'NextHopIPv4Class'";
      }
      description "Next-hop IPv4 data";
      uses DESTINATION-NEXT-HOP-IPV4-ADDRESS-DATA;
    }

    container next-hop-ipv6-data {
      when "../destination-class = 'next-hop-ipv6-class'" {
        description "../DestinationClass = 'NextHopIPv6Class'";
      }
      description "Next-hop IPv6 data";
      uses DESTINATION-NEXT-HOP-IPV6-ADDRESS-DATA;
    }
    leaf destination-class {
      type Destination-class;
      description "DestinationClass";
    }
    leaf invalid-value {
      when "../destination-class != 'interface-class' and"+
        " ../destination-class != 'pseudowire-class' and"+
        " ../destination-class != 'next-hop-ipv4-class' and"+
        " ../destination-class != 'next-hop-ipv6-class'" {
          description
            "../DestinationClass != 'InterfaceClass' and .
            ./DestinationClass != 'PseudowireClass' and .
            ./DestinationClass != 'NextHopIPv4Class' and .
            ./DestinationClass != 'NextHopIPv6Class'";
      }
      type Optional-value;
      description "Invalid Parameter";
    }
  }

  grouping SPAN-MGR-SESSION-BAG {
    description "SPAN Manager Session Information";

    container destination-data {
      description "Destination data";
      uses DESTINATION-STATE;
    }

    container destination-id {
      description "Destination ID";
      uses DESTINATION-ID;
    }

    container inject-interface {
      description "Inject interface data";
      uses INJECT-INTERFACE-DATA;
    }
    leaf name {
      type string;
      description "Session Name";
    }
    leaf session-class {
      type Session-class;
      description "Session class";
    }
    leaf id {
      type uint32;
      description "Numerical ID assigned to session";
    }
    leaf destination-error {
      type uint32;
      description "Last error observed for the destination ";
    }
    leaf destination-interface-name {
      type string;
      description
        "Destination interface name (deprecated by
        DestinationData, invalid for pseudowires)";
    }
    leaf destination-interface-handle {
      type xr:Interface-name;
      description
        "Destination interface handle (deprecated by
        DestinationID, invalid for pseudowires)";
    }
    leaf interface-error {
      type uint32;
      description
        "Last error observed for the destination
        interface (deprecated by DestinationError)";
    }
  }
}
