module Cisco-IOS-XR-asr9k-asic-errors-oper {

  /*** NAMESPACE / PREFIX DEFINITION ***/

  namespace "http://cisco.com/ns/yang"+
    "/Cisco-IOS-XR-asr9k-asic-errors-oper";


  prefix "asr9k-asic-errors-oper";

  /*** LINKAGE (IMPORTS / INCLUDES) ***/

  import Cisco-IOS-XR-types { prefix "xr"; }

  include Cisco-IOS-XR-asr9k-asic-errors-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-asic-errors package operational data.

     This module contains definitions
     for the following management objects:
       asic-error-stats: Asic error stats operational data

     Copyright (c) 2013-2018 by Cisco Systems, Inc.
     All rights reserved.";

  revision "2015-11-09" {
    description
      "IOS XR 6.0 revision.";
  }


  container asic-error-stats {
    config false;
    description "Asic error stats operational data";

    container racks {
      description "Table of racks";

      list rack {
        key "rack";
        description "Number";

        container nodes {
          description "Table of Nodes";

          list node {
            key "node-name";
            description "Information about a particular node";

            container counts {
              description
                "Table of all Asic Types information on a
                node";

              list count {
                key "type";
                description
                  "Summary Asic error counts for a Asic Type";
                leaf type {
                  type xr:Cisco-ios-xr-string;
                  description "Asic Type";
                }
                uses HFR-ASIC-SUMMARY;
              }
            }
            leaf node-name {
              type xr:Node-id;
              description "Node name";
            }
          }
        }
        leaf rack {
          type uint32;
          description "Rack number";
        }
      }
    }
  }
}
