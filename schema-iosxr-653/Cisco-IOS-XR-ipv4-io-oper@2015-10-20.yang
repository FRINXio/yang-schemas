module Cisco-IOS-XR-ipv4-io-oper {

  /*** NAMESPACE / PREFIX DEFINITION ***/

  namespace "http://cisco.com/ns/yang/Cisco-IOS-XR-ipv4-io-oper";


  prefix "ipv4-io-oper";

  /*** LINKAGE (IMPORTS / INCLUDES) ***/

  import Cisco-IOS-XR-types { prefix "xr"; }

  include Cisco-IOS-XR-ipv4-io-oper-sub2 {
    revision-date 2015-10-20;
  }

  include Cisco-IOS-XR-ipv4-io-oper-sub1 {
    revision-date 2015-10-20;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-io package operational data.

     This module contains definitions
     for the following management objects:
       ipv4-network: IPv4 network operational data

     Copyright (c) 2013-2018 by Cisco Systems, Inc.
     All rights reserved.";

  revision "2015-10-20" {
    description
      "this schema file has all the latest changes.";
  }

  revision "2015-01-07" {
    description
      "IOS XR 5.3.1 revision.";
  }


  container ipv4-network {
    config false;
    description "IPv4 network operational data";

    container nodes {
      description "Node-specific IPv4 network operational data";

      list node {
        key "node-name";
        description
          "IPv4 network operational data for a particular
          node";

        container interface-data {
          description "IPv4 network operational interface data";

          container vrfs {
            description
              "VRF specific IPv4 network operational
              interface data";

            list vrf {
              key "vrf-name";
              description "VRF name of an interface belong to";

              container briefs {
                description
                  "Brief interface IPv4 network operational
                  data for a node";

                list brief {
                  key "interface-name";
                  description
                    "Brief interface IPv4 network operational
                    data for an interface";
                  leaf interface-name {
                    type xr:Interface-name;
                    description "The name of the interface";
                  }
                  uses IPV4-IF-BRIEF;
                }
              }

              container details {
                description
                  "Detail interface IPv4 network operational
                  data for a node";

                list detail {
                  key "interface-name";
                  description
                    "Detail interface IPv4 network operational
                    data for an interface";
                  leaf interface-name {
                    type xr:Interface-name;
                    description "The name of the interface";
                  }
                  uses IPV4-IF-DETAIL;
                }
              }
              leaf vrf-name {
                type xr:Cisco-ios-xr-string;
                description "The VRF name";
              }
            }
          }

          container summary {
            description
              "Summary of IPv4 network operational interface
              data on a node";
            uses IPV4-IF-SUMMARY;
          }
        }

        container statistics {
          description
            "Statistical IPv4 network operational data for
            a node";

          container traffic {
            description "Traffic statistics for a node";
            uses IP-TRAFFIC;
          }
        }
        leaf node-name {
          type xr:Node-id;
          description "The node name";
        }
      }
    }
  }
}
