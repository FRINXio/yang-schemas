submodule Cisco-IOS-XR-ppp-ea-oper-sub1 {

  belongs-to Cisco-IOS-XR-ppp-ea-oper {
    prefix Cisco-IOS-XR-ppp-ea-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ppp-ea package operational data.

     Copyright (c) 2013-2018 by Cisco Systems, Inc.
     All rights reserved.";

  revision "2015-11-09" {
    description
      "IOS XR 6.0 revision.";
  }

  typedef Ppp-ea-adj-state {
    type enumeration {
      enum ppp-ea-adj-state-not-installed {
        value 0;
        description "Ajacency not installed in AIB";
      }
      enum ppp-ea-adj-state-installed {
        value 1;
        description "Adjacency installed in AIB";
      }
    }
    description "Ppp ea adj state";
  }

  grouping PPP-EA-INTERFACE-INFO {
    description "PPP EA interface information";
    leaf interface {
      type xr:Interface-name;
      description "Interface";
    }
    leaf is-lcp-running {
      type boolean;
      description
        "TRUE if LCP is running in the dataplane for the
        interface";
    }
    leaf is-ipcp-running {
      type boolean;
      description
        "TRUE if IPCP is running in the dataplane for the
        interface";
    }
    leaf is-ipv6cp-running {
      type boolean;
      description
        "TRUE if IPV6CP is running in the dataplane for
        the interface";
    }
    leaf is-mplscp-running {
      type boolean;
      description
        "TRUE if MPLSCP is running in the dataplane for
        the interface";
    }
    leaf local-mtu {
      type uint16;
      description "Local interface MTU";
    }
    leaf local-mrru {
      type uint16;
      description "Local MRRU";
    }
    leaf peer-mrru {
      type uint16;
      description "Peer MRRU";
    }
    leaf local-magic {
      type uint32;
      description "Local magic number";
    }
    leaf peer-magic {
      type uint32;
      description "Peer magic number";
    }
    leaf local-mcmp-classes {
      type uint8;
      description "Local number of MCMP Suspension classes";
    }
    leaf peer-mcmp-classes {
      type uint8;
      description "Peer number of MCMP Suspension classes";
    }
    leaf echo-request-interval {
      type uint32;
      description "Echo-Request interval";
    }
    leaf echo-request-retry-count {
      type uint32;
      description "Echo-Request retry count";
    }
    leaf is-multilink-bundle {
      type boolean;
      description "TRUE if this is a Multilink bundle interface";
    }
    leaf synchronized {
      type boolean;
      description "MA synchronization";
    }
    leaf forwarding-enabled {
      type boolean;
      description "Forwarding State";
    }
    leaf multilink-interface {
      type xr:Interface-name;
      description
        "Multilink interface that this interface is a
        member of, if any";
    }
    leaf l2-tunnel-enabled {
      type boolean;
      description "L2 Tunnel State";
    }
    leaf l2-provisioned {
      type boolean;
      description "L2 Provisioned State";
    }
    leaf l2ip-interworking-enabled {
      type boolean;
      description "L2 IP Interworking State";
    }
    leaf is-vpdn-tunneled {
      type boolean;
      description "Is VPDN tunneled";
    }
    leaf xconnect-id {
      type uint32;
      description "XConnect ID";
    }
    leaf parent-interface-handle {
      type xr:Interface-name;
      description "Parent Interface Handle";
    }
    leaf vrf-table-id {
      type uint32;
      description "IPCP VRF Table ID";
    }
    leaf ipv6vrf-table-id {
      type uint32;
      description "IPv6CP VRF Table ID";
    }
    leaf l2-adjacency-state {
      type Ppp-ea-adj-state;
      description "L2 adjacency state";
    }
    leaf l2ip-interworking-adjacency-state {
      type Ppp-ea-adj-state;
      description "L2 IP Interworking adjacency state";
    }
    leaf lac-adjacency-state {
      type Ppp-ea-adj-state;
      description "LAC adjacency state";
    }
    leaf interface-adjacency-state {
      type Ppp-ea-adj-state;
      description "Interface adjacency state";
    }
    leaf ipv4-adjacency-state {
      type Ppp-ea-adj-state;
      description "Ipv4 adjacency state";
    }
    leaf ipv6-adjacency-state {
      type Ppp-ea-adj-state;
      description "IPv6 adjacency state";
    }
    leaf mpls-adjacency-state {
      type Ppp-ea-adj-state;
      description "MPLS adjacency state";
    }
  }
}
