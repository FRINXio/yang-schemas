submodule Cisco-IOS-XR-ipv6-acl-oper-sub1 {

  belongs-to Cisco-IOS-XR-ipv6-acl-oper {
    prefix Cisco-IOS-XR-ipv6-acl-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-acl package operational data.

     Copyright (c) 2013-2018 by Cisco Systems, Inc.
     All rights reserved.";

  revision "2017-05-01" {
    description
      "Fixing backward compatibility error in module.";
  }

  revision "2015-11-09" {
    description
      "IOS XR 6.0 revision.";
  }

  typedef Bag-acl-nh-at-status {
    type enumeration {
      enum unknown {
        description "AT State Unknown";
      }
      enum up {
        description "AT State UP";
      }
      enum down {
        description "AT State DOWN";
      }
      enum not-present {
        description "AT State Not Present";
      }
      enum max {
        description "invalid status";
      }
    }
    description "Bag acl nh at status";
  }
  typedef Bag-acl-nh-status {
    type enumeration {
      enum not-present {
        description "State Not Present";
      }
      enum unknown {
        description "State Unknown";
      }
      enum down {
        description "State DOWN";
      }
      enum up {
        description "State UP";
      }
      enum max {
        description "invalid status";
      }
    }
    description "Bag acl nh status";
  }
  typedef Bag-acl-nh {
    type enumeration {
      enum nexthop-none {
        description "Next Hop None";
      }
      enum nexthop-default {
        description "Nexthop Default";
      }
      enum nexthop {
        description "Nexthop";
      }
    }
    description "Bag acl nh";
  }
  typedef Acl-ttl-operator {
    type Acl-port-operator;
    description "Acl ttl operator";
  }
  typedef Acl-plen-operator {
    type Acl-port-operator;
    description "Acl plen operator";
  }
  typedef Acl-tcpflags-operator {
    type enumeration {
      enum match-none {
        description "Match None";
      }
      enum match-all {
        description "Match All";
      }
      enum match-any-old {
        description "Match any old";
      }
      enum match-any {
        description "Match any";
      }
    }
    description "Acl tcpflags operator";
  }
  typedef Acl-log {
    type enumeration {
      enum log-none {
        value 0;
        description "Log None";
      }
      enum log {
        value 1;
        description "Log Regular";
      }
      enum log-input {
        value 2;
        description "Log Input";
      }
    }
    description "Acl log";
  }
  typedef Acl-proto-operator {
    type Acl-port-operator;
    description "Acl proto operator";
  }
  typedef Acl-port-operator {
    type enumeration {
      enum none {
        value 0;
        description "None";
      }
      enum eq {
        value 1;
        description "Equal";
      }
      enum gt {
        value 2;
        description "Greater than";
      }
      enum lt {
        value 3;
        description "Less than";
      }
      enum neq {
        value 4;
        description "Not Equal";
      }
      enum range {
        value 5;
        description "Range";
      }
      enum onebyte {
        value 8;
        description "One Byte";
      }
      enum twobytes {
        value 9;
        description "Two Bytes";
      }
    }
    description "Acl port operator";
  }
  typedef Acl-action {
    type enumeration {
      enum deny {
        value 0;
        description "Deny";
      }
      enum permit {
        value 1;
        description "Permit";
      }
      enum encrypt {
        value 2;
        description "Encrypt";
      }
      enum bypass {
        value 3;
        description "Bypass";
      }
      enum fallthrough {
        value 4;
        description "Fallthrough";
      }
      enum invalid {
        value 5;
        description "Invalid";
      }
    }
    description "Acl action";
  }
  typedef Acl-ace1 {
    type enumeration {
      enum normal {
        description "This is Normal ACE";
      }
      enum remark {
        description "This is Remark ACE";
      }
      enum abf {
        description "This is ABF ACE";
      }
    }
    description "ACE Types";
  }
  typedef Acl-ace {
    type Acl-ace1;
    description "ACE Types";
  }

  grouping IPV6-ACL-EDM-OOR-DETAIL {
    description "Oor deatil config BAG";
    leaf is-default-maximum-configurable-ac-ls {
      type uint32;
      description "default max configurable acls";
    }
    leaf is-default-maximum-configurable-ac-es {
      type uint32;
      description "default max configurable aces";
    }
    leaf is-current-configured-ac-ls {
      type uint32;
      description "Current configured acls";
    }
    leaf is-current-configured-aces {
      type uint32;
      description "Current configured aces";
    }
    leaf is-current-maximum-configurable-acls {
      type uint32;
      description "Current max configurable acls";
    }
    leaf is-current-maximum-configurable-aces {
      type uint32;
      description "Current max configurable aces";
    }
    leaf is-maximum-configurable-ac-ls {
      type uint32;
      description "max configurable acls";
    }
    leaf is-maximum-configurable-ac-es {
      type uint32;
      description "max configurable aces";
    }
  }

  grouping ACL-UDF-ACE {
    description "ACL UDF ACE";
    leaf udf-name {
      type string {
        length "0..17";
      }
      description "UDF Name";
    }
    leaf udf-value {
      type uint32;
      description "UDF Value";
    }
    leaf udf-mask {
      type uint32;
      description "UDF Mask";
    }
  }

  grouping IPV6-ACL-BAG-HW-NH-INFO {
    description "HW_NH_Info structure";
    leaf type {
      type Bag-acl-nh;
      description "The next-hop type";
    }
    leaf next-hop {
      type inet:ipv6-address;
      description "The Next Hop";
    }
    leaf table-id {
      type uint32;
      description "Table ID";
    }
    leaf vrf-name {
      type string {
        length "0..32";
      }
      description "Vrf Name";
    }
  }

  grouping IPV6-ACL-BAG-NH-INFO {
    description "NH_Info structure";
    leaf next-hop {
      type inet:ipv6-address;
      description "The next hop";
    }
    leaf vrf-name {
      type string {
        length "0..32";
      }
      description "Vrf Name";
    }
    leaf track-name {
      type string {
        length "0..33";
      }
      description "Track name";
    }
    leaf status {
      type Bag-acl-nh-status;
      description "The next hop status";
    }
    leaf at-status {
      type Bag-acl-nh-at-status;
      description "The next hop at status";
    }
    leaf acl-nh-exist {
      type int32;
      description "The nexthop exist";
    }
  }

  grouping IPV6-ACL-EDM-ACE {
    description "ACLE bag";

    container hw-next-hop-info {
      description "HW Next hop info";
      uses IPV6-ACL-BAG-HW-NH-INFO;
    }
    leaf is-ace-type {
      type Acl-ace;
      description "ACE type (acl, remark)";
    }
    leaf is-ace-sequence-number {
      type uint32;
      description "ACLE sequence number";
    }
    leaf is-packet-allow-or-deny {
      type Acl-action;
      description "Grant value permit/deny ";
    }
    leaf is-protocol-operator {
      type Acl-proto-operator;
      description "Protocol operator";
    }
    leaf is-ipv6-protocol-type {
      type int32;
      description "Protocol 1";
    }
    leaf is-ipv6-protocol2-type {
      type int32;
      description "Protocol 2";
    }
    leaf is-source-address-in-numbers {
      type inet:ipv6-address;
      description "IsSourceAddressInNumbers";
    }
    leaf is-source-address-prefix-length {
      type uint32;
      description "IsSourceAddressPrefixLength";
    }
    leaf source-mask {
      type inet:ipv6-address;
      description "Source Mask";
    }
    leaf is-destination-address-in-numbers {
      type inet:ipv6-address;
      description "IsDestinationAddressInNumbers";
    }
    leaf is-destination-address-prefix-length {
      type uint32;
      description "IsDestinationAddressPrefixLength";
    }
    leaf destination-mask {
      type inet:ipv6-address;
      description "Destination Mask";
    }
    leaf is-source-operator {
      type Acl-port-operator;
      description "eq, ne, lt, etc...";
    }
    leaf is-source-port1 {
      type uint32;
      description "IsSourcePort1";
    }
    leaf is-source-port2 {
      type uint32;
      description "IsSourcePort2";
    }
    leaf is-destination-operator {
      type Acl-port-operator;
      description "eq, ne, lt, etc...";
    }
    leaf is-destination-port1 {
      type uint32;
      description "IsDestinationPort1";
    }
    leaf is-destination-port2 {
      type uint32;
      description "IsDestinationPort2";
    }
    leaf is-log-option {
      type Acl-log;
      description "IsLogOption";
    }
    leaf counter-name {
      type string;
      description "Counter name";
    }
    leaf is-tcp-bits-operator {
      type Acl-tcpflags-operator;
      description "IsTCPBitsOperator";
    }
    leaf is-tcp-bits {
      type uint32;
      description "IsTCPBits";
    }
    leaf is-tcp-bits-mask {
      type uint32;
      description "IsTCPBitsMask";
    }
    leaf is-dscp-present {
      type int32;
      description "IsDSCPPresent";
    }
    leaf dscp-operator {
      type uint8;
      description "DSCP Operator";
    }
    leaf is-dscp-valu {
      type uint8;
      description "IsDSCPValu";
    }
    leaf is-dscp-valu2 {
      type uint8;
      description "IsDSCPValu2";
    }
    leaf is-precedence-present {
      type int32;
      description "IsPrecedencePresent";
    }
    leaf is-precedence-value {
      type uint32;
      description "range from 0 to 7";
    }
    leaf is-header-matches {
      type uint32;
      description "Match if routing header is presant";
    }
    leaf is-packet-length-operator {
      type Acl-plen-operator;
      description "Match if routing header is presant";
    }
    leaf is-packet-length-start {
      type uint32;
      description "IsPacketLengthStart";
    }
    leaf is-packet-length-end {
      type uint32;
      description "IsPacketLengthEnd";
    }
    leaf is-time-to-live-operator {
      type Acl-ttl-operator;
      description "IsTimeToLiveOperator";
    }
    leaf is-time-to-live-start {
      type uint32;
      description "IsTimeToLiveStart";
    }
    leaf is-time-to-live-end {
      type uint32;
      description "IsTimeToLiveEnd";
    }
    leaf no-stats {
      type int32;
      description "no stats";
    }
    leaf hits {
      type uint64;
      description "hits";
    }
    leaf capture {
      type boolean;
      description "Capture option, TRUE if enabled";
    }
    leaf undetermined-transport {
      type boolean;
      description "Undetermined transport option, TRUE if enabled";
    }
    leaf is-icmp-message-off {
      type int32;
      description "Don't generate the icmp message";
    }
    leaf qos-group {
      type uint16;
      description "Set qos-group";
    }
    leaf is-comment-for-entry {
      type string;
      description "IsCommentForEntry";
    }
    leaf next-hop-type {
      type Bag-acl-nh;
      description "Next hop type";
    }
    leaf is-flow-id {
      type uint32;
      description "IsFlowId";
    }
    leaf source-prefix-group {
      type string;
      description "Source prefix object-group";
    }
    leaf destination-prefix-group {
      type string;
      description "Destination prefix object-group";
    }
    leaf source-port-group {
      type string;
      description "Source port object-group";
    }
    leaf destination-port-group {
      type string;
      description "Destination port object-group";
    }
    leaf acl-name {
      type string;
      description "ACL Name";
    }
    leaf sequence-str {
      type string;
      description "Sequence String";
    }
    leaf set-ttl {
      type uint16;
      description "SetTTL";
    }

    list next-hop-info {
      max-elements "3";
      description "Next hop info";
      uses IPV6-ACL-BAG-NH-INFO;
    }

    list udf {
      description "UDF";
      uses ACL-UDF-ACE;
    }
  }

  grouping IPV6-PFX-EDM-ACE {
    description "Prefix list entry BAG";
    leaf is-ace-type {
      type Acl-ace;
      description "ACE type (acl, remark)";
    }
    leaf is-ace-sequence-number {
      type uint32;
      description "ACLE sequence number";
    }
    leaf is-packet-allow-or-deny {
      type Acl-action;
      description "Grant value permit/deny ";
    }
    leaf is-address-in-numbers {
      type inet:ipv6-address;
      description "IPv6 prefix";
    }
    leaf is-address-mask-length {
      type uint32;
      description "Prefix length ";
    }
    leaf is-length-operator {
      type Acl-port-operator;
      description "Port Operator";
    }
    leaf is-packet-minimum-length {
      type uint32;
      description "Min length";
    }
    leaf is-packet-maximum-length {
      type uint32;
      description "Maximum length";
    }
    leaf hits {
      type uint32;
      description "Number of hits";
    }
    leaf is-comment-for-entry {
      type string;
      description "Remark String";
    }
    leaf acl-name {
      type string;
      description "ACL Name";
    }
  }
}
