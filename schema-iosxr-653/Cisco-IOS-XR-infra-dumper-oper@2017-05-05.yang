module Cisco-IOS-XR-infra-dumper-oper {

  /*** NAMESPACE / PREFIX DEFINITION ***/

  namespace "http://cisco.com/ns"+
    "/yang/Cisco-IOS-XR-infra-dumper-oper";


  prefix "infra-dumper-oper";

  /*** LINKAGE (IMPORTS / INCLUDES) ***/

  import Cisco-IOS-XR-types { prefix "xr"; }

  include Cisco-IOS-XR-infra-dumper-oper-sub1 {
    revision-date 2017-05-05;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-dumper package operational data.

     This module contains definitions
     for the following management objects:
       context: Core dump configuration commands

     Copyright (c) 2013-2018 by Cisco Systems, Inc.
     All rights reserved.";

  revision "2017-05-05" {
    description
      "Fix comp-mdata.pl for adding sub1 yang file to /pkg/yang";
  }

  revision "2015-11-09" {
    description
      "IOS XR 6.0 revision.";
  }


  grouping ALL {
    description
      "Common node of context, context-number,
      context-location";

    container all {
      description "context bag";
      uses DUMPER-CRASH-INFO-XML;
    }
  }

  grouping ENTER {
    description "Common node of location, number";

    container enter {
      description "Context info bag";
      uses DUMPER-CRASH-INFO-XML;
    }
  }

  container context {
    config false;
    description "Core dump configuration commands";

    container context-numbers {
      description "Context number table";

      list context-number {
        key "context-num";
        description "Context number ";

        container locations {
          description "Core Context location table";

          list location {
            key "node-name";
            description
              "Operational Context for a particular location";
            leaf node-name {
              type xr:Node-id;
              description "The node";
            }
            uses ENTER;
          }
        }
        leaf context-num {
          type uint32;
          description "Context for which crash dump info required";
        }
        uses ALL;
      }
    }

    container context-locations {
      description "Core Context location table";

      list context-location {
        key "node-name";
        description "Operational Context for a particular location";

        container numbers {
          description "Context number Table";

          list number {
            key "context-num";
            description "Context number";
            leaf context-num {
              type uint32;
              description
                "Context for which crash dump info required";
            }
            uses ENTER;
          }
        }
        leaf node-name {
          type xr:Node-id;
          description "The node";
        }
        uses ALL;
      }
    }
    uses ALL;
  }
}
