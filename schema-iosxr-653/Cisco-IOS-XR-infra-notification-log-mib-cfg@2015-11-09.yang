module Cisco-IOS-XR-infra-notification-log-mib-cfg {

  /*** NAMESPACE / PREFIX DEFINITION ***/

  namespace "http://cisco.com/ns/yang"+
    "/Cisco-IOS-XR-infra-notification-log-mib-cfg";


  prefix "infra-notification-log-mib-cfg";

  /*** LINKAGE (IMPORTS / INCLUDES) ***/

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-notification-log-mib package configuration.

     This YANG module augments the
       Cisco-IOS-XR-snmp-agent-cfg
     module with configuration data.

     Copyright (c) 2013-2018 by Cisco Systems, Inc.
     All rights reserved.";

  revision "2015-11-09" {
    description
      "IOS XR 6.0 revision.";
  }


  augment "/a1:mib" {

    container notification-log-mib {
      description "Notification log MIB configuration";
      leaf global-age-out {
        type uint32 {
          range "1..4294967295";
        }
        units "minute";
        description
          "GlobalAgeOut is the minutes associated with the
          mib";
      }
      leaf disable {
        type empty;
        description
          "Disable, to disable the logging in default log";
      }
      leaf default {
        type empty;
        description "To create a default log";
      }
      leaf global-size {
        type uint32 {
          range "1..15000";
        }
        description
          "GlobalSize, max number of notifications that
          can be logged in all logs";
      }
      leaf default-size {
        type uint32 {
          range "1..15000";
        }
        description
          "The max number of notifications that this log
          (default) can hold";
      }
    }
    description
      "This augment extends the configuration data of
      'Cisco-IOS-XR-snmp-agent-cfg'";
  }
}
