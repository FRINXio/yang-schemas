submodule Cisco-IOS-XR-manageability-object-tracking-oper-sub1 {

  belongs-to Cisco-IOS-XR-manageability-object-tracking-oper {
    prefix Cisco-IOS-XR-manageability-object-tracking-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR manageability-object-tracking package operational data.

     Copyright (c) 2013-2018 by Cisco Systems, Inc.
     All rights reserved.";

  revision "2015-11-09" {
    description
      "IOS XR 6.0 revision.";
  }

  typedef Track {
    type enumeration {
      enum interface-type {
        value 1;
        description "Line protocol type";
      }
      enum route-type {
        value 2;
        description "Route type";
      }
      enum bool-and-type {
        value 3;
        description "Boolean and type";
      }
      enum bool-or-type {
        value 4;
        description "Boolean or type";
      }
      enum ipsla-type {
        value 5;
        description "Ipsla track type";
      }
      enum undefined-type {
        value 6;
        description "type undefined";
      }
      enum threshold-weight {
        value 7;
        description "type threshold weight";
      }
      enum threshold-percentage {
        value 8;
        description "type threshold percentage";
      }
      enum bfd-type {
        value 9;
        description "type bfd rtr";
      }
    }
    description "Track";
  }

  grouping TRACK-INFO-BRIEF {
    description "TRACK INFO BRIEF";

    list track-info-brief {
      description "track info brief";

      container track-type-info {
        description "Track type information";
        uses TRACK-TYPE-INFO-UNION;
      }
      leaf tracke-name {
        type string {
          length "0..33";
        }
        description "Track Name";
      }
      leaf type {
        type Track;
        description "Track type";
      }
      leaf track-state {
        type boolean;
        description "Track state";
      }
    }
  }

  grouping DELAYED-STATE-STATUS {
    description "DELAYED STATE STATUS";
    leaf time-remaining {
      type uint32;
      units "second";
      description
        "The time remaining in seconds for the counter to
        trigger state change";
    }
    leaf track-state {
      type boolean;
      description
        "State the track will transition to. Track state.
        True means track is up; False means track is
        down.";
    }
  }

  grouping INTERFACE-TRACKING-INFO {
    description "INTERFACE TRACKING INFO";

    list interface-tracking-info {
      description "interface tracking info";
      leaf interface-name {
        type string {
          length "0..120";
        }
        description "Interface Name";
      }
    }
  }

  grouping THRESHOLD-TRACK-INFO {
    description "THRESHOLD TRACK INFO";

    list threshold-track-info {
      description "threshold track info";
      leaf object-name {
        type string {
          length "0..33";
        }
        description "Object name";
      }
      leaf track-state {
        type boolean;
        description
          "Track state. True means track is up; False
          means track is down.";
      }
      leaf weight {
        type uint32;
        units "percentage";
        description
          "Weight is the number assigned to a track object
          . In case of a type threshold weight( i.e.
          weighted sum list), weight is asigned by User
          at the time of configuration. In case of a type
          threshold percentage (i.e. percentage based
          list), weight is internally computed by
          (1/N)x100, where N is the number of objects in
          the list.";
      }
    }
  }

  grouping BOOL-TRACK-INFO {
    description "BOOL TRACK INFO";

    list bool-track-info {
      description "bool track info";
      leaf object-name {
        type string {
          length "0..33";
        }
        description "Object Name";
      }
      leaf track-state {
        type boolean;
        description "Track state";
      }
      leaf with-not {
        type boolean;
        description "Track object with Not";
      }
    }
  }

  grouping BFDRTR-TRACK-INFO {
    description "BFDRTR TRACK INFO";
    leaf interface-name {
      type string {
        length "0..120";
      }
      description "Interface Name";
    }
    leaf destination-address {
      type uint32;
      description "Destination Address";
    }
    leaf rate {
      type uint32;
      description "Rate";
    }
    leaf debounce-count {
      type uint32;
      description "Debounce Count";
    }
  }

  grouping RTR-TRACK-INFO {
    description "RTR TRACK INFO";
    leaf ipsla-op-id {
      type uint32;
      description "Op Id";
    }
    leaf rtt {
      type uint32;
      description "Latest RTT";
    }
    leaf return-code {
      type uint32;
      description "Latest Return Code";
    }
  }

  grouping ROUTE-TRACK-INFO {
    description "ROUTE TRACK INFO";
    leaf prefix {
      type uint32;
      description "Prefix";
    }
    leaf prefix-length {
      type uint32;
      description "Prefix Length";
    }
    leaf vrf {
      type string {
        length "0..120";
      }
      description "VRF Name";
    }
    leaf next-hop {
      type string {
        length "0..120";
      }
      description "Next Hop";
    }
  }

  grouping INTF-TRACK-INFO {
    description "INTF TRACK INFO";
    leaf interface-name {
      type string {
        length "0..120";
      }
      description "Interface Name";
    }
  }

  grouping TRACK-TYPE-INFO-UNION {
    description "TRACK TYPE INFO UNION";

    container interface-tracks {
      when "../discriminant = 'interface-type'" {
        description "../discriminant = 'InterfaceType'";
      }
      description "track type interface info";
      uses INTF-TRACK-INFO;
    }

    container route-tracks {
      when "../discriminant = 'route-type'" {
        description "../discriminant = 'RouteType'";
      }
      description "track type route info";
      uses ROUTE-TRACK-INFO;
    }

    container ipsla-tracks {
      when "../discriminant = 'ipsla-type'" {
        description "../discriminant = 'IpslaType'";
      }
      description "track type rtr info";
      uses RTR-TRACK-INFO;
    }

    container bfd-tracks {
      when "../discriminant = 'bfd-type'" {
        description "../discriminant = 'BfdType'";
      }
      description "track type bfdrtr info";
      uses BFDRTR-TRACK-INFO;
    }
    leaf discriminant {
      type Track;
      description "discriminant";
    }
  }

  grouping TRACK-INFO {
    description "TRACK INFO";

    list track-info {
      description "track info";

      container track-type-info {
        description "Track type information";
        uses TRACK-TYPE-INFO-UNION;
      }

      container bool-tracks {
        description "boolean objects";
        uses BOOL-TRACK-INFO;
      }

      container threshold-tracks {
        description "Threshold objects";
        uses THRESHOLD-TRACK-INFO;
      }

      container tracking-interaces {
        description "Tracking Interfaces";
        uses INTERFACE-TRACKING-INFO;
      }

      container delayed {
        description "Is the state change delay counter in progress";
        uses DELAYED-STATE-STATUS;
      }
      leaf tracke-name {
        type string {
          length "0..33";
        }
        description "Track Name";
      }
      leaf type {
        type Track;
        description "Track type";
      }
      leaf track-state {
        type boolean;
        description "Track state";
      }
      leaf state-change-counter {
        type uint32;
        description "State Change Counter";
      }
      leaf seconds-last-change {
        type uint64;
        units "second";
        description "Seconds Last Change";
      }
      leaf threshold-up {
        type uint32;
        description "User specified threshold upper limit";
      }
      leaf threshold-down {
        type uint32;
        description "User specified threshold lower limit";
      }
    }
  }
}
