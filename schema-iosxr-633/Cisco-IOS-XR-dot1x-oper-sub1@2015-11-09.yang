submodule Cisco-IOS-XR-dot1x-oper-sub1 {

  belongs-to Cisco-IOS-XR-dot1x-oper {
    prefix Cisco-IOS-XR-dot1x-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dot1x package operational data.

     Copyright (c) 2013-2017 by Cisco Systems, Inc.
     All rights reserved.";

  revision "2015-11-09" {
    description
      "IOS XR 6.0 revision.";
  }


  grouping DOT1X-INTERFACE-MKA {
    description "DOT1X INTERFACE MKA";
    leaf tie-break-role {
      type string;
      description
        "Dot1x Tie breaker role chosen for mka when PAE
        type is BOTH";
    }
    leaf eap-based-macsec {
      type string;
      description "EAP Mode status for MKA";
    }
    leaf mka-start-time {
      type string;
      description
        "Time stamp when Dot1x posting a message to  MKA
        to start session.";
    }
    leaf mka-stop-time {
      type string;
      description
        "Time stamp when Dot1x posting a message to  MKA
        to stop session.";
    }
    leaf mka-response-time {
      type string;
      description "Time Stamp of MKA acknowledgement to Dot1x";
    }
  }

  grouping DOT1X-SUPP-CLIENT-INFO {
    description "DOT1X SUPP CLIENT INFO";
    leaf mac {
      type string;
      description "formatted MAC Address";
    }
    leaf eap-method {
      type string;
      description "EAP Method";
    }
    leaf last-auth-time {
      type string;
      description "Last Authenticated Timestamp (formatted)";
    }
    leaf auth-sm-state {
      type string;
      description "supp SM State";
    }
    leaf auth-bend-sm-state {
      type string;
      description "supp back end SM State";
    }
  }

  grouping DOT1X-SUPP-INFO {
    description "DOT1X SUPP INFO";
    leaf eap-profile {
      type string;
      description "EAP profile";
    }
    leaf config-dependency {
      type string;
      description "Configuration Dependency ";
    }

    list client {
      description "Supp Client info";
      uses DOT1X-SUPP-CLIENT-INFO;
    }
  }

  grouping DOT1X-AUTH-CLIENT-INFO {
    description "DOT1X AUTH CLIENT INFO";
    leaf mac {
      type string;
      description "formatted MAC Address";
    }
    leaf auth-sm-state {
      type string;
      description "Auth SM State";
    }
    leaf auth-bend-sm-state {
      type string;
      description "Auth back end SM State";
    }
    leaf time-to-next-reauth {
      type string;
      description "remaining time for next reauthentication";
    }
    leaf last-auth-time {
      type string;
      description "Last Authenticated Timestamp (formatted)";
    }
  }

  grouping DOT1X-AUTH-INFO {
    description "DOT1X AUTH INFO";
    leaf reauth {
      type string;
      description "Re-Authentication enabled status";
    }
    leaf config-dependency {
      type string;
      description "Configuration Dependency ";
    }

    list client {
      description "Authenticator client list";
      uses DOT1X-AUTH-CLIENT-INFO;
    }
  }

  grouping DOT1X-INTERFACE-INFO {
    description "DOT1X INTERFACE INFO";

    container auth-info {
      description "Dot1x Authenticator info";
      uses DOT1X-AUTH-INFO;
    }

    container supp-info {
      description "Dot1x Supplicant info";
      uses DOT1X-SUPP-INFO;
    }
    leaf pae {
      type string;
      description "PAE type on interface";
    }
    leaf port-status {
      type string;
      description "Dot1x Port Status";
    }
    leaf dot1x-profile {
      type string;
      description "Dot1x Profile";
    }
  }

  grouping DOT1X-INTERFACE-DETAIL {
    description "DOT1X INTERFACE DETAIL";

    container intf-info {
      description "Dot1x interface Info";
      uses DOT1X-INTERFACE-INFO;
    }

    container mka-status-info {
      description "MKA session secure status";
      uses DOT1X-INTERFACE-MKA;
    }
    leaf interface-name {
      type string;
      description "Interface Display name ";
    }
    leaf interface-sname {
      type string;
      description "Interface Display short_name ";
    }
    leaf if-handle {
      type string;
      description "Interface handle";
    }
    leaf mac {
      type string;
      description "formatted MAC Address";
    }
    leaf ethertype {
      type string;
      description "EAPOL Ethertype";
    }
  }

  grouping DOT1X-GLOBAL-STATISTICS {
    description "DOT1X GLOBAL STATISTICS";
    leaf tx-total {
      type uint32;
      description "TxTotal";
    }
    leaf rx-total {
      type uint32;
      description "RxTotal";
    }
    leaf rx-no-idb {
      type uint32;
      description "RxNoIDB";
    }
  }

  grouping DOT1X-STATISTICS {
    description "DOT1X STATISTICS";

    container gl-stats {
      description "Global statistics";
      uses DOT1X-GLOBAL-STATISTICS;
    }

    list if-stats {
      description "dot1x interface statistics list";
      uses DOT1X-IF-STATISTICS;
    }
  }

  grouping DOT1X-SUPP-TIMERS {
    description "DOT1X SUPP TIMERS";
    leaf auth-period {
      type uint32;
      units "second";
      description
        "in Seconds, supplicant waits for a response from
        an authenticator except for EAPOL-START before
        timing out";
    }
    leaf held-period {
      type uint32;
      units "second";
      description
        "in Seconds, supplicant will stay in the HELD
        state (that is, the length of time it will wait
        before trying to send the credentials again
        after a failed attempt)";
    }
    leaf start-period {
      type uint32;
      units "second";
      description
        "Configures the interval, in seconds, between two
        successive EAPOL-Start frames when they are
        being retransmitted";
    }
    leaf max-start {
      type uint32;
      description
        "Max No. of EAPOL-Start frames supplicant can
        send to the authenticator";
    }
  }

  grouping DOT1X-AUTH-TIMERS {
    description "DOT1X AUTH TIMERS";
    leaf quiet-period {
      type uint32;
      units "second";
      description
        "in Seconds, authenticator remains quiet (in the
        HELD state) following a failed authentication
        exchange before trying to reauthenticate the
        client";
    }
    leaf tx-period {
      type uint32;
      units "second";
      description
        "in Seconds, Timeout for supplicant reply,
        authenticator-to-supplicant retransmission time
        for EAP-request-ID packets (assuming that no
        response is received) from the client";
    }
    leaf max-reauth-req {
      type uint32;
      description
        "Max No. of Reauthentication Attempts (or)
        retransmits an EAP-request-ID frame to the
        client before restarting the authentication
        process";
    }
    leaf supp-timeout {
      type uint32;
      units "second";
      description
        "in Seconds, Timeout for supplicant reply,
        authenticator-to-supplicant retransmission time
        for all EAP messages except for EAP Request ID
        packets";
    }
    leaf max-req {
      type uint32;
      description
        "Max No. of EAP-Req (except for EAP-Request-ID)
        retransmits (authenticator-to-supplicant) before
        sending EAP-Failure";
    }
    leaf reauth-period {
      type uint32;
      units "second";
      description
        "in Seconds,  after which an automatic
        reauthentication should be initiated";
    }
  }

  grouping DOT1X-DEFAULT {
    description "DOT1X DEFAULT";

    container auth-timers {
      description "Dot1x Authenticator default Timer values";
      uses DOT1X-AUTH-TIMERS;
    }

    container supp-timers {
      description "Dot1x Supllicant default Timer values";
      uses DOT1X-SUPP-TIMERS;
    }
    leaf version {
      type uint32;
      description "Dot1x Protocol Version";
    }
  }

  grouping DOT1X-IF-SUPP-STATISTICS {
    description "DOT1X IF SUPP STATISTICS";
    leaf rx-req {
      type uint32;
      description "RxReq";
    }
    leaf rx-invalid {
      type uint32;
      description "RxInvalid";
    }
    leaf rx-len-err {
      type uint32;
      description "RxLenErr";
    }
    leaf rx-my-mac-err {
      type uint32;
      description "RxMyMacErr";
    }
    leaf rx-total {
      type uint32;
      description "RxTotal";
    }
    leaf tx-start {
      type uint32;
      description "TxStart";
    }
    leaf tx-logoff {
      type uint32;
      description "TxLogoff";
    }
    leaf tx-resp {
      type uint32;
      description "TxResp";
    }
    leaf tx-total {
      type uint32;
      description "TxTotal";
    }
  }

  grouping DOT1X-IF-AUTH-STATISTICS {
    description "DOT1X IF AUTH STATISTICS";
    leaf rx-start {
      type uint32;
      description "RxStart";
    }
    leaf rx-logoff {
      type uint32;
      description "RxLogoff";
    }
    leaf rx-resp {
      type uint32;
      description "RxResp";
    }
    leaf rx-resp-id {
      type uint32;
      description "RxRespID";
    }
    leaf rx-invalid {
      type uint32;
      description "RxInvalid";
    }
    leaf rx-len-err {
      type uint32;
      description "RxLenErr";
    }
    leaf rx-my-mac-err {
      type uint32;
      description "RxMyMacErr";
    }
    leaf rx-total {
      type uint32;
      description "RxTotal";
    }
    leaf tx-req {
      type uint32;
      description "TxReq";
    }
    leaf tx-reqid {
      type uint32;
      description "TxReqID";
    }
    leaf tx-total {
      type uint32;
      description "TxTotal";
    }
  }

  grouping DOT1X-IDB-STATISTICS {
    description "DOT1X IDB STATISTICS";
    leaf rx-total {
      type uint32;
      description "RxTotal";
    }
    leaf tx-total {
      type uint32;
      description "TxTotal";
    }
    leaf no-rx-on-intf-down {
      type uint32;
      description "NoRxOnIntfDown";
    }
  }

  grouping DOT1X-IF-STATISTICS {
    description "DOT1X IF STATISTICS";

    container idb {
      description "Dot1x interface database Statistics";
      uses DOT1X-IDB-STATISTICS;
    }

    container auth {
      description "Dot1x Authenticator Port Statistics";
      uses DOT1X-IF-AUTH-STATISTICS;
    }

    container supp {
      description "Dot1x Supplicant Port Statistics";
      uses DOT1X-IF-SUPP-STATISTICS;
    }
    leaf interface-name {
      type string;
      description "Interface Display name ";
    }
    leaf pae {
      type string;
      description "PAE type on interface";
    }
  }
}
