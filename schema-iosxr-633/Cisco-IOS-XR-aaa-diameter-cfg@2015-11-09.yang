module Cisco-IOS-XR-aaa-diameter-cfg {

  /*** NAMESPACE / PREFIX DEFINITION ***/

  namespace "http://cisco.com/ns/yang/Cisco-IOS-XR-aaa-diameter-cfg";


  prefix "aaa-diameter-cfg";

  /*** LINKAGE (IMPORTS / INCLUDES) ***/

  import ietf-inet-types { prefix "inet"; }

  import Cisco-IOS-XR-types { prefix "xr"; }

  import Cisco-IOS-XR-aaa-lib-cfg { prefix "a1"; }

  import Cisco-IOS-XR-aaa-locald-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-diameter package configuration.

     This YANG module augments the
       Cisco-IOS-XR-aaa-lib-cfg,
       Cisco-IOS-XR-aaa-locald-cfg
     modules with configuration data.

     Copyright (c) 2013-2017 by Cisco Systems, Inc.
     All rights reserved.";

  revision "2015-11-09" {
    description
      "IOS XR 6.0 revision.";
  }

  typedef Aaa-diameter-tls {
    type uint32 {
      range "0..1";
    }
    description "Aaa diameter tls";
  }
  typedef Aaa-diameter-timeout {
    type uint32 {
      range "6..1000";
    }
    description "Aaa diameter timeout";
  }
  typedef Aaa-diameter-port {
    type uint32 {
      range "1..65535";
    }
    description "Aaa diameter port";
  }
  typedef Aaa-diameter-attr {
    type uint32 {
      range "0..23";
    }
    description "Aaa diameter attr";
  }

  augment "/a1:aaa" {

    container diameter {
      description "Diameter base protocol";

      container gy {
        description "Start diameter policy-if";
        leaf retransmit {
          type uint32 {
            range "1..10";
          }
          description "Set retransmit count";
        }
        leaf dest-host {
          type string;
          description "Destination Host name in FQDN format";
        }
        leaf tx-timer {
          type Aaa-diameter-timeout;
          description "Transaction timer value";
        }
      }

      container origin {
        description "Origin sub commands";
        leaf realm {
          type string;
          description "Origin Realm String";
        }
        leaf host {
          type string;
          description "Host name in FQDN format";
        }
      }

      container nas {
        description "Start diameter Nas";
        leaf dest-host {
          type string;
          description "Destination Host name in FQDN format";
        }
      }

      container diameter-tls {
        description "TLS sub commands";
        leaf trustpoint {
          type string;
          description "Trustpoint label to be used";
        }
      }

      container peers {
        description "List of diameter peers";

        list peer {
          key "peer-name";
          description "Diameter peer instance";

          container peer-timer {
            description "Timers used for the peer";
            leaf transaction {
              type Aaa-diameter-timeout;
              description "Timer value in seconds";
            }
            leaf connection {
              type Aaa-diameter-timeout;
              description "Timer value in seconds";
            }
            leaf watchdog {
              type Aaa-diameter-timeout;
              description "Timer value in seconds";
            }
          }

          container peer-type {
            description "Peer Type";
            leaf server {
              type boolean;
              description "Enabled or disabled";
            }
          }
          leaf host-destination {
            type string;
            description "Destination host information";
          }
          leaf ipv4-address {
            type inet:ipv4-address-no-zone;
            description "IPv4 address of diameter server";
          }
          leaf realm-destination {
            type string;
            description "Realm to which the peer belongs to";
          }
          leaf tcp-transport {
            type Aaa-diameter-port;
            description "Specify a Diameter transport protocol";
          }
          leaf source-interface {
            type xr:Interface-name;
            description
              "Specify interface for source address in
              DIAMETER packets";
          }
          leaf ipv6-address {
            type inet:ipv6-address-no-zone;
            description "IPv6 address of diameter server";
          }
          leaf tls-transport {
            type Aaa-diameter-tls;
            description "Specify a Diameter security type";
          }
          leaf vrf-ip {
            type string;
            description "VRF the peer belongs to";
          }
          leaf peer-name {
            type xr:Cisco-ios-xr-string;
            description "Name for the diameter peer configuration";
          }
        }
      }

      container diams {
        description "Attribute list configuration for test command";

        list diam {
          key "list-id";
          description "attribute list configuration";

          container diam-attr-defs {
            description "Specify an attribute definition";

            list diam-attr-def {
              key "vendor-id attribute-id";
              description "vendor id";

              container diam-attr-value {
                description "attr subcommands";
                leaf type-string {
                  type string;
                  description "String type";
                }
                leaf type-ipv4-address {
                  type inet:ipv4-address-no-zone;
                  description "IPv4 address type";
                }
                leaf type-binary {
                  type string;
                  description "Binary type";
                }
                leaf type-boolean {
                  type uint32 {
                    range "0..4294967295";
                  }
                  description "Boolean type";
                }
                leaf type-enum {
                  type uint32 {
                    range "0..4294967295";
                  }
                  description "Enumeration type";
                }
                leaf type-grouped {
                  type uint32 {
                    range "0..99";
                  }
                  description "Grouped attribute";
                }
                leaf type-ulong {
                  type uint32 {
                    range "0..4294967295";
                  }
                  description "Numeric type";
                }
                leaf type-identity {
                  type string;
                  description "Diameter-identity type";
                }
                leaf data-type {
                  type Aaa-diameter-attr;
                  description "Dataypte of attribute";
                }
                leaf mandatory {
                  type uint32 {
                    range "0..1";
                  }
                  description "Is mandatory?";
                }
              }
              leaf vendor-id {
                type uint32 {
                  range "0..4294967295";
                }
                description "value for vendor id";
              }
              leaf attribute-id {
                type uint32 {
                  range "1..65535";
                }
                description "enter attribute id";
              }
            }
          }
          leaf list-id {
            type uint32 {
              range "0..99";
            }
            description "attribute list number";
          }
        }
      }

      container gx {
        description "Start diameter policy-if";
        leaf retransmit {
          type uint32 {
            range "1..10";
          }
          description "Set retransmit count";
        }
        leaf dest-host {
          type string;
          description "Destination Host name in FQDN format";
        }
        leaf tx-timer {
          type Aaa-diameter-timeout;
          description "Transaction timer value";
        }
      }

      container diameter-timer {
        description "Timers used for the peer";
        leaf transaction {
          type Aaa-diameter-timeout;
          description "Timer value in seconds";
        }
        leaf connection {
          type Aaa-diameter-timeout;
          description "Timer value in seconds";
        }
        leaf watchdog {
          type Aaa-diameter-timeout;
          description "Timer value in seconds";
        }
      }

      container vendor {
        description "Vendor specific";

        container supported {
          description "Supported vendors";
          leaf cisco {
            type boolean;
            description "Cisco attribute support";
          }
          leaf threegpp {
            type boolean;
            description "3GPP attribute support";
          }
          leaf etsi {
            type boolean;
            description "Etsi attribute support";
          }
          leaf vodafone {
            type boolean;
            description "Vodafone attribute support";
          }
        }
      }
      leaf source-interface {
        type xr:Interface-name;
        description
          "Specify interface for source address in
          DIAMETER packets";
      }
    }
    description
      "This augment extends the configuration data of
      'Cisco-IOS-XR-aaa-lib-cfg'";
  }

  augment "/a1:aaa/a2:server-groups" {

    container diameter-server-groups {
      description "DIAMETER server group definition";

      list diameter-server-group {
        key "server-group-name";
        description "DIAMETER server group name";

        container servers {
          description
            "List of DIAMETER servers present in the group";

          list server {
            key "ordering-index peer-name";
            description "A server to include in the server group";
            leaf ordering-index {
              type int32;
              description
                "This is used to sort the servers in the
                order of precedence";
            }
            leaf peer-name {
              type xr:Cisco-ios-xr-string;
              description
                "Name for the diameter peer configuration";
            }
          }
        }
        leaf server-group-name {
          type xr:Cisco-ios-xr-string;
          description "DIAMETER server group name";
        }
      }
    }
    description
      "This augment extends the configuration data of
      'Cisco-IOS-XR-aaa-locald-cfg'";
  }
}
