module Cisco-IOS-XR-dwdm-ui-cfg {

  /*** NAMESPACE / PREFIX DEFINITION ***/

  namespace "http://cisco.com/ns/yang/Cisco-IOS-XR-dwdm-ui-cfg";


  prefix "dwdm-ui-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dwdm-ui package configuration.

     This YANG module augments the
       Cisco-IOS-XR-ifmgr-cfg
     module with configuration data.

     Copyright (c) 2013-2017 by Cisco Systems, Inc.
     All rights reserved.";

  revision "2017-05-01" {
    description
      "Fixing backward compatibility error in module.";
  }

  revision "2015-12-16" {
    description
      "Adding additional In Service Transport Admin State to allow configuration while dwdm controller is in service";
  }

  revision "2015-11-09" {
    description
      "IOS XR 6.0 revision.";
  }

  typedef Prbs-pattern {
    type enumeration {
      enum none {
        value 0;
        description "None Pattern";
      }
      enum null {
        value 1;
        description "Null Pattern";
      }
      enum pn11 {
        value 2;
        description "PN11 Pattern";
      }
      enum pn23 {
        value 3;
        description "PN23 Pattern";
      }
      enum pn31 {
        value 4;
        description "PN31 Pattern";
      }
    }
    description "Prbs pattern";
  }
  typedef Proactive {
    type enumeration {
      enum default {
        value 1;
        description "Proactive Protection Default Mode";
      }
      enum graceful {
        value 2;
        description "Proactive Protection Graceful Mode";
      }
    }
    description "Proactive";
  }
  typedef Expected-tti {
    type enumeration {
      enum expected-tti-ascii {
        value 3;
        description "Expected TTI ascii string";
      }
      enum expected-tti-hex {
        value 4;
        description "Expected TTI hex string";
      }
    }
    description "Expected tti";
  }
  typedef Fec {
    type enumeration {
      enum none {
        value 0;
        description "No FEC";
      }
      enum standard {
        value 1;
        description "Standard FEC";
      }
      enum enhanced {
        value 2;
        description "Enhanced FEC";
      }
      enum high-gain-hd {
        value 3;
        description "High-Gain Hard Decision";
      }
      enum long-haul-hd {
        value 4;
        description "Long-Haul Hard Decision";
      }
      enum high-gain-sd {
        value 5;
        description "High-Gain Soft Decision";
      }
      enum long-haul-sd {
        value 6;
        description "Long-Haul Soft Decision";
      }
      enum ci-bch {
        value 7;
        description "Ci BCH";
      }
      enum high-gain-multivendor-hd {
        value 8;
        description
          "High-Gain Multivendor Interoperable Hard
          Decision";
      }
    }
    description "Fec";
  }
  typedef Framing {
    type enumeration {
      enum opu1e {
        value 1;
        description "opu1e Framing";
      }
      enum opu2e {
        value 2;
        description "opu2e Framing";
      }
    }
    description "Framing";
  }
  typedef Otu-threshold {
    type enumeration {
      enum prefec-sd {
        value 0;
        description "PREFEC SD BER THRESHOLD";
      }
      enum prefec-sf {
        value 1;
        description "PREFEC SF BER THRESHOLD";
      }
      enum otu-sd {
        value 4;
        description "OTU SD BER threshold";
      }
      enum otu-sf {
        value 5;
        description "OTU SF BER threshold";
      }
    }
    description "Otu threshold";
  }
  typedef Dwdm-loopback {
    type enumeration {
      enum none {
        value 0;
        description "No Loopback";
      }
      enum line {
        value 1;
        description "Line Loopback";
      }
      enum internal {
        value 2;
        description "Internal Loopback";
      }
    }
    description "Dwdm loopback";
  }
  typedef Efec {
    type enumeration {
      enum none {
        value 0;
        description
          "default submode to handle backward
          compatibility";
      }
      enum i.4 {
        value 1;
        description "efec i.4";
      }
      enum i.7 {
        value 2;
        description "efec i.7";
      }
    }
    description "Efec";
  }
  typedef Odu-alarm {
    type enumeration {
      enum oci {
        value 14;
        description "ODU OCI";
      }
      enum odu-ais {
        value 15;
        description "ODU AIS";
      }
      enum lck {
        value 16;
        description "ODU LCK";
      }
      enum odu-bdi {
        value 17;
        description "ODU BDI";
      }
      enum odu-sf {
        value 20;
        description "ODU SF BER";
      }
      enum odu-sd {
        value 21;
        description "ODU SD BER";
      }
      enum plm {
        value 22;
        description "ODU PTIM";
      }
      enum odu-tim {
        value 23;
        description "ODU TIM";
      }
    }
    description "Odu alarm";
  }
  typedef Prbs-mode {
    type enumeration {
      enum source {
        value 0;
        description "Source Mode";
      }
      enum sink {
        value 1;
        description "Sink Mode";
      }
      enum source-sink {
        value 2;
        description "Source-Sink Mode";
      }
      enum invalid {
        value 3;
        description "Invalid Mode";
      }
    }
    description "Prbs mode";
  }
  typedef Tx-tti {
    type enumeration {
      enum tx-tti-ascii {
        value 0;
        description "TX TTI ascii string";
      }
      enum tx-tti-hex {
        value 1;
        description "TX TTI hex string";
      }
    }
    description "Tx tti";
  }
  typedef Otu-alarm {
    type enumeration {
      enum los {
        value 0;
        description "LOS";
      }
      enum lof {
        value 1;
        description "LOF";
      }
      enum lom {
        value 2;
        description "LOM";
      }
      enum iae {
        value 6;
        description "OTU IAE";
      }
      enum otu-bdi {
        value 7;
        description "OTU BDI";
      }
      enum otu-tim {
        value 8;
        description "OTU TIM";
      }
      enum otu-sf {
        value 10;
        description "OTU SF BER";
      }
      enum otu-sd {
        value 11;
        description "OTU SD BER";
      }
      enum fec-mismatch {
        value 24;
        description "FEC mismatch";
      }
      enum prefec-sd-ber {
        value 31;
        description "PREFEC SD BER";
      }
      enum prefec-sf-ber {
        value 32;
        description "PREFEC SF BER";
      }
    }
    description "Otu alarm";
  }
  typedef Dwdm-admin-state {
    type enumeration {
      enum out-of-service {
        value 0;
        description "Out of service";
      }
      enum in-service {
        value 1;
        description "In service";
      }
      enum maintenance {
        value 2;
        description "Out of service maintenance";
      }
      enum in-service-config-allowed {
        value 3;
        description "In service Config allowed";
      }
    }
    description "Dwdm admin state";
  }
  typedef Odu-threshold {
    type enumeration {
      enum odu-sd {
        value 8;
        description "ODU SD BER threshold";
      }
      enum odu-sf {
        value 9;
        description "ODU SF BER threshold";
      }
    }
    description "Odu threshold";
  }
  typedef Wave-channel-num {
    type enumeration {
      enum default {
        value 0;
        description "Default Wave Channel Number";
      }
      enum channel-wavelength {
        value 1;
        description "Wavelength Wave Channel Number";
      }
      enum channel-frequency {
        value 2;
        description "Frequency Wave Channel Number";
      }
      enum 100mhz-frequency {
        value 4;
        description "Frequency in Steps of 100MHz";
      }
    }
    description "Wave channel num";
  }

  augment "/a1:interface-configurations/a1:interface-configuration" {
    leaf maintenance-embargo {
      type boolean;
      description
        "configure maintenance embargo flag on the given
        interface";
    }
    description
      "This augment extends the configuration data of
      'Cisco-IOS-XR-ifmgr-cfg'";
  }

  augment "/a1:interface-configurations/a1:interface-configuration" {

    container dwdm {
      description "DWDM port controller configuration";

      container network-srlgs {
        description "Configure Network srlgs";

        list network-srlg {
          key "set-id";
          description "Configure network srlg sets";
          leaf set-id {
            type uint32 {
              range "1..17";
            }
            description "Set index";
          }
          leaf srlg1 {
            type uint32 {
              range "0..4294967294";
            }
            description "none";
          }
          leaf srlg2 {
            type uint32 {
              range "0..4294967294";
            }
            description "none";
          }
          leaf srlg3 {
            type uint32 {
              range "0..4294967294";
            }
            description "none";
          }
          leaf srlg4 {
            type uint32 {
              range "0..4294967294";
            }
            description "none";
          }
          leaf srlg5 {
            type uint32 {
              range "0..4294967294";
            }
            description "none";
          }
          leaf srlg6 {
            type uint32 {
              range "0..4294967294";
            }
            description "none";
          }
        }
      }

      container g709 {
        description "Configure G709 parameters";

        container odu {
          description "Configure ODU parameters";

          container odu-reports {
            description "Configure ODU alarm reporting";

            list odu-report {
              key "alarm";
              description "none";
              leaf alarm {
                type Odu-alarm;
                description "ODU alarm type";
              }
            }
          }

          container odu-thresholds {
            description "Configure ODU threshold value";

            list odu-threshold {
              key "threshold";
              description "none";
              leaf threshold {
                type Odu-threshold;
                description "ODU Threshold type";
              }
              leaf threshold-value {
                type uint32 {
                  range "1..9";
                }
                mandatory true;
                description "Bit error rate (10 to the minus n)";
              }
            }
          }

          container odu-expected-tti {
            description "Configure ODU Expected TTI value";
            leaf string-type {
              type Expected-tti;
              description "TTI string type (ascii or hex format)";
            }
            leaf ascii-string {
              when "../string-type = 'expected-tti-ascii'" {
                description "../StringType = EXPECTED_TTI_ASCII";
              }
              type string {
                length "1..64";
              }
              description "ASCII text (Max 64 characters)";
            }
            leaf hex-string {
              when "../string-type = 'expected-tti-hex'" {
                description "../StringType = EXPECTED_TTI_HEX";
              }
              type string {
                length "1..128";
              }
              description
                "Hex nibbles (Max 128- The string length
                should be an even number)";
            }
          }

          container odu-tx-tti {
            description "Configure ODU TTI value";
            leaf string-type {
              type Tx-tti;
              description "TTI string type (ascii or hex format)";
            }
            leaf ascii-string {
              when "../string-type = 'tx-tti-ascii'" {
                description "../StringType = TX_TTI_ASCII";
              }
              type string {
                length "1..64";
              }
              description "ASCII text (Max 64 characters)";
            }
            leaf hex-string {
              when "../string-type = 'tx-tti-hex'" {
                description "../StringType = TX_TTI_HEX";
              }
              type string {
                length "1..128";
              }
              description
                "Hex nibbles (Max 128- The string length
                should be an even number)";
            }
          }
        }

        container otu {
          description "Configure OTU parameters";

          container otu-expected-tti {
            description "Configure OTU Expected TTI value";
            leaf string-type {
              type Expected-tti;
              description "TTI string type (ascii or hex format)";
            }
            leaf ascii-string {
              when "../string-type = 'expected-tti-ascii'" {
                description "../StringType = EXPECTED_TTI_ASCII";
              }
              type string {
                length "1..64";
              }
              description "ASCII text (Max 64 characters)";
            }
            leaf hex-string {
              when "../string-type = 'expected-tti-hex'" {
                description "../StringType = EXPECTED_TTI_HEX";
              }
              type string {
                length "1..128";
              }
              description
                "Hex nibbles (Max 128- The string length
                should be an even number)";
            }
          }

          container otu-thresholds {
            description "Configure OTU threshold value";

            list otu-threshold {
              key "threshold";
              description "none";
              leaf threshold {
                type Otu-threshold;
                description "OTU Threshold type";
              }
              leaf threshold-value {
                type uint32 {
                  range "1..9";
                }
                mandatory true;
                description "Bit error rate (10 to the minus n)";
              }
            }
          }

          container frr {
            description
              "Configure FRR thresholds and Window for
              trigger and revert";

            container trigger-window {
              presence "Indicates a trigger-window node is"+
                " configured.";
              description "Configure FRR trigger window";
              leaf window {
                type uint32 {
                  range "10..10000";
                }
                mandatory true;
                description
                  "Integration window for FRR trigger in MS";
              }
              leaf dummy {
                type uint32 {
                  range "0..2";
                }
                description
                  "Just a Dummy for window for FRR revert in
                  MS";
              }
            }

            container revert-threshold {
              presence "Indicates a revert-threshold node is"+
                " configured.";
              description
                "Configure proactive protection revert
                threshold";
              leaf ber-base {
                type uint32 {
                  range "1..9";
                }
                mandatory true;
                description "Bit error rate base (x of xE-y)";
              }
              leaf ber-power {
                type uint32 {
                  range "3..10";
                }
                mandatory true;
                description "Bit error rate power (y of xE-y)";
              }
            }

            container trigger-threshold {
              presence "Indicates a trigger-threshold node is"+
                " configured.";
              description
                "Configure proactive protection trigger
                threshold";
              leaf ber-base {
                type uint32 {
                  range "1..9";
                }
                mandatory true;
                description "Bit error rate base (x of xE-y)";
              }
              leaf ber-power {
                type uint32 {
                  range "2..9";
                }
                mandatory true;
                description "Bit error rate power (y of xE-y)";
              }
            }

            container revert-window {
              presence "Indicates a revert-window node is"+
                " configured.";
              description "Configure FRR revert window";
              leaf window {
                type uint32 {
                  range "500..100000";
                }
                mandatory true;
                description
                  "Integration window for FRR revert in MS";
              }
              leaf dummy {
                type uint32 {
                  range "0..2";
                }
                description
                  "Just a Dummy for window for FRR revert in
                  MS";
              }
            }
          }

          container otu-reports {
            description "Configure OTU alarm reporting";

            list otu-report {
              key "alarm";
              description "none";
              leaf alarm {
                type Otu-alarm;
                description "OTU alarm type";
              }
            }
          }

          container otu-tx-tti {
            description "Configure OTU TTI value";
            leaf string-type {
              type Tx-tti;
              description "TTI string type (ascii or hex format)";
            }
            leaf ascii-string {
              when "../string-type = 'tx-tti-ascii'" {
                description "../StringType = TX_TTI_ASCII";
              }
              type string {
                length "1..64";
              }
              description "ASCII text (Max 64 characters)";
            }
            leaf hex-string {
              when "../string-type = 'tx-tti-hex'" {
                description "../StringType = TX_TTI_HEX";
              }
              type string {
                length "1..128";
              }
              description
                "Hex nibbles (Max 128- The string length
                should be an even number)";
            }
          }
        }

        container prbs {
          presence "Indicates a prbs node is configured.";
          description "Configure PRBS mode and pattern";
          leaf prbs-mode {
            type Prbs-mode;
            mandatory true;
            description "Enable PRBS with mode";
          }
          leaf prbs-pattern {
            type Prbs-pattern;
            mandatory true;
            description "Enable prbs test with pattern";
          }
        }

        container fec {
          presence "Indicates a fec node is configured.";
          description "Configure FEC mode";
          leaf fec-mode {
            type Fec;
            mandatory true;
            description
              "None, Standard, Enhanced, High-Gain,
              Long-Haul, Ci-BCH";
          }
          leaf efec-mode {
            type Efec;
            default "none";
            description
              "Enhanced FECMode to use i.4, i.7, Other
              FECMode to use None";
          }
        }
        leaf proactive {
          type Proactive;
          description
            "Enable proactive protectioni Graceful or
            Default mode";
        }
        leaf bdi-to-gais {
          type empty;
          description "Enable GAIS insertion";
        }
        leaf tim-to-gais {
          type empty;
          description
            "Configure Trace Identifier Mismatch alarm
            consequence";
        }
        leaf proactive-logging-file {
          type xr:Cisco-ios-xr-string {
            length "1..128";
          }
          description "Configure proactive protection log file";
        }
        leaf tti-processing {
          type empty;
          description
            "Configure Trail Trace Identifier  processing";
        }
        leaf enable {
          type boolean;
          description "Disable or Enable g709 framing";
        }
        leaf framing {
          type Framing;
          description
            "Over clocking mode for client signal bw
            compatibility";
        }
      }

      container wavelength {
        presence "Indicates a wavelength node is configured.";
        description "Configure transponder wavelength";
        leaf wave-channel {
          type uint32 {
            range "1..1568362";
          }
          mandatory true;
          description
            "Select a ITU channel number,channel range for
            C-band: 1~82,L-band:106~185,spacing:50GHZ or
            100MHz";
        }
        leaf wave-channel-number {
          type Wave-channel-num;
          mandatory true;
          description "Wave Channel Number";
        }
        leaf prog-frequency {
          type string {
            length "1..128";
          }
          description "Enter Frequency Data in THz";
        }
      }
      leaf enable-vtxp {
        type boolean;
        description "Disable or Enable VTXP configuration";
      }
      leaf network-port-id {
        type string {
          length "1..64";
        }
        description "Configure network port id";
      }
      leaf transport-admin-state {
        type Dwdm-admin-state;
        default "out-of-service";
        description "Configure transport admin state";
      }
      leaf laser {
        type empty;
        description "Configure laser off/on";
      }
      leaf transmit-power {
        type int32 {
          range "-190..10";
        }
        description "Select power level (in units of 0.1dBm)";
      }
      leaf rx-threshold {
        type int32 {
          range "-350..50";
        }
        description "Select power level (in units of 0.1dBm)";
      }
      leaf network-connection-id {
        type string {
          length "1..64";
        }
        description "Configure network connection id";
      }
      leaf loopback {
        type Dwdm-loopback;
        default "none";
        description "Configure loopback mode ";
      }
    }
    description
      "This augment extends the configuration data of
      'Cisco-IOS-XR-ifmgr-cfg'";
  }
}
