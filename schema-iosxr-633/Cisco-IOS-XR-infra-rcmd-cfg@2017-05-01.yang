module Cisco-IOS-XR-infra-rcmd-cfg {

  /*** NAMESPACE / PREFIX DEFINITION ***/

  namespace "http://cisco.com/ns/yang/Cisco-IOS-XR-infra-rcmd-cfg";


  prefix "infra-rcmd-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rcmd package configuration.

     This module contains definitions
     for the following management objects:
       router-convergence: Configure Router Convergence Monitoring

     Copyright (c) 2013-2017 by Cisco Systems, Inc.
     All rights reserved.";

  revision "2017-05-01" {
    description
      "Fixing backward compatibility error in module.";
  }

  revision "2015-11-09" {
    description
      "IOS XR 6.0 revision.";
  }

  typedef Rcmd-priority {
    type enumeration {
      enum critical {
        value 0;
        description "Critical routes";
      }
      enum high {
        value 1;
        description "High priority routes";
      }
      enum medium {
        value 2;
        description "Medium priority routes";
      }
      enum low {
        value 3;
        description "Low priority routes";
      }
    }
    description "Rcmd priority";
  }
  typedef Protocol-name {
    type enumeration {
      enum ospf {
        value 0;
        description "Configure parameters related to OSPF";
      }
      enum isis {
        value 1;
        description "Configure parameters related to ISIS";
      }
    }
    description "Protocol name";
  }

  container router-convergence {
    description "Configure Router Convergence Monitoring";

    container protocols {
      description "Table of Protocol";

      list protocol {
        key "protocol-name";
        description
          "Protocol for which to configure RCMD parameters";

        container priorities {
          description "Table of Priority";

          list priority {
            key "rcmd-priority";
            description "Priority";
            leaf threshold {
              type int32;
              description
                "Threshold value for convergence (in msec)";
            }
            leaf leaf-networks {
              type uint32 {
                range "10..100";
              }
              description
                "Specify the maximum number of leaf networks
                monitored";
            }
            leaf disable {
              type empty;
              description
                "Disables the monitoring of route convergence
                for specified priority";
            }
            leaf enable {
              type empty;
              description
                "Enable Priority. Deletion of this object
                also causes deletion of all associated
                objects under Priority.";
            }
            leaf frr-threshold {
              type uint32 {
                range "1..100";
              }
              units "percentage";
              description
                "Threshold value for Fast ReRoute Coverage
                (in percentage)";
            }
            leaf rcmd-priority {
              type Rcmd-priority;
              description "Specify the priority";
            }
          }
        }
        leaf enable {
          type empty;
          description
            "Enable Protocol for which to configure RCMD
            parameters. Deletion of this object also
            causes deletion of all associated objects
            under Protocol.";
        }
        leaf protocol-name {
          type Protocol-name;
          description "Specify the protocol";
        }
      }
    }

    container storage-location {
      presence "Indicates a storage-location node is configured.";
      description
        "Absolute directory path for saving the archive
        files. Example /disk0:/rcmd/ or
        <tftp-location>/rcmd/";
      leaf diagnostics {
        type string;
        description
          "Absolute directory path for storing diagnostic
          reports. Example /disk0:/rcmd/ or
          <tftp-location>/rcmd/";
      }
      leaf diagnostics-size {
        type uint32 {
          range "5..80";
        }
        description
          "Maximum size of diagnostics dir (5% - 80%) for
          local storage.";
      }
      leaf reports-size {
        type uint32 {
          range "5..80";
        }
        description
          "Maximum size of reports dir (5% - 80%) for
          local storage.";
      }
      leaf reports {
        type string;
        description
          "Absolute directory path for storing reports.
          Example /disk0:/rcmd/ or <tftp-location>/rcmd/";
      }
    }

    container mpls-ldp {
      presence "Indicates a mpls-ldp node is configured.";
      description "RCMD related configuration for MPLS-LDP";

      container remote-lfa {
        presence "Indicates a remote-lfa node is configured.";
        description "Monitoring configuration for Remote LFA";
        leaf threshold {
          type uint32 {
            range "1..100";
          }
          units "percentage";
          description
            "Threshold value for label coverage (in
            percentage)";
        }
      }
    }

    container collect-diagnostics {
      description "Table of CollectDiagnostics";

      list collect-diagnostic {
        key "node-name";
        description "Collect diagnostics on specified node";
        leaf enable {
          type empty;
          description
            "Enables collection of diagnostics on the
            specified location";
        }
        leaf node-name {
          type xr:Node-id;
          description "Specified location";
        }
      }
    }

    container nodes {
      description "Table of Node";

      list node {
        key "node-name";
        description
          "Configure parameters for the specified node
          (Partially qualified location allowed)";
        leaf disable {
          type empty;
          description
            "Disables the monitoring of route convergence
            on specified location";
        }
        leaf enable {
          type empty;
          description
            "Enable Configure parameters for the specified
            node (Partially qualified location allowed).
            Deletion of this object also causes deletion
            of all associated objects under Node.";
        }
        leaf node-name {
          type xr:Pq-node-id;
          description
            "Wildcard expression(eg. */*/*, R/*/*, R/S/*,
            R/S/I)";
        }
      }
    }
    leaf event-buffer-size {
      type uint32 {
        range "100..500";
      }
      description
        "Event buffer size for storing event traces (as
        number of events)";
    }
    leaf prefix-monitor-limit {
      type uint32 {
        range "0..100";
      }
      description "Limits Individual Prefix Monitoring";
    }
    leaf disable {
      type empty;
      description
        "Disable the monitoring of route convergence on
        the entire router";
    }
    leaf enable {
      type empty;
      description
        "Enable Configure Router Convergence Monitoring.
        Deletion of this object also causes deletion of
        all associated objects under RouterConvergence.";
    }
    leaf max-events-stored {
      type uint32 {
        range "10..500";
      }
      description "Maximum number of events stored in the server";
    }
    leaf monitoring-interval {
      type uint32 {
        range "5..120";
      }
      units "minute";
      description "Interval in which to collect logs (in mins)";
    }
  }
}
