module Cisco-IOS-XR-ethernet-link-oam-oper {

  /*** NAMESPACE / PREFIX DEFINITION ***/

  namespace "http://cisco.com/ns/yang"+
    "/Cisco-IOS-XR-ethernet-link-oam-oper";


  prefix "ethernet-link-oam-oper";

  /*** LINKAGE (IMPORTS / INCLUDES) ***/

  import Cisco-IOS-XR-types { prefix "xr"; }

  include Cisco-IOS-XR-ethernet-link-oam-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-link-oam package operational data.

     This module contains definitions
     for the following management objects:
       ether-link-oam: Ethernet Link OAM operational data

     Copyright (c) 2013-2017 by Cisco Systems, Inc.
     All rights reserved.";

  revision "2015-11-09" {
    description
      "IOS XR 6.0 revision.";
  }


  container ether-link-oam {
    config false;
    description "Ethernet Link OAM operational data";

    container discovery-info-interfaces {
      description
        "Table of Ethernet Link OAM enabled interfaces
        within Discovery Info container";

      list discovery-info-interface {
        key "member-interface";
        description
          "Ethernet Link OAM interface to get Discovery
          Info for";
        leaf member-interface {
          type xr:Interface-name;
          description "Member Interface";
        }
        uses ELOD-DISCOVERY-INFO;
      }
    }

    container interface-state-interfaces {
      description
        "Table of Ethernet Link OAM enabled interfaces
        within Interface State container";

      list interface-state-interface {
        key "member-interface";
        description
          "Ethernet Link OAM interface to get Interface
          State for";
        leaf member-interface {
          type xr:Interface-name;
          description "Member Interface";
        }
        uses ELOD-INTERFACE-STATE;
      }
    }

    container running-config-interfaces {
      description
        "Table of Ethernet Link OAM enabled interfaces
        within Running Config container";

      list running-config-interface {
        key "member-interface";
        description
          "Ethernet Link OAM interface to get Running
          Config for";
        leaf member-interface {
          type xr:Interface-name;
          description "Member Interface";
        }
        uses ELOD-RUNNING-CONFIG;
      }
    }

    container nodes {
      description "Node table for node-specific operational data";

      list node {
        key "node-name";
        description "Node-specific data for a particular node";

        container summary {
          description
            "Ethernet Link OAM Summary information for the
            entire node";
          uses ELOD-SUMMARY-INFO;
        }
        leaf node-name {
          type xr:Node-id;
          description "Node";
        }
      }
    }

    container event-log-entry-interfaces {
      description
        "Table of Ethernet Link OAM enabled interfaces
        within Event Log Entry container";

      list event-log-entry-interface {
        key "member-interface";
        description
          "Ethernet Link OAM enabled interface to get
          Event Log Entry for";

        container event-log-entry-indexes {
          description
            "Table of Ethernet Link OAM Event Log entries
            on the interface";

          list event-log-entry-index {
            key "event-log-entry-index";
            description
              "Ethernet Link OAM Event Log Entry Index to
              get data for";
            leaf event-log-entry-index {
              type xr:Cisco-ios-xr-string;
              description "Event Log Entry index";
            }
            uses ELOD-LOG-ENTRY;
          }
        }
        leaf member-interface {
          type xr:Interface-name;
          description "Member Interface";
        }
      }
    }

    container stats-interfaces {
      description
        "Table of Ethernet Link OAM enabled interfaces
        within Stats container";

      list stats-interface {
        key "member-interface";
        description "Ethernet Link OAM interface to get Stats for";
        leaf member-interface {
          type xr:Interface-name;
          description "Member Interface";
        }
        uses ELOD-STATS;
      }
    }
  }
}
