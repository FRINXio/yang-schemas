submodule Cisco-IOS-XR-mpls-io-oper-sub1 {

  belongs-to Cisco-IOS-XR-mpls-io-oper {
    prefix Cisco-IOS-XR-mpls-io-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-io package operational data.

     Copyright (c) 2013-2017 by Cisco Systems, Inc.
     All rights reserved.";

  revision "2017-05-18" {
    description
      "IOS XR 6.2.2 revision.";
  }

  revision "2015-11-09" {
    description
      "IOS XR 6.0 revision.";
  }


  grouping MPLS-IO-SHOW-INTF-INFO {
    description "MPLS EA information for a particular Interface";
    leaf mtu {
      type uint32;
      description "MTU for fragmentation";
    }
    leaf bkp-label-stack-depth {
      type uint8;
      description "Bkp Label Stack Depth";
    }
    leaf srte-label-stack-depth {
      type uint8;
      description "Srte Label Stack Depth";
    }
    leaf pri-label-stack-depth {
      type uint8;
      description "Pri Label Stack Depth";
    }
  }
}
