submodule Cisco-IOS-XR-asr9k-sc-invmgr-admin-oper-sub1 {

  belongs-to Cisco-IOS-XR-asr9k-sc-invmgr-admin-oper {
    prefix Cisco-IOS-XR-asr9k-sc-invmgr-admin-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-sc-invmgr-admin package operational data.

     Copyright (c) 2013-2017 by Cisco Systems, Inc.
     All rights reserved.";

  revision "2018-06-28" {
    description
      "FRU bag elements data type change to enum from value";
  }

  revision "2017-01-04" {
    description
      "IOS-XR 6.2.1 revision.";
  }

  revision "2015-11-09" {
    description
      "IOS XR 6.0 revision.";
  }

  typedef Inv-reset-reason {
    type enumeration {
      enum module-reset-reason-unknown {
        value 0;
        description "module reset reason unknown";
      }
      enum module-reset-reason-powerup {
        value 1;
        description "module reset reason powerup";
      }
      enum module-reset-reason-user-shutdown {
        value 2;
        description "module reset reason user shutdown";
      }
      enum module-reset-reason-user-reload {
        value 3;
        description "module reset reason user reload";
      }
      enum module-reset-reason-auto-reload {
        value 4;
        description "module reset reason auto reload";
      }
      enum module-reset-reason-environment {
        value 5;
        description "module reset reason environment";
      }
      enum module-reset-reason-user-unpower {
        value 6;
        description "module reset reason user unpower";
      }
    }
    description "Inv reset reason";
  }
  typedef Inv-monitor-state {
    type enumeration {
      enum unmonitored {
        value 0;
        description "unmonitored";
      }
      enum monitored {
        value 1;
        description "monitored";
      }
    }
    description "Inv monitor state";
  }
  typedef Inv-card-state {
    type enumeration {
      enum inv-card-not-present {
        value 0;
        description "inv card not present";
      }
      enum inv-card-present {
        value 1;
        description "inv card present";
      }
      enum inv-card-reset {
        value 2;
        description "inv card reset";
      }
      enum inv-card-booting {
        value 3;
        description "inv card booting";
      }
      enum inv-card-mbi-booting {
        value 4;
        description "inv card mbi booting";
      }
      enum inv-card-running-mbi {
        value 5;
        description "inv card running mbi";
      }
      enum inv-card-running-ena {
        value 6;
        description "inv card running ena";
      }
      enum inv-card-bring-down {
        value 7;
        description "inv card bring down";
      }
      enum inv-card-ena-failure {
        value 8;
        description "inv card ena failure";
      }
      enum inv-card-f-diag-run {
        value 9;
        description "inv card f diag run";
      }
      enum inv-card-f-diag-failure {
        value 10;
        description "inv card f diag failure";
      }
      enum inv-card-powered {
        value 11;
        description "inv card powered";
      }
      enum inv-card-unpowered {
        value 12;
        description "inv card unpowered";
      }
      enum inv-card-mdr {
        value 13;
        description "inv card mdr";
      }
      enum inv-card-mdr-running-mbi {
        value 14;
        description "inv card mdr running mbi";
      }
      enum inv-card-main-t-mode {
        value 15;
        description "inv card main t mode";
      }
      enum inv-card-admin-down {
        value 16;
        description "inv card admin down";
      }
      enum inv-card-no-mon {
        value 17;
        description "inv card no mon";
      }
      enum inv-card-unknown {
        value 18;
        description "inv card unknown";
      }
      enum inv-card-failed {
        value 19;
        description "inv card failed";
      }
      enum inv-card-ok {
        value 20;
        description "inv card ok";
      }
      enum inv-card-missing {
        value 21;
        description "inv card missing";
      }
      enum inv-card-field-diag-downloading {
        value 22;
        description "inv card field diag downloading";
      }
      enum inv-card-field-diag-unmonitor {
        value 23;
        description "inv card field diag unmonitor";
      }
      enum inv-card-fabric-field-diag-unmonitor {
        value 24;
        description "inv card fabric field diag unmonitor";
      }
      enum inv-card-field-diag-rp-launching {
        value 25;
        description "inv card field diag rp launching";
      }
      enum inv-card-field-diag-running {
        value 26;
        description "inv card field diag running";
      }
      enum inv-card-field-diag-pass {
        value 27;
        description "inv card field diag pass";
      }
      enum inv-card-field-diag-fail {
        value 28;
        description "inv card field diag fail";
      }
      enum inv-card-field-diag-timeout {
        value 29;
        description "inv card field diag timeout";
      }
      enum inv-card-disabled {
        value 30;
        description "inv card disabled";
      }
      enum inv-card-spa-booting {
        value 31;
        description "inv card spa booting";
      }
      enum inv-card-not-allowed-online {
        value 32;
        description "inv card not allowed online";
      }
      enum inv-card-stopped {
        value 33;
        description "inv card stopped";
      }
      enum inv-card-incompatible-fw-ver {
        value 34;
        description "inv card incompatible fw ver";
      }
      enum inv-card-fpd-hold {
        value 35;
        description "inv card fpd hold";
      }
      enum inv-card-node-prep {
        value 36;
        description "inv card node prep";
      }
      enum inv-card-updating-fpd {
        value 37;
        description "inv card updating fpd";
      }
      enum inv-card-num-states {
        value 38;
        description "inv card num states";
      }
    }
    description "Inv card state";
  }
  typedef Inv-power-admin-state {
    type enumeration {
      enum admin-power-invalid {
        value 0;
        description "admin power invalid";
      }
      enum admin-on {
        value 2;
        description "admin on";
      }
      enum admin-off {
        value 3;
        description "admin off";
      }
    }
    description "Inv power admin state";
  }
  typedef Inv-admin-state {
    type enumeration {
      enum admin-state-invalid {
        value 0;
        description "admin state invalid";
      }
      enum admin-up {
        value 1;
        description "admin up";
      }
      enum admin-down {
        value 2;
        description "admin down";
      }
    }
    description "Inv admin state";
  }

  grouping INV-PWG-INFO {
    description "Power supply group bag";
    leaf power-group-redundancy-mode {
      type int32;
      description "redundancy mode";
    }
    leaf power-group-power-units {
      type string;
      description "power units";
    }
    leaf power-group-available-current {
      type int32;
      description "available current";
    }
    leaf power-group-drawn-current {
      type int32;
      description "drawn current";
    }
  }

  grouping INV-TIMESPEC {
    description "Inventory FRU Info Time Spec";
    leaf time-in-seconds {
      type int32;
      units "second";
      description "Time Value in Seconds";
    }
    leaf time-in-nano-seconds {
      type int32;
      units "nanosecond";
      description "Time Value in Nano-seconds";
    }
  }

  grouping INV-XML-FRU-INFO {
    description "FRU Information";

    container last-operational-state-change {
      description "Time operational state is   last changed";
      uses INV-TIMESPEC;
    }

    container module-up-time {
      description "Module up time";
      uses INV-TIMESPEC;
    }
    leaf module-administrative-state {
      type Inv-admin-state;
      description "Administrative    state";
    }
    leaf module-power-administrative-state {
      type Inv-power-admin-state;
      description "Power administrative state";
    }
    leaf module-operational-state {
      type Inv-card-state;
      description "Operation state";
    }
    leaf module-monitor-state {
      type Inv-monitor-state;
      description "Monitor state";
    }
    leaf module-reset-reason {
      type Inv-reset-reason;
      description "Reset reason";
    }
  }

  grouping INV-PHY-ENTITY-BASIC-INFO {
    description
      "Bag contains all the basic inventory information
      for each entity";
    leaf description {
      type string {
        length "0..255";
      }
      description
        "describes in user-readable terms       what the
        entity in question does";
    }
    leaf vendor-type {
      type string {
        length "0..255";
      }
      description "maps to the vendor OID string";
    }
    leaf name {
      type string {
        length "0..255";
      }
      description "name string for the entity";
    }
    leaf hardware-revision {
      type string {
        length "0..255";
      }
      description "hw revision string";
    }
    leaf firmware-revision {
      type string {
        length "0..255";
      }
      description "firmware revision string";
    }
    leaf software-revision {
      type string {
        length "0..255";
      }
      description "software revision string";
    }
    leaf chip-hardware-revision {
      type string {
        length "0..255";
      }
      description "chip module hw revision string";
    }
    leaf serial-number {
      type string {
        length "0..255";
      }
      description "serial number";
    }
    leaf manufacturer-name {
      type string {
        length "0..255";
      }
      description "manufacturer's name";
    }
    leaf model-name {
      type string {
        length "0..255";
      }
      description "model name";
    }
    leaf asset-id-str {
      type string {
        length "0..255";
      }
      description "asset Identification string";
    }
    leaf asset-identification {
      type int32;
      description "asset Identification";
    }
    leaf is-field-replaceable-unit {
      type boolean;
      description "1 if Field Replaceable Unit 0, if not";
    }
    leaf manufacturer-asset-tags {
      type int32;
      description "Manufacture Asset Tags";
    }
    leaf composite-class-code {
      type int32;
      description "Major&minor class of the entity";
    }
    leaf memory-size {
      type int32;
      description
        "Size of memory associated with       the entity
        where applicable";
    }
    leaf environmental-monitor-path {
      type string {
        length "0..255";
      }
      description "sysdb name of sensor in the envmon EDM";
    }
    leaf alias {
      type string {
        length "0..255";
      }
      description "useful for storing an entity alias ";
    }
    leaf group-flag {
      type boolean;
      description "indicates if this entity is group       or not";
    }
    leaf new-deviation-number {
      type int32;
      description "integer value for New Deviation Number 0x88";
    }
    leaf physical-layer-interface-module-type {
      type int32;
      description
        "integer value for plim type if     applicable to
        this entity";
    }
    leaf unrecognized-fru {
      type boolean;
      description "1 if UnrecognizedFRU and 0 for recognizedFRU";
    }
    leaf redundancystate {
      type int32;
      description
        "integer value for Redundancy State if    
        applicable to this entity";
    }
    leaf ceport {
      type boolean;
      description "1 if ce port found, 0 if not";
    }
    leaf xr-scoped {
      type boolean;
      description "1 if xr scoped, 0 if not";
    }
    leaf unique-id {
      type int32;
      description "Unique id for an entity";
    }
  }
}
