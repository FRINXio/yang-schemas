module Cisco-IOS-XR-infra-xtc-oper {

  /*** NAMESPACE / PREFIX DEFINITION ***/

  namespace "http://cisco.com/ns/yang/Cisco-IOS-XR-infra-xtc-oper";


  prefix "infra-xtc-oper";

  /*** LINKAGE (IMPORTS / INCLUDES) ***/

  import ietf-inet-types { prefix "inet"; }

  import Cisco-IOS-XR-types { prefix "xr"; }

  include Cisco-IOS-XR-infra-xtc-oper-sub1 {
    revision-date 2017-08-24;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-xtc package operational data.

     This module contains definitions
     for the following management objects:
       pce-lsp-data: PCE LSP's data
       pce-peer: pce peer
       pce-topology: pce topology
       pce: pce

     Copyright (c) 2013-2017 by Cisco Systems, Inc.
     All rights reserved.";

  revision "2017-08-24" {
    description
      "Added C flag to pcep flags.";
  }

  revision "2017-06-26" {
    description
      "Change identifiers to be more readable.";
  }

  revision "2017-05-01" {
    description
      "Fixing backward compatibility error in module.";
  }

  revision "2016-05-31" {
    description
      "Revision description string.";
  }

  revision "2015-11-09" {
    description
      "IOS XR 6.0 revision.";
  }

  typedef Pce-asso {
    type enumeration {
      enum unknown {
        value 0;
        description "Unknown type";
      }
      enum link {
        value 1;
        description "LINK";
      }
      enum node {
        value 2;
        description "NODE";
      }
      enum srlg {
        value 3;
        description "SRLG";
      }
    }
    description "Pce asso";
  }

  grouping PEER-TABLE {
    description "Common node of pce, pce-peer";

    container peer-infos {
      description "Peers database in XTC";

      list peer-info {
        key "peer-address";
        description "PCE peer information";
        leaf peer-address {
          type inet:ip-address-no-zone;
          description "Peer Address";
        }
        uses PCE-PEER-BAG;
      }
    }
  }

  grouping PEER-DETAIL-TABLE {
    description "Common node of pce, pce-peer";

    container peer-detail-infos {
      description "Detailed peers database in XTC";

      list peer-detail-info {
        key "peer-address";
        description "Detailed PCE peer information";
        leaf peer-address {
          type inet:ip-address-no-zone;
          description "Peer Address";
        }
        uses PCE-PEER-DETAIL-BAG;
      }
    }
  }

  grouping PREFIX-TABLE {
    description "Common node of pce, pce-topology";

    container prefix-infos {
      description "Prefixes database in XTC";

      list prefix-info {
        key "node-identifier";
        description "PCE prefix information";
        leaf node-identifier {
          type int32;
          description "Node ID";
        }
        uses PCE-PFX-BAG;
      }
    }
  }

  grouping TUNNEL-TABLE {
    description "Common node of pce, pce-lsp-data";

    container tunnel-infos {
      description "Tunnel database in XTC";

      list tunnel-info {
        key "peer-address plsp-id tunnel-name";
        description "Tunnel information";
        leaf peer-address {
          type inet:ip-address-no-zone;
          description "Peer Address";
        }
        leaf plsp-id {
          type int32;
          description "PCEP LSP ID";
        }
        leaf tunnel-name {
          type xr:Cisco-ios-xr-string;
          description "Tunnel name";
        }
        uses PCE-TUN-BAG;
      }
    }
  }

  grouping TOPOLOGY-SUMMARY {
    description "Common node of pce, pce-topology";

    container topology-summary {
      description "Node summary database in XTC";
      uses PCE-NODE-SUMMARY-BAG;
    }
  }

  grouping LSP-SUMMARY {
    description "Common node of pce, pce-lsp-data";

    container lsp-summary {
      description "LSP summary database in XTC";
      uses PCE-LSP-SUMMARY-BAG;
    }
  }

  grouping TOPOLOGY-NODE-TABLE {
    description "Common node of pce, pce-topology";

    container topology-nodes {
      description "Node database in XTC";

      list topology-node {
        key "node-identifier";
        description "Node information";
        leaf node-identifier {
          type int32;
          description "Node Identifier";
        }
        uses PCE-XTC-NODE-BAG;
      }
    }
  }

  grouping TUNNEL-DETAIL-TABLE {
    description "Common node of pce, pce-lsp-data";

    container tunnel-detail-infos {
      description "Detailed tunnel database in XTC";

      list tunnel-detail-info {
        key "peer-address plsp-id tunnel-name";
        description "Detailed tunnel information";
        leaf peer-address {
          type inet:ip-address-no-zone;
          description "Peer Address";
        }
        leaf plsp-id {
          type int32;
          description "PCEP LSP ID";
        }
        leaf tunnel-name {
          type xr:Cisco-ios-xr-string;
          description "Tunnel name";
        }
        uses PCE-TUN-DETAIL-BAG;
      }
    }
  }

  container pce-lsp-data {
    config false;
    description "PCE LSP's data";
    uses TUNNEL-TABLE;
    uses LSP-SUMMARY;
    uses TUNNEL-DETAIL-TABLE;
  }

  container pce-peer {
    config false;
    description "pce peer";
    uses PEER-DETAIL-TABLE;
    uses PEER-TABLE;
  }

  container pce-topology {
    config false;
    description "pce topology";
    uses TOPOLOGY-SUMMARY;
    uses TOPOLOGY-NODE-TABLE;
    uses PREFIX-TABLE;
  }

  container pce {
    config false;
    description "pce";

    container association-infos {
      description "Associaition database in XTC";

      list association-info {
        key "group-id";
        description "PCE Association information";
        leaf group-id {
          type int32;
          description "Group ID";
        }
        leaf type {
          type Pce-asso;
          description "Type";
        }
        leaf sub-id {
          type int32;
          description "Sub ID";
        }
        uses PCE-ASSO-BAG;
      }
    }

    container cspf {
      description "CSPF path info";

      container cspf-paths {
        description
          "This table models the path calculation
          capabilities in XTC.A GET operation for the
          complete table will return no entries.";

        list cspf-path {
          key "af source1 destination1 metric-type source2"+
            " destination2 disjoint-level disjoint-strict"+
            " shortest-path";
          description
            "A GET operation on this class returns the path
            .";
          leaf af {
            type int32;
            description "Address Family";
          }
          leaf source1 {
            type inet:ip-address-no-zone;
            description "Source of path 1";
          }
          leaf destination1 {
            type inet:ip-address-no-zone;
            description "Destination of path 1";
          }
          leaf metric-type {
            type int32;
            description "Metric type";
          }
          leaf source2 {
            type inet:ip-address-no-zone;
            description "Source of path 2";
          }
          leaf destination2 {
            type inet:ip-address-no-zone;
            description "Destination of path 2";
          }
          leaf disjoint-level {
            type int32;
            description "Disjointness level";
          }
          leaf disjoint-strict {
            type int32;
            description "Strict disjointness required";
          }
          leaf shortest-path {
            type int32;
            description "Whether path 1 or 2 should be shortest";
          }
          uses PCE-PATH-LIST-BAG;
        }
      }
    }
    uses TOPOLOGY-SUMMARY;
    uses TUNNEL-TABLE;
    uses PEER-DETAIL-TABLE;
    uses TOPOLOGY-NODE-TABLE;
    uses PREFIX-TABLE;
    uses LSP-SUMMARY;
    uses PEER-TABLE;
    uses TUNNEL-DETAIL-TABLE;
  }
}
