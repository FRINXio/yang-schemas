module Cisco-IOS-XR-ipv6-io-cfg {

  /*** NAMESPACE / PREFIX DEFINITION ***/

  namespace "http://cisco.com/ns/yang/Cisco-IOS-XR-ipv6-io-cfg";


  prefix "ipv6-io-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-io package configuration.

     This module contains definitions
     for the following management objects:
       ipv6-configuration: IPv6 Configuration Data

     Copyright (c) 2013-2017 by Cisco Systems, Inc.
     All rights reserved.";

  revision "2016-05-10" {
    description
      "Added top container.";
  }

  revision "2015-11-09" {
    description
      "IOS XR 6.0 revision.";
  }


  container ipv6-configuration {
    description "IPv6 Configuration Data";

    container ipv6-assembler {
      description "IPv6 fragmented packet assembler";
      leaf timeout {
        type uint32 {
          range "1..120";
        }
        units "second";
        description
          "Number of seconds an assembly queue will hold
          before timeout";
      }
      leaf max-packets {
        type uint32 {
          range "1..50";
        }
        units "percentage";
        description
          "Maxinum packets allowed in assembly queues (in
          percent)";
      }
    }

    container ipv6icmp {
      presence "Indicates a ipv6icmp node is configured.";
      description "Configure IPv6 ICMP parameters";
      leaf error-interval {
        type uint32 {
          range "0..2147483647";
        }
        units "millisecond";
        mandatory true;
        description "Interval between tokens in milliseconds";
      }
      leaf bucket-size {
        type uint32 {
          range "1..200";
        }
        default "10";
        description "Bucket size";
      }
    }
    leaf ipv6-pmtu-time-out {
      type uint32 {
        range "1..15";
      }
      units "minute";
      description
        "Configure IPv6 Path MTU timeout value in minutes";
    }
    leaf ipv6-source-route {
      type boolean;
      default "true";
      description "TRUE if enabled, FALSE if disabled";
    }
    leaf ipv6-pmtu-enable {
      type boolean;
      default "false";
      description "TRUE if enabled, FALSE if disabled";
    }
    leaf ipv6-hop-limit {
      type uint32 {
        range "1..255";
      }
      description "Configure IPv6 hop count limit";
    }
  }
}
