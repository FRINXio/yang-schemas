module Cisco-IOS-XR-asr9k-fab-cfg {

  /*** NAMESPACE / PREFIX DEFINITION ***/

  namespace "http://cisco.com/ns/yang/Cisco-IOS-XR-asr9k-fab-cfg";


  prefix "asr9k-fab-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-fab package configuration.

     This module contains definitions
     for the following management objects:
       fab-vqi-config: Configure Fabric Operation Mode

     Copyright (c) 2013-2017 by Cisco Systems, Inc.
     All rights reserved.";

  revision "2015-11-09" {
    description
      "IOS XR 6.0 revision.";
  }

  typedef Asr9k-fab-mode {
    type enumeration {
      enum highbandwidth {
        value 1;
        description "High bandwidth mode";
      }
      enum a99-highbandwidth {
        value 2;
        description "A99 High bandwidth mode";
      }
    }
    description "Asr9k fab mode";
  }

  container fab-vqi-config {
    description "Configure Fabric Operation Mode";

    container mode {
      description "Mode Type";
      leaf fab-mode-type-xr {
        type Asr9k-fab-mode;
        description "Mode Type";
      }
      leaf fab-mode-type {
        type Asr9k-fab-mode;
        description "Mode Type";
      }
    }
  }
}
