module Cisco-IOS-XR-mpls-te-datatypes {

  /*** NAMESPACE / PREFIX DEFINITION ***/

  namespace "http://cisco.com/ns"+
    "/yang/Cisco-IOS-XR-mpls-te-datatypes";


  prefix "mpls-te-datatypes";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2017 by Cisco Systems, Inc.
     All rights reserved.";

  revision "2017-05-01" {
    description
      "Fixing backward compatibility error in module.";
  }

  revision "2015-11-09" {
    description
      "IOS XR 6.0 revision.";
  }

  typedef Mpls-tesrlg-exclude {
    type enumeration {
      enum mandatory {
        value 1;
        description "SRLG Mandatory Exclude";
      }
      enum preferred {
        value 2;
        description "SRLG Preferred Exclude";
      }
      enum weighted {
        value 3;
        description "SRLG Weighted Exclude";
      }
    }
    description "Mpls tesrlg exclude";
  }
  typedef Mpls-te-affinity-value {
    type enumeration {
      enum hex-value {
        value 1;
        description "Affinity value in Hex number";
      }
      enum bit-position {
        value 2;
        description "Affinity value by Bit-Position";
      }
    }
    description "Mpls te affinity value";
  }
  typedef Destination-list-name-length {
    type xr:Cisco-ios-xr-string {
      length "1..32";
    }
    description "Destination list name length";
  }
  typedef Mpls-percent-range {
    type uint32 {
      range "0..100";
    }
    description "Mpls percent range";
  }
  typedef Sr-prepend {
    type enumeration {
      enum none-type {
        value 0;
        description "NoneType";
      }
      enum next-label {
        value 1;
        description "Next Label";
      }
      enum bgp-n-hop {
        value 2;
        description "BGP NHOP";
      }
    }
    description "Sr prepend";
  }
  typedef Mpls-te-path-selection-tiebreaker {
    type enumeration {
      enum min-fill {
        value 1;
        description "Prefer the path with the least-utilized links";
      }
      enum max-fill {
        value 2;
        description "Prefer the path with the most-utilized links";
      }
      enum random {
        value 3;
        description "Prefer a path with links utilized randomly";
      }
    }
    description "Mpls te path selection tiebreaker";
  }
  typedef Attribute-set-name-length {
    type xr:Cisco-ios-xr-string {
      length "1..64";
    }
    description "Attribute set name length";
  }
  typedef Mpls-te-otn-aps-protection {
    type enumeration {
      enum 1plus1-unidir-no-aps {
        value 4;
        description "1PLUS1 UNIDIR NO APS";
      }
      enum 1plus1-unidir-aps {
        value 8;
        description "1PLUS1 UNIDIR APS";
      }
      enum 1plus1-bdir-aps {
        value 16;
        description "1PLUS1 BIDIR APS";
      }
    }
    description "Mpls te otn aps protection";
  }
  typedef Mpls-te-path-option-property {
    type enumeration {
      enum none {
        value 0;
        description "No property";
      }
      enum lockdown {
        value 1;
        description "Path is not a canditate forreoptimization";
      }
      enum verbatim {
        value 4;
        description
          "Explicit path does not require topology
          database";
      }
      enum pce {
        value 8;
        description "Dynamic path found by PCE server";
      }
      enum segment-routing {
        value 16;
        description "Segment Routing path";
      }
    }
    description "Mpls te path option property";
  }
  typedef Mpls-te-path-option-xro {
    type empty;
    description "Defined as attribute-set";
  }
  typedef Mpls-te-tunnel-affinity {
    type enumeration {
      enum include {
        value 1;
        description "Include Affinity";
      }
      enum include-strict {
        value 2;
        description "Strictly Include Affinity";
      }
      enum exclude {
        value 3;
        description "Exclude Affinity";
      }
      enum exclude-all {
        value 4;
        description "Exclude All Affinities";
      }
      enum ignore {
        value 5;
        description "Ignore Affinity";
      }
    }
    description "Mpls te tunnel affinity";
  }
  typedef Mpls-te-switching-cap {
    type enumeration {
      enum psc1 {
        value 1;
        description "PSC1";
      }
      enum lsc {
        value 150;
        description "LSC";
      }
      enum fsc {
        value 200;
        description "FSC";
      }
    }
    description "Mpls te switching cap";
  }
  typedef Mpls-te-otn-aps-protection-mode {
    type enumeration {
      enum revertive {
        value 1;
        description "Revertive";
      }
      enum non-revertive {
        value 2;
        description "Non Revertive";
      }
    }
    description "Mpls te otn aps protection mode";
  }
  typedef Mpls-te-bfd-session-down-action {
    type enumeration {
      enum re-setup {
        value 1;
        description "Tear down and resetup";
      }
    }
    description "Mpls te bfd session down action";
  }
  typedef Mpls-te-log-frr-protection {
    type enumeration {
      enum frr-active-primary {
        value 1;
        description "Track only FRR active on primary LSP";
      }
      enum backup {
        value 256;
        description "backup tunnel";
      }
      enum frr-ready-primary {
        value 512;
        description "Track only FRR ready on primary LSP";
      }
      enum primary {
        value 513;
        description "primary LSP";
      }
      enum all {
        value 769;
        description "all";
      }
    }
    description "Mpls te log frr protection";
  }
  typedef Mpls-te-autoroute-metric {
    type enumeration {
      enum relative {
        value 1;
        description "Relative";
      }
      enum absolute {
        value 2;
        description "Absolute";
      }
      enum constant {
        value 3;
        description "Constant";
      }
    }
    description "Mpls te autoroute metric";
  }
  typedef Mpls-te-backup-bandwidth-pool {
    type enumeration {
      enum any-pool {
        value 1;
        description "Any Pool";
      }
      enum global-pool {
        value 2;
        description "Global Pool";
      }
      enum sub-pool {
        value 4;
        description "Sub Pool";
      }
    }
    description "Mpls te backup bandwidth pool";
  }
  typedef Mpls-te-otn-snc-mode {
    type enumeration {
      enum snc-n {
        value 1;
        description "SNC N";
      }
      enum snc-i {
        value 2;
        description "SNC I";
      }
      enum snc-s {
        value 3;
        description "SNC S";
      }
    }
    description "Mpls te otn snc mode";
  }
  typedef Bfd-reverse-path {
    type enumeration {
      enum bfd-reverse-path-binding-label {
        value 1;
        description "BindingLabel";
      }
    }
    description "Bfd reverse path";
  }
  typedef Mpls-te-path-selection-metric {
    type enumeration {
      enum igp {
        value 1;
        description "IGP Metric";
      }
      enum te {
        value 2;
        description "TE Metric";
      }
      enum delay {
        value 4;
        description "DELAY Metric";
      }
    }
    description "Mpls te path selection metric";
  }
  typedef Mpls-te-path-option {
    type enumeration {
      enum not-set {
        value 0;
        description "Not Set";
      }
      enum dynamic {
        value 1;
        description "Dynamic";
      }
      enum explicit-name {
        value 3;
        description "Explicit, identified by name";
      }
      enum explicit-number {
        value 4;
        description "Explicit, identified by number";
      }
      enum no-ero {
        value 5;
        description "No ERO";
      }
      enum sr {
        value 6;
        description "Segment routing";
      }
    }
    description "Mpls te path option";
  }
  typedef Mpls-te-bandwidth-pool {
    type enumeration {
      enum any-pool {
        value 0;
        description "Any Pool";
      }
      enum sub-pool {
        value 1;
        description "Sub Pool";
      }
    }
    description "Mpls te bandwidth pool";
  }
  typedef Mpls-te-bandwidth-dste {
    type enumeration {
      enum standard-dste {
        value 0;
        description "IETF-Standard DSTE";
      }
      enum pre-standard-dste {
        value 1;
        description "Pre-Standard DSTE";
      }
    }
    description "Mpls te bandwidth dste";
  }
  typedef Mpls-te-path-selection-invalidation-timer-expire {
    type enumeration {
      enum tunnel-action-tear {
        value 1;
        description "Tear down tunnel.";
      }
      enum tunnel-action-drop {
        value 2;
        description "Drop tunnel traffic.";
      }
    }
    description "Mpls te path selection invalidation timer expire";
  }
  typedef Ctype {
    type enumeration {
      enum ctype-null {
        value 0;
        description "CTYPE NULL";
      }
      enum ctype-ipv4 {
        value 1;
        description "CTYPE IPV4";
      }
      enum ctype-ipv4-p2p-tunnel {
        value 7;
        description "CTYPE IPV4 P2P TUNNEL";
      }
      enum ctype-ipv6-p2p-tunnel {
        value 8;
        description "CTYPE IPV6 P2P TUNNEL";
      }
      enum ctype-ipv4-uni {
        value 9;
        description "CTYPE IPV4 UNI";
      }
      enum ctype-ipv4-p2mp-tunnel {
        value 13;
        description "CTYPE IPV4 P2MP TUNNEL";
      }
      enum ctype-ipv6-p2mp-tunnel {
        value 14;
        description "CTYPE IPV6 P2MP TUNNEL";
      }
    }
    description "Ctype";
  }
  typedef Mpls-te-path-diversity-conformance {
    type enumeration {
      enum strict {
        value 0;
        description "Strict";
      }
      enum best-effort {
        value 1;
        description "Best effort";
      }
    }
    description "Mpls te path diversity conformance";
  }
  typedef Mpls-te-backup-bandwidth-class {
    type enumeration {
      enum class0 {
        value 0;
        description "Class 0";
      }
      enum class1 {
        value 1;
        description "Class 1";
      }
      enum any-class {
        value 9;
        description "Any Class";
      }
    }
    description "Mpls te backup bandwidth class";
  }
  typedef Mpls-te-attr-set {
    type enumeration {
      enum not-used {
        value 0;
        description "Not used";
      }
      enum static {
        value 1;
        description "Static";
      }
      enum lsp {
        value 2;
        description "LSP";
      }
      enum unassigned {
        value 3;
        description "Unassigned";
      }
      enum auto-backup {
        value 4;
        description "Auto backup";
      }
      enum auto-mesh {
        value 5;
        description "Auto mesh";
      }
      enum xro {
        value 6;
        description "XRO";
      }
      enum p2mp-te {
        value 7;
        description "P2MP TE";
      }
      enum otn-pp {
        value 8;
        description "OTN Path Protection";
      }
      enum p2p-te {
        value 9;
        description "P2P TE";
      }
    }
    description "Mpls te attr set";
  }
  typedef Mpls-te-otn-aps-restoration-style {
    type enumeration {
      enum keep-failed-lsp {
        value 1;
        description "Keep Failed Lsp";
      }
      enum delete-failed-lsp {
        value 2;
        description "Delete Failed Lsp";
      }
    }
    description "Mpls te otn aps restoration style";
  }
  typedef Mpls-te-path-selection-segment-routing-adjacency-protection {
    type enumeration {
      enum not-set {
        value 0;
        description "Any segment can be used in a path.";
      }
      enum adj-unprotected {
        value 1;
        description
          "Only unprotected adjacency segments can be used
          in a path.";
      }
      enum adj-protected {
        value 2;
        description
          "Only protected adjacency segments can be used
          in a path.";
      }
    }
    description
      "Mpls te path selection segment routing adjacency
      protection";
  }
  typedef Mpls-te-path-option-protection {
    type enumeration {
      enum active {
        value 0;
        description "Active path";
      }
      enum protecting {
        value 1;
        description "Protecting Path";
      }
    }
    description "Mpls te path option protection";
  }
  typedef Mpls-te-sig-name-option {
    type enumeration {
      enum none {
        value 0;
        description "None";
      }
      enum address {
        value 1;
        description "Address";
      }
      enum name {
        value 2;
        description "Name";
      }
    }
    description "Mpls te sig name option";
  }
  typedef Mpls-te-bandwidth-limit {
    type enumeration {
      enum unlimited {
        value 64;
        description "Unlimited";
      }
      enum limited {
        value 128;
        description "Limited";
      }
    }
    description "Mpls te bandwidth limit";
  }
  typedef Mesh-group-id {
    type uint32 {
      range "0..4294967295";
    }
    description "Mesh group id";
  }
  typedef Path-invalidation-action {
    type enumeration {
      enum tear {
        value 1;
        description "Tear";
      }
      enum drop {
        value 2;
        description "Drop";
      }
    }
    description "Path invalidation action";
  }
  typedef Mpls-te-igp-protocol {
    type enumeration {
      enum none {
        value 0;
        description "Not set";
      }
      enum isis {
        value 1;
        description "IS IS";
      }
      enum ospf {
        value 2;
        description "OSPF";
      }
    }
    description "Mpls te igp protocol";
  }
}
