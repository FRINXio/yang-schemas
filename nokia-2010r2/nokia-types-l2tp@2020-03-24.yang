module nokia-types-l2tp {

    yang-version "1.1";

    namespace "urn:nokia.com:sros:ns:yang:sr:types-l2tp";

    prefix "types-l2tp";

    import nokia-sros-yang-extensions     { prefix "sros-ext"; }
    import nokia-types-sros               { prefix "types-sros"; }


    sros-ext:sros-major-release "rel20";

    organization "Nokia";

    contact
        "Nokia SR OS Support
         Web: <http://www.nokia.com>";

    description
        "Common L2TP data types used in the SR OS management system.

         Copyright 2016 Nokia. All rights reserved. Reproduction of this document
         is authorized on the condition that the foregoing copyright notice is included.

         This nokia-types-l2tp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-24";

    typedef base-tunnel-session-limit {
        type int32 {
            range "1..65534";
        }
        description "The number of sessions allowed.";
    }

    typedef child-tunnel-session-limit {
        type union {
            type int32 {
                range "1..65534";
            }
            type enumeration {
                enum "unlimited"                    { value -1; }
            }
        }
        description "The number of sessions allowed.";
    }

    typedef base-session-limit {
        type int32 {
            range "1..250000";
        }
        description "The number of sessions allowed.";
    }

    typedef child-session-limit {
        type union {
            type int32 {
                range "1..250000";
            }
            type enumeration {
                enum "unlimited"                    { value -1; }
            }
        }
        description "The number of sessions allowed.";
    }

    typedef base-receive-window-size {
        type uint32 {
            range "4..1024";
        }
        default "64";
        description "The receive window size.";
    }

    typedef child-receive-window-size {
        type uint32 {
            range "4..1024";
        }
        description "The receive window size.";
    }

    typedef peer-address-change-policy-option {
        type enumeration {
            enum "accept"                       { value 1; }
            enum "ignore"                       { value 2; }
            enum "reject"                       { value 3; }
        }
        default "reject";
        description
            "Specifies what to do in case the system receives a L2TP response
             from another address than the one the request was sent to.";
    }

    typedef base-hello-interval {
        type union {
            type types-sros:time-duration {
                range "10..3600";
            }
            type enumeration {
                enum "infinite"                     { value -1; }
            }
        }
        units "seconds";
        default "300";
        description "The time interval between two consecutive tunnel Hello messages.";
    }

    typedef child-hello-interval {
        type union {
            type types-sros:time-duration {
                range "10..3600";
            }
            type enumeration {
                enum "infinite"                     { value -1; }
            }
        }
        units "seconds";
        description "The time interval between two consecutive tunnel Hello messages.";
    }

    typedef base-idle-timeout {
        type union {
            type types-sros:time-duration {
                range "0..3600";
            }
            type enumeration {
                enum "infinite"                     { value -1; }
            }
        }
        units "seconds";
        default "infinite";
        description
            "The period of time that an established tunnel with no active sessions persists
             before being disconnected.";
    }

    typedef child-idle-timeout {
        type union {
            type types-sros:time-duration {
                range "0..3600";
            }
            type enumeration {
                enum "infinite"                     { value -1; }
            }
        }
        units "seconds";
        description
            "The period of time that an established tunnel with no active sessions persists
             before being disconnected.";
    }

    typedef base-destruct-timeout {
        type types-sros:time-duration {
            range "60..86400";
        }
        units "seconds";
        default "60";
        description
            "The period of time that the data of a disconnected tunnel persists before
             being removed.

             If the system needs the resources taken by the disconnected tunnel data,
             it may remove the data earlierThe period of time that an established tunnel
             with no active sessions persists before being disconnected.";
    }

    typedef child-destruct-timeout {
        type types-sros:time-duration {
            range "60..86400";
        }
        units "seconds";
        description
            "The period of time that the data of a disconnected tunnel persists before
             being removed.

             If the system needs the resources taken by the disconnected tunnel data,
             it may remove the data earlierThe period of time that an established tunnel
             with no active sessions persists before being disconnected.";
    }

    typedef base-max-retries {
        type int32 {
            range "2..7";
        }
        default "5";
        description "The number of retries allowed for a tunnel before its control connection goes down.";
    }

    typedef child-max-retries {
        type int32 {
            range "2..7";
        }
        description "The number of retries allowed for a tunnel before its control connection goes down.";
    }

    typedef base-avp-hiding {
        type enumeration {
            enum "sensitive"                    { value 3; }
            enum "always"                       { value 4; }
        }
        description
            "This type describes when the H bit is set in an L2TP Attribute Value Pair (AVP).

             The value 'never' specifies that the H bit is never set.

             The value 'sensitive' specifies that the H bit is only set for AVP's
             containing sensitive information.

             The value 'always' specifies that the H bit is set for all AVP's where
             it is allowed.";
    }

    typedef child-avp-hiding {
        type enumeration {
            enum "never"                        { value 2; }
            enum "sensitive"                    { value 3; }
            enum "always"                       { value 4; }
        }
        description "This type describes when the H bit is set in an L2TP Attribute Value Pair (AVP).";
    }

    typedef base-session-assign-method {
        type enumeration {
            enum "existing-first"               { value 1; }
            enum "weighted"                     { value 2; }
            enum "weighted-random"              { value 3; }
        }
        default "existing-first";
        description
            "This type describes how new sessions are assigned to one of the set of
             suitable tunnels that are available or could be made available.

             The value 'existing-first' specifies that the first suitable tunnel is
             used or set up for the first session and re-used for all subsequent
             sessions.

             The value 'weighted' specifies that the sessions are shared between the
             available tunnels; if necessary, new tunnels are set up until the
             maximum number is reached; the distribution aims at an equal ratio of
             the actual number of sessions to the maximum number of sessions.

             The value 'weighted-random' is identical to 'weighted' except that one
             tunnel is picked randomly from the ones that have the same lowest
             ratio of the actual number of sessions to the maximum number of sessions.";
    }

    typedef child-session-assign-method {
        type enumeration {
            enum "existing-first"               { value 1; }
            enum "weighted"                     { value 2; }
            enum "weighted-random"              { value 3; }
        }
        description
            "This type describes how new sessions are assigned to one of the set of
             suitable tunnels that are available or could be made available.";
    }

    typedef host-name {
        type string {
            length "1..64";
        }
        description "The host name.";
    }

    typedef rtm-debounce-time {
        type union {
            type int32 {
                range "0..5000";
            }
            type enumeration {
                enum "infinite"                     { value -1; }
            }
        }
        units "milliseconds";
        default "infinite";
        description
            "This type specifies the debounce time the system applies before reacting to
             relevant events signaled by the system's Routing Table Manager (RTM).

             The time is rounded to multiples of 100 ms.";
    }

    typedef base-failover-recovery-method {
        type enumeration {
            enum "mcs"                          { value 1; }
            enum "recovery-tunnel"              { value 2; }
        }
        default "mcs";
        description
            "This type specifies how a pair of redundant LAC peers recover tunnel and
             session state (sequence numbers, for example) immediately after a failover.";
    }

    typedef child-failover-recovery-method {
        type enumeration {
            enum "mcs"                          { value 1; }
            enum "recovery-tunnel"              { value 2; }
        }
        description
            "This type specifies how a pair of redundant LAC peers recover tunnel and
             session state (sequence numbers, for example) immediately after a failover.";
    }

    typedef base-failover-recovery-time {
        type int32 {
            range "0..900";
        }
        units "seconds";
        default "0";
        description
            "The period of time an endpoint asks its peer to wait before assuming the
             recovery process has failed.";
    }

    typedef child-failover-recovery-time {
        type int32 {
            range "0..900";
        }
        units "seconds";
        description
            "The period of time an endpoint asks its peer to wait before assuming the
             recovery process has failed.";
    }

    typedef base-v3-cookie-length {
        type int32 {
            range "4|8";
        }
        description "The length of the cookie added to the data messages of the L2TP session";
    }

    typedef child-v3-cookie-length {
        type union {
            type int32 {
                range "4|8";
            }
            type enumeration {
                enum "disable"                      { value 0; }
            }
        }
        description "The length of the cookie added to the data messages of the L2TP session";
    }

    typedef base-v3-digest-type {
        type enumeration {
            enum "md5"                          { value 2; }
            enum "sha1"                         { value 3; }
        }
        description
            "The digest type to be used in the Message Digest AVP of the outgoing
             control messages of the L2TP tunnel.";
    }

    typedef child-v3-digest-type {
        type enumeration {
            enum "none"                         { value 1; }
            enum "md5"                          { value 2; }
            enum "sha1"                         { value 3; }
        }
        description
            "The digest type to be used in the Message Digest AVP of the outgoing
             control messages of the L2TP tunnel.";
    }

    typedef base-v3-nonce-length {
        type int32 {
            range "0|16..64";
        }
        default "0";
        description
            "The length of the nonce in the Control Message Authentication Nonce AVP added
             to outgoing control messages.";
    }

    typedef child-v3-nonce-length {
        type int32 {
            range "0|16..64";
        }
        description
            "The length of the nonce in the Control Message Authentication Nonce AVP added
             to outgoing control messages.";
    }

    typedef base-v3-reconnect-timeout {
        type union {
            type types-sros:time-duration {
                range "10..3600";
            }
            type enumeration {
                enum "infinite"                     { value -1; }
            }
        }
        units "seconds";
        default "infinite";
        description
            "The time the ethernet tunnel client of L2TP waits before a retry of the session
             after session setup failed or the session was closed.";
    }

    typedef child-v3-reconnect-timeout {
        type union {
            type types-sros:time-duration {
                range "10..3600";
            }
            type enumeration {
                enum "infinite"                     { value -1; }
            }
        }
        units "seconds";
        description
            "The time the ethernet tunnel client of L2TP waits before a retry of the session
             after session setup failed or the session was closed.";
    }

    typedef base-v3-tcp-mss-adjust {
        type int32 {
            range "512..9000";
        }
        units "octets";
        description
            "The Maximum Segment Size (MSS) for the TCP traffic in an L2TP tunnel of this
             virtual router which is sent from the public network to the private
             network. The system may use this value to adjust or insert the MSS
             option in the TCP SYN packet packet.";
    }

    typedef child-v3-tcp-mss-adjust {
        type union {
            type int32 {
                range "512..9000";
            }
            type enumeration {
                enum "disable"                      { value -1; }
            }
        }
        units "octets";
        description
            "The Maximum Segment Size (MSS) for the TCP traffic in an L2TP tunnel of this
             virtual router which is sent from the public network to the private
             network. The system may use this value to adjust or insert the MSS
             option in the TCP SYN packet packet.";
    }

    typedef loc-tunnel-id-or-zero {
        type uint32 {
            range "0..16383";
        }
        description "The local tunnel-id.";
    }

    typedef loc-tunnel-id {
        type uint32 {
            range "1..16383";
        }
        description "The local tunnel-id.";
    }

    typedef lns-group-id {
        type uint32 {
            range "1..4";
        }
        description "The identification number for a L2TP protocol ISA group.";
    }

    typedef protocol-version {
        type enumeration {
            enum "v2"                           { value 1; }
            enum "v3"                           { value 2; }
            enum "v3draft"                      { value 3; }
        }
        default "v2";
        description "The protocol version to be used";
    }

    typedef base-load-balance-method {
        type enumeration {
            enum "per-session"                  { value 1; }
            enum "per-tunnel"                   { value 2; }
        }
        description "The method used to assign sessions to ISA.";
    }

    typedef child-load-balance-method {
        type enumeration {
            enum "per-session"                  { value 1; }
            enum "per-tunnel"                   { value 2; }
        }
        description "The method used to assign sessions to ISA.";
    }

    typedef base-ppp-auth-protocol {
        type enumeration {
            enum "pap"                          { value 1; }
            enum "chap"                         { value 2; }
            enum "pref-chap"                    { value 3; }
            enum "pref-pap"                     { value 4; }
        }
        description "Specify what authentication protocol(s) will be negotiated during the LCP phase.";
    }

    typedef child-ppp-auth-protocol {
        type enumeration {
            enum "pap"                          { value 1; }
            enum "chap"                         { value 2; }
            enum "pref-chap"                    { value 3; }
            enum "pref-pap"                     { value 4; }
        }
        description "Specify what authentication protocol(s) will be negotiated during the LCP phase.";
    }

    typedef base-ppp-mtu {
        type uint32 {
            range "512..9212";
        }
        units "octets";
        description "The MTU size";
    }

    typedef child-ppp-mtu {
        type uint32 {
            range "512..9212";
        }
        units "octets";
        description "The MTU size";
    }

    typedef base-lcp-keepalive-multiplier {
        type uint32 {
            range "1..5";
        }
        description
            "Specifies how many LCP keepalive messages can be missed
             before the related session is brought down";
    }

    typedef child-lcp-keepalive-multiplier {
        type uint32 {
            range "1..5";
        }
        description
            "Specifies how many LCP keepalive messages can be missed
             before the related session is brought down";
    }

    typedef base-lcp-keepalive-interval {
        type uint32 {
            range "10..300";
        }
        units "seconds";
        description "Specifies the time interval at which LCP echo requests are transmitted.";
    }

    typedef child-lcp-keepalive-interval {
        type uint32 {
            range "10..300";
        }
        units "seconds";
        description "Specifies the time interval at which LCP echo requests are transmitted.";
    }

    typedef base-chap-challenge-length {
        type uint32 {
            range "8..64";
        }
        units "octets";
        description "The length of the CHAP challenge generated by the system";
    }

    typedef child-chap-challenge-length {
        type uint32 {
            range "8..64";
        }
        units "octets";
        description "The length of the CHAP challenge generated by the system";
    }

    typedef base-mlppp-max-links {
        type uint32 {
            range "1..8";
        }
        description "the maximum number of links in a MLPPP bundle";
    }

    typedef child-mlppp-max-links {
        type uint32 {
            range "1..8";
        }
        description "the maximum number of links in a MLPPP bundle";
    }

    typedef base-mlppp-max-frag-delay {
        type union {
            type uint32 {
                range "5..1000";
            }
            type enumeration {
                enum "no-fragmentation"             { value 0; }
            }
        }
        units "milliseconds";
        description "The maximum delay for MLPPP fragments.";
    }

    typedef child-mlppp-max-frag-delay {
        type uint32 {
            range "5..1000";
        }
        units "milliseconds";
        description "The maximum delay for MLPPP fragments.";
    }

    typedef base-mlppp-reassembly-timeout {
        type uint32 {
            range "100|1000";
        }
        units "milliseconds";
        description "The reassembly timeout for MLPPP fragments.";
    }

    typedef child-mlppp-reassembly-timeout {
        type uint32 {
            range "100|1000";
        }
        units "milliseconds";
        description "The reassembly timeout for MLPPP fragments.";
    }

    typedef group-oper-state {
        type enumeration {
            enum "active"                       { value 1; }
            enum "drain"                        { value 2; }
        }
        description "The operational state of the tunnel group.";
    }

    typedef connection-id {
        type uint32;
        description "The connection-id.";
    }

    typedef tunnel-oper-state {
        type enumeration {
            enum "unknown"                      { value 1; }
            enum "idle"                         { value 2; }
            enum "wait-reply"                   { value 3; }
            enum "wait-connected"               { value 4; }
            enum "established-idle"             { value 5; }
            enum "established"                  { value 6; }
            enum "draining"                     { value 7; }
            enum "drained"                      { value 8; }
            enum "closed"                       { value 9; }
            enum "closed-by-peer"               { value 10; }
        }
        description "The operational state of the tunnel.";
    }

    typedef transport-type {
        type enumeration {
            enum "unknown"                      { value 0; }
            enum "udp-ip"                       { value 1; }
            enum "ip"                           { value 2; }
        }
        description "The transport type used to carry L2TP messages.";
    }

    typedef stop-ccn-result {
        type enumeration {
            enum "no-error"                     { value 0; }
            enum "general-req"                  { value 1; }
            enum "general-err"                  { value 2; }
            enum "already-exists"               { value 3; }
            enum "req-not-auth"                 { value 4; }
            enum "version"                      { value 5; }
            enum "req-shutdown"                 { value 6; }
            enum "fsm-error"                    { value 7; }
        }
        description "The result of a StopCCN message.";
    }

    typedef cdn-result {
        type enumeration {
            enum "reserved"                     { value 0; }
            enum "disconnected-due-to-loss-of-carrier" { value 1; }
            enum "disconnected-see-error-code"  { value 2; }
            enum "disconnected-for-administrative-reasons" { value 3; }
            enum "failed-temporary-missing-facilities" { value 4; }
            enum "failed-permanent-missing-facitilities" { value 5; }
            enum "invalid-destination"          { value 6; }
            enum "failed-no-carrier"            { value 7; }
            enum "failed-busy-signal-detected"  { value 8; }
            enum "failed-no-dial-tone"          { value 9; }
            enum "not-established-in-allotted-time" { value 10; }
            enum "connected-but-no-framing"     { value 11; }
            enum "lost-tie-breaker"             { value 13; }
            enum "unsupported-pseudo-wire-type" { value 14; }
            enum "seq-without-valid-l2-layer"   { value 15; }
            enum "finite-state-machine-error-or-timeout" { value 16; }
        }
        description "The result of a CDN message.";
    }

    typedef general-error {
        type enumeration {
            enum "no-error"                     { value 0; }
            enum "no-control"                   { value 1; }
            enum "wrong-length"                 { value 2; }
            enum "field-out-of-range"           { value 3; }
            enum "insufficient-res"             { value 4; }
            enum "session-id-invalid"           { value 5; }
            enum "vendor-specific"              { value 6; }
            enum "try-another"                  { value 7; }
            enum "unknown-mandatory"            { value 8; }
            enum "try-another-directed"         { value 9; }
        }
        description
            "Indicates types of errors that are not specific to any particular
             L2TP request, but rather to protocol or message format errors.";
    }

    typedef blacklist-state {
        type enumeration {
            enum "not-blacklisted"              { value 0; }
            enum "blacklisted"                  { value 1; }
            enum "selectable"                   { value 2; }
        }
        description "The blacklist state.";
    }

    typedef proto-stats-type {
        type enumeration {
            enum "event"                        { value 1; }
            enum "dropped-msg-type"             { value 2; }
            enum "accepted-msg-type"            { value 3; }
            enum "original-transmitted-msg-type" { value 4; }
            enum "retransmitted-msg-type"       { value 5; }
            enum "incoming-cdn-result-code"     { value 6; }
            enum "incoming-stopccn-result-code" { value 7; }
            enum "incoming-error-code"          { value 8; }
            enum "outgoing-cdn-result-code"     { value 9; }
            enum "outgoing-stopccn-result-code" { value 10; }
            enum "outgoing-error-code"          { value 11; }
        }
        description "The statistics type.";
    }

    typedef failover-state {
        type enumeration {
            enum "not-recoverable"              { value 1; }
            enum "recoverable"                  { value 2; }
            enum "recovering"                   { value 3; }
            enum "recovery-failed"              { value 4; }
        }
        description "The failover state of the tunnel.";
    }

    typedef recovery-state {
        type enumeration {
            enum "recovery-tunnel"              { value 1; }
            enum "recovery-rejected"            { value 2; }
        }
        description "The failover state of a recovery tunnel";
    }

    typedef control-msg-behavior {
        type enumeration {
            enum "handle"                       { value 1; }
            enum "forward-to-mcs-peer"          { value 2; }
        }
        description "Indicates the behavior of this system with respect to control messages.";
    }

    typedef recovery-time {
        type uint32 {
            range "0..36000000";
        }
        units "milliseconds";
        description "The recovery time.";
    }

    typedef nonce {
        type string {
            length "0..130";
        }
        description "The value of the nonce AVP";
    }

    typedef session-oper-state {
        type enumeration {
            enum "unknown"                      { value 0; }
            enum "idle"                         { value 1; }
            enum "wait-tunnel"                  { value 2; }
            enum "wait-reply"                   { value 3; }
            enum "wait-acceptance"              { value 4; }
            enum "wait-connected"               { value 5; }
            enum "established"                  { value 6; }
            enum "closed"                       { value 7; }
            enum "closed-by-peer"               { value 8; }
        }
        description "The operational state of the session.";
    }

    typedef tunnel-id {
        type uint32 {
            range "0..65535";
        }
        description "The tunnel-id.";
    }

    typedef session-id {
        type uint32 {
            range "0..65535";
        }
        description "The session-id.";
    }

    typedef mlppp-bundle-index {
        type uint32;
        description "The MLPPP bundle index";
    }

    typedef pseudo-wire-type {
        type enumeration {
            enum "ethernet-vlan"                { value 4; }
            enum "ethernet"                     { value 5; }
            enum "ppp"                          { value 7; }
        }
        description "The pseudo-wire type.";
    }

    typedef seq-num-present-in-packet-type {
        type enumeration {
            enum "all"                          { value 1; }
            enum "never"                        { value 2; }
            enum "non-ip"                       { value 3; }
        }
        description "Indicates for which packet types sequence numbers are present.";
    }

    typedef peer-reachability {
        type enumeration {
            enum "unreachable"                  { value 1; }
            enum "reachable"                    { value 2; }
            enum "selectable"                   { value 3; }
            enum "blacklisted"                  { value 4; }
        }
        description "Indicates the reachability state.";
    }

    typedef peer-roles {
        type bits {
            bit lac                            { position 0; }
            bit lns                            { position 1; }
        }
        description "Indicates the roles the peer can take.";
    }

    typedef isa-member-oper-state {
        type enumeration {
            enum "unknown"                      { value 1; }
            enum "in-service"                   { value 2; }
            enum "out-of-service"               { value 3; }
            enum "draining"                     { value 4; }
            enum "drained"                      { value 5; }
        }
        description "The operational state of the ISA member";
    }

}
