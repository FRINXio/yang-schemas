module nokia-types-esa {

    yang-version "1.1";

    namespace "urn:nokia.com:sros:ns:yang:sr:types-esa";

    prefix "types-esa";

    import nokia-sros-yang-extensions     { prefix "sros-ext"; }


    sros-ext:sros-major-release "rel20";

    organization "Nokia";

    contact
        "Nokia SR OS Support
         Web: <http://www.nokia.com>";

    description
        "Common esa types data types used in the SR OS management system.

         Copyright 2016 Nokia. All rights reserved. Reproduction of this document
         is authorized on the condition that the foregoing copyright notice is included.

         This nokia-types-esa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-26";

    typedef esa-id {
        type int32 {
            range "1..16";
        }
        description "The ID of the ESA.";
    }

    typedef vm-id {
        type int32 {
            range "1..4";
        }
        description "The ID of the VM.";
    }

}
