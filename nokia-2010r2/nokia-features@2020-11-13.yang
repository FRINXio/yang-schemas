module nokia-features {

    yang-version "1.1";

    namespace "urn:nokia.com:sros:ns:yang:sr:features";

    prefix "nokia-features";

    import nokia-sros-yang-extensions     { prefix "sros-ext"; }


    sros-ext:sros-major-release "rel20";

    organization "Nokia";

    contact
        "Nokia SR OS Support
         Web: <http://www.nokia.com>";


    revision "2020-11-13";

    feature sros-filter-door-monitoring {
        description "Indicates whether this device supports filter door monitoring.";
    }

    feature sros-port-aps {
        description "Indicates whether this device supports APS ports.";
    }

    feature sros-power-shelf {
        description "Indicates whether this device supports Power Shelves.";
    }

    feature sros-qtag-manipulation {
        description "Indicates whether this device supports container qtag-manipulation under SAP ingress/egress.";
    }

    feature sros-vlan-manipulation {
        description "Indicates whether this device supports container vlan-manipulation under SAP ingress/egress";
    }

    feature sros-xgig-wan {
        description "Indicates whether this device supports xgig WAN mode.";
    }

}
