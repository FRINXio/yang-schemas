module nokia-types-pim {

    yang-version "1.1";

    namespace "urn:nokia.com:sros:ns:yang:sr:types-pim";

    prefix "types-pim";

    import nokia-sros-yang-extensions     { prefix "sros-ext"; }


    sros-ext:sros-major-release "rel20";

    organization "Nokia";

    contact
        "Nokia SR OS Support
         Web: <http://www.nokia.com>";

    description
        "Common pim data types used in the SR OS management system.

         Copyright 2016 Nokia. All rights reserved. Reproduction of this document
         is authorized on the condition that the foregoing copyright notice is included.

         This nokia-types-pim YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-09-16";

    typedef multicast-addr-family {
        type enumeration {
            enum "ipv4-multicast"               { value 0; }
            enum "ipv6-multicast"               { value 1; }
        }
        description "This type denotes the family for multicast protocol.";
    }

    typedef rpfv-type {
        type enumeration {
            enum "none"                         { value 0; }
            enum "mvpn"                         { value 1; }
            enum "core"                         { value 2; }
        }
        description "RPF vector type.";
    }

    typedef mrib-source-flags {
        type bits {
            bit self                           { position 0; }
            bit direct                         { position 1; }
            bit remote                         { position 2; }
        }
        description "The MRIB information about the source.";
    }

    typedef sg-flags {
        type bits {
            bit immediate-oif-list             { position 0; }
            bit inherited-oif-list             { position 1; }
            bit inherited-rpt-oif-list         { position 2; }
            bit local-rx-include               { position 3; }
            bit local-rx-exclude               { position 4; }
            bit join-prune-list                { position 5; }
            bit lost-assert-list               { position 6; }
            bit sg-rpt-prune-oif-list          { position 7; }
        }
        description "This type is used to indicate the different lists to which an element containing a field of this type belongs to.";
    }

    typedef vpls-sg-flags {
        type bits {
            bit immediate-oif-list             { position 0; }
            bit inherited-oif-list             { position 1; }
            bit inherited-rpt-oif-list         { position 2; }
            bit joined                         { position 3; }
            bit rpf-port                       { position 4; }
        }
        description "This type is used to indicate the different lists to which an element containing a field of this type belongs to.";
    }

    typedef sg-type {
        type enumeration {
            enum "star-star-rp"                 { value 0; }
            enum "star-g"                       { value 1; }
            enum "sg"                           { value 2; }
        }
        description "The type of the SG entry.";
    }

    typedef cscg-state {
        type enumeration {
            enum "tx-join-pending"              { value 0; }
            enum "tx-joined"                    { value 1; }
            enum "rx-not-joined"                { value 2; }
            enum "rx-joined"                    { value 3; }
            enum "rx-joined-tracking"           { value 4; }
        }
        description "The state of the (C-S,C-G).";
    }

    typedef join-prune-state {
        type enumeration {
            enum "no-info"                      { value 0; }
            enum "joined"                       { value 1; }
            enum "prune-pend"                   { value 2; }
            enum "pruned"                       { value 3; }
        }
    }

    typedef pim-vpls-operational-mode {
        type enumeration {
            enum "out-of-service"               { value 1; }
            enum "snooping-mode"                { value 2; }
            enum "proxy-mode"                   { value 3; }
        }
        description
            "Specifies the general operational mode for the
             pim on a vpls.";
    }

    typedef pmsi-interface-type {
        type enumeration {
            enum "rx"                           { value 0; }
            enum "tx"                           { value 1; }
        }
        description "PMSI interface type.";
    }

}
