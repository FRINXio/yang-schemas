module nokia-types-isis {

    yang-version "1.1";

    namespace "urn:nokia.com:sros:ns:yang:sr:types-isis";

    prefix "types-isis";

    import nokia-sros-yang-extensions     { prefix "sros-ext"; }


    sros-ext:sros-major-release "rel16";

    organization "Nokia";

    contact
        "Nokia SR OS Support
         Web: <http://www.nokia.com>";

    description
        "Common ISIS data types used in the SR OS management system.

         Copyright 2016 Nokia. All rights reserved. Reproduction of this document
         is authorized on the condition that the foregoing copyright notice is included.

         This nokia-types-isis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-07-14";

    typedef auth-type {
        type enumeration {
            enum "password"                     { value 2; }
            enum "message-digest"               { value 3; }
        }
        description
            "The method of authentication used to verify the authenticity of packets sent
             by neighboring routers on an IS-IS interface.";
    }

    typedef interface-type {
        type enumeration {
            enum "point-to-point"               { value 1; }
            enum "broadcast"                    { value 2; }
        }
        description "Type of interface.";
    }

    typedef area-address {
        type string {
            length "2..38";
            pattern "[0-9a-fA-F]{2}((\\.[0-9a-fA-F]{4})|(\\.[0-9a-fA-F]{2}){1,2}){0,6}";
        }
        description "OSI Network Service Address, e.g. NSAP, Network Entity Title.";
    }

    typedef level {
        type enumeration {
            enum "1"                            { value 1; }
            enum "2"                            { value 2; }
            enum "1/2"                          { value 3; }
        }
        default "1/2";
        description "Specifies the IS-IS Level.";
    }

    typedef overload-status {
        type enumeration {
            enum "not-in-overload"              { value 1; }
            enum "dynamic"                      { value 2; }
            enum "manual"                       { value 3; }
            enum "manual-on-boot"               { value 4; }
            enum "sfm-overload"                 { value 5; }
            enum "fib-add-fail"                 { value 6; }
            enum "rtm-add-fail"                 { value 7; }
            enum "prefix-limit"                 { value 8; }
        }
        description "Overload status of the IS-IS protocol level.";
    }

    typedef level-state {
        type enumeration {
            enum "off"                          { value 1; }
            enum "on"                           { value 2; }
            enum "waiting"                      { value 3; }
        }
        description "States of the ISIS protocol.";
    }

    typedef routing-topology {
        type enumeration {
            enum "false"                        { value 0; }
            enum "native"                       { value 1; }
            enum "mt"                           { value 2; }
        }
        description
            "isis routing topology.
             native(1) - Indicates standard topology.
             mt(2) - Indicates multi-topology for IPv4/IPv6 unicast/multicast routing.";
    }

    typedef lsp-buffer-size {
        type int32 {
            range "490..9190";
        }
        units "bytes";
        description "Represents the extended integer sub range for LSP size.";
    }

    typedef hello-padding-type {
        type enumeration {
            enum "adaptive"                     { value 1; }
            enum "loose"                        { value 2; }
            enum "strict"                       { value 3; }
            enum "none"                         { value 4; }
        }
        description "Specifies the type of padding that should be done on the ISIS hello packets.";
    }

    typedef sid-type {
        type enumeration {
            enum "index"                        { value 1; }
            enum "label"                        { value 2; }
        }
        description "Specifies how the value of SID shall be interpreted.";
    }

    typedef circuit-id {
        type string {
            length "4..18";
        }
        description "ID for a circuit.";
    }

    typedef metric {
        type uint32 {
            range "1..16777215";
        }
        description "Specifies metric type.";
    }

    typedef oper-metric {
        type union {
            type types-isis:metric;
            type enumeration {
                enum "none"                         { value 0; }
            }
        }
    }

    typedef cidr-next-hop-type {
        type enumeration {
            enum "regular"                      { value 1; }
            enum "tunneled"                     { value 2; }
            enum "six-over-mpls"                { value 3; }
            enum "six-over-four"                { value 4; }
            enum "tunneled-ipv6"                { value 5; }
        }
        description
            "The cidr-next-hop-type is the type of next hop for a route.
             regular       : Next hop is an IPv4 destination address for an
                             IPv4 prefix or and IPv6 destination address for
                             and IPv6 prefix.
             tunneled      : Next hop refers to a IPv4 LDP/RSVP/GRE tunnel.
             six-over-mpls : Next hop is a MPLS tunnel for IPv6 prefix.
             six-over-four : Next hop is a IPv4 destination for IPv6 prefix.
             tunneled-ipv6 : Next hop refers to a IPv6 LDP tunnel.";
    }

    typedef cidr-next-hop-owner {
        type enumeration {
            enum "unknown"                      { value 0; }
            enum "rsvp"                         { value 1; }
            enum "ldp"                          { value 2; }
            enum "ldp-over-rsvp"                { value 3; }
            enum "bgp"                          { value 4; }
            enum "sr-ospf"                      { value 5; }
            enum "sr-isis"                      { value 6; }
            enum "sr-te"                        { value 7; }
            enum "udp"                          { value 8; }
            enum "sr-bgp"                       { value 9; }
        }
        description
            "The cidr-next-hop-owner is the owner of the next hop for a route.
             unknown       :  Next hop owner is unknown.
             rsvp          :  Next hop owner is RSVP.
             ldp           :  Next hop owner is LDP.
             ldp-over-rsvp :  Next hop owner is LDP over RSVP.
             bgp           :  Next hop owner is BGP.
             sr-ospf       :  Next hop owner is SR-OSPF.
             sr-isis       :  Next hop owner is SR-ISIS.
             sr-te         :  Next hop owner is SR-TE.
             udp           :  Next hop owner is UDP.
             srBgp         :  Next hop owner is BGP-SR TE.";
    }

    typedef snpa-address {
        type string {
            length "0..40";
        }
    }

    typedef lsp-id {
        type string {
            length "20";
            pattern "([0-9A-Fa-f]{4}\\.){3}[0-9A-Fa-f]{2}-[0-9A-Fa-f]{2}";
        }
        default "0000.0000.0000.00-00";
    }

    typedef tlv-type {
        type enumeration {
            enum "unassigned"                   { value 0; }
            enum "area-addresses"               { value 1; }
            enum "is-neighbors"                 { value 2; }
            enum "instance-id"                  { value 7; }
            enum "authentication"               { value 10; }
            enum "purge-oi"                     { value 13; }
            enum "extended-is-reachability"     { value 22; }
            enum "ipv4-internal-reachability"   { value 128; }
            enum "supported-protocols"          { value 129; }
            enum "ipv4-external-reachability"   { value 130; }
            enum "ipv4-if-addresses"            { value 132; }
            enum "router-id"                    { value 134; }
            enum "extended-ipv4-reachability"   { value 135; }
            enum "hostname"                     { value 137; }
            enum "srlg"                         { value 138; }
            enum "mt-is-neigbor"                { value 222; }
            enum "multi-topology"               { value 229; }
            enum "ipv6-if-addresses"            { value 232; }
            enum "mt-ipv4-reachability"         { value 235; }
            enum "ipv6-reachability"            { value 236; }
            enum "mt-ipv6-reachability"         { value 237; }
            enum "router-capability"            { value 242; }
        }
    }

    typedef sub-tlv-rtr-cap-type {
        type enumeration {
            enum "unassigned"                   { value 0; }
            enum "te-node"                      { value 1; }
            enum "segment-routing-capability"   { value 2; }
            enum "te-router-id"                 { value 11; }
            enum "segment-routing-algorithm"    { value 19; }
            enum "entropy-label-suport"         { value 20; }
            enum "entropy-label-max-stack-depth" { value 21; }
        }
    }

    typedef sub-tlv-ext-is-reach-type {
        type enumeration {
            enum "unassigned"                   { value 0; }
            enum "admin-group"                  { value 3; }
            enum "local-and-remote-id"          { value 4; }
            enum "ipv4-interface-address"       { value 6; }
            enum "ipv4-neighbor-address"        { value 8; }
            enum "max-link-bandwidth"           { value 9; }
            enum "max-reservable-link-bandwidth" { value 10; }
            enum "unreserved-bandwidth"         { value 11; }
            enum "te-default-metric"            { value 18; }
            enum "bandwidth-constraints"        { value 22; }
            enum "spb-metric"                   { value 29; }
            enum "adjacency-sid"                { value 31; }
            enum "adjacency-sid-lan"            { value 32; }
        }
    }

    typedef sub-tlv-prefix-reach-type {
        type enumeration {
            enum "unassigned"                   { value 0; }
            enum "tag32"                        { value 1; }
            enum "tag64"                        { value 2; }
            enum "prefix-sid"                   { value 3; }
            enum "flags"                        { value 4; }
        }
    }

}
