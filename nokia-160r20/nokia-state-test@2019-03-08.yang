submodule nokia-state-test {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel16";

    organization "Nokia";

    contact
        "Nokia SR OS Support
         Web: <http://www.nokia.com>";

    description
        "Nokia YANG Data model with operational state for Internal test yang to be used for MD-CLI testing on SR OS based routers.

         Copyright 2016 Nokia. All rights reserved. Reproduction of this document
         is authorized on the condition that the foregoing copyright notice is included.

         This nokia-state-test YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-03-08";

    grouping state-test {
        container test {
            description "Root test. All lists and containers should be inside this list";

            container container-structures {
                description "Container for testing structures supports config groups.";

                leaf leaf-union-address {
                    type union {
                        type types-sros:ip-address;
                        type types-sros:ipv6-address;
                        type yang:mac-address;
                    }
                    description "Ip, Ipv6, Mac address.";
                }

                leaf leaf-bytes-union-enum-int64 {
                    type union {
                        type enumeration {
                            enum "no-limit"                     { value 0; }
                        }
                        type int64 {
                            range "1..max";
                        }
                    }
                    units "bytes";
                    description "Maximum allowed amount of memory that can be allocated for a group.";
                }

                leaf leaf-percent-union-decimal64-string {
                    type union {
                        type decimal64 {
                            range "0..100";
                            fraction-digits 2;
                        }
                        type string {
                            length "5";
                        }
                    }
                    units "percent";
                    description "Relative amount of time used by the busiest task/core.";
                }

                list list-1-key-leafref-string {
                    key "leafref-key1";
                    description "List with leafref key.";

                    leaf leafref-key1 {
                        type leafref {
                            path "../../list-1-key-string/key1";
                        }
                        description "Leafref key for this list.";
                    }

                    leaf leaf-union-address {
                        type union {
                            type types-sros:ip-address;
                            type types-sros:ipv6-address;
                            type yang:mac-address;
                        }
                        description "Ip, Ipv6, Mac address.";
                    }

                    leaf leaf-bytes-union-enum-int64 {
                        type union {
                            type enumeration {
                                enum "no-limit"                     { value 0; }
                            }
                            type int64 {
                                range "1..max";
                            }
                        }
                        units "bytes";
                        description "Maximum allowed amount of memory that can be allocated for a group.";
                    }

                    leaf leaf-percent-union-decimal64-string {
                        type union {
                            type decimal64 {
                                range "0..100";
                                fraction-digits 2;
                            }
                            type string {
                                length "5";
                            }
                        }
                        units "percent";
                        description "Relative amount of time used by the busiest task/core.";
                    }

                } // list list-1-key-leafref-string

                list list-2-keys-enum-int32 {
                    key "key1 key2";
                    description "Entry of summary filter log.";

                    leaf key1 {
                        type enumeration {
                            enum "first"                        { value 0; }
                            enum "second"                       { value 1; }
                            enum "third"                        { value 2; }
                        }
                        description "Filter type.";
                    }

                    leaf key2 {
                        type int32;
                        description "Entry identifier.";
                    }

                    leaf leaf-union-address {
                        type union {
                            type types-sros:ip-address;
                            type types-sros:ipv6-address;
                            type yang:mac-address;
                        }
                        description "Ip, Ipv6, Mac address.";
                    }

                    leaf leaf-bytes-union-enum-int64 {
                        type union {
                            type enumeration {
                                enum "no-limit"                     { value 0; }
                            }
                            type int64 {
                                range "1..max";
                            }
                        }
                        units "bytes";
                        description "Maximum allowed amount of memory that can be allocated for a group.";
                    }

                    leaf leaf-percent-union-decimal64-string {
                        type union {
                            type decimal64 {
                                range "0..100";
                                fraction-digits 2;
                            }
                            type string {
                                length "5";
                            }
                        }
                        units "percent";
                        description "Relative amount of time used by the busiest task/core.";
                    }

                } // list list-2-keys-enum-int32

                list list-2-keys-leafref-string-leafref-string {
                    key "leafref-key1 leafref-key2";
                    description "List with 2 leafref keys.";

                    leaf leafref-key1 {
                        type leafref {
                            path "../../list-2-keys-string-string/key1";
                        }
                        description "Leafref 1/2 key for this list.";
                    }

                    leaf leafref-key2 {
                        type leafref {
                            path "../../list-2-keys-string-string/key2";
                        }
                        description "Leafref 2/2 key for this list.";
                    }

                    leaf leaf-union-address {
                        type union {
                            type types-sros:ip-address;
                            type types-sros:ipv6-address;
                            type yang:mac-address;
                        }
                        description "Ip, Ipv6, Mac address.";
                    }

                    leaf leaf-bytes-union-enum-int64 {
                        type union {
                            type enumeration {
                                enum "no-limit"                     { value 0; }
                            }
                            type int64 {
                                range "1..max";
                            }
                        }
                        units "bytes";
                        description "Maximum allowed amount of memory that can be allocated for a group.";
                    }

                    leaf leaf-percent-union-decimal64-string {
                        type union {
                            type decimal64 {
                                range "0..100";
                                fraction-digits 2;
                            }
                            type string {
                                length "5";
                            }
                        }
                        units "percent";
                        description "Relative amount of time used by the busiest task/core.";
                    }

                } // list list-2-keys-leafref-string-leafref-string

                list list-1-key-string {
                    key "key1";
                    description "List with 1 key - string.";

                    leaf key1 {
                        type string;
                        description
                            "Key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    container container-no-nmi {
                        description "no NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-no-nmi

                    container container-nmi {
                        description "NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-nmi

                    container container-xxxx-with-very-long-name {
                        description "Test container for testing.";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-yyyy-with-even-longer-than-very-long-name {
                            description "Test container for testing.";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                            container container-zzz-with-super-long-name-even-longer-than-previous-long-name {
                                description "Test container for testing.";

                                leaf leaf-union-address {
                                    type union {
                                        type types-sros:ip-address;
                                        type types-sros:ipv6-address;
                                        type yang:mac-address;
                                    }
                                    description "Ip, Ipv6, Mac address.";
                                }

                                leaf leaf-bytes-union-enum-int64 {
                                    type union {
                                        type enumeration {
                                            enum "no-limit"                     { value 0; }
                                        }
                                        type int64 {
                                            range "1..max";
                                        }
                                    }
                                    units "bytes";
                                    description "Maximum allowed amount of memory that can be allocated for a group.";
                                }

                                leaf leaf-percent-union-decimal64-string {
                                    type union {
                                        type decimal64 {
                                            range "0..100";
                                            fraction-digits 2;
                                        }
                                        type string {
                                            length "5";
                                        }
                                    }
                                    units "percent";
                                    description "Relative amount of time used by the busiest task/core.";
                                }

                            } // container container-zzz-with-super-long-name-even-longer-than-previous-long-name

                        } // container container-yyyy-with-even-longer-than-very-long-name

                    } // container container-xxxx-with-very-long-name

                } // list list-1-key-string

                list list-1-key-int32 {
                    key "key1";
                    description "List with 1 key - int32.";

                    leaf key1 {
                        type int32;
                        description
                            "Key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    container container-no-nmi {
                        description "no NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-no-nmi

                    container container-nmi {
                        description "NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-nmi

                    container container-xxxx-with-very-long-name {
                        description "Test container for testing.";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-yyyy-with-even-longer-than-very-long-name {
                            description "Test container for testing.";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                            container container-zzz-with-super-long-name-even-longer-than-previous-long-name {
                                description "Test container for testing.";

                                leaf leaf-union-address {
                                    type union {
                                        type types-sros:ip-address;
                                        type types-sros:ipv6-address;
                                        type yang:mac-address;
                                    }
                                    description "Ip, Ipv6, Mac address.";
                                }

                                leaf leaf-bytes-union-enum-int64 {
                                    type union {
                                        type enumeration {
                                            enum "no-limit"                     { value 0; }
                                        }
                                        type int64 {
                                            range "1..max";
                                        }
                                    }
                                    units "bytes";
                                    description "Maximum allowed amount of memory that can be allocated for a group.";
                                }

                                leaf leaf-percent-union-decimal64-string {
                                    type union {
                                        type decimal64 {
                                            range "0..100";
                                            fraction-digits 2;
                                        }
                                        type string {
                                            length "5";
                                        }
                                    }
                                    units "percent";
                                    description "Relative amount of time used by the busiest task/core.";
                                }

                            } // container container-zzz-with-super-long-name-even-longer-than-previous-long-name

                        } // container container-yyyy-with-even-longer-than-very-long-name

                    } // container container-xxxx-with-very-long-name

                } // list list-1-key-int32

                list list-2-keys-string-int32 {
                    key "key1 key2";
                    description "List with 2 keys - string, int32.";

                    leaf key1 {
                        type string;
                        description
                            "1/2 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    leaf key2 {
                        type int32;
                        description
                            "2/2 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    container container-no-nmi {
                        description "no NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-no-nmi

                    container container-nmi {
                        description "NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-nmi

                    container container-xxxx-with-very-long-name {
                        description "Test container for testing.";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-yyyy-with-even-longer-than-very-long-name {
                            description "Test container for testing.";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                            container container-zzz-with-super-long-name-even-longer-than-previous-long-name {
                                description "Test container for testing.";

                                leaf leaf-union-address {
                                    type union {
                                        type types-sros:ip-address;
                                        type types-sros:ipv6-address;
                                        type yang:mac-address;
                                    }
                                    description "Ip, Ipv6, Mac address.";
                                }

                                leaf leaf-bytes-union-enum-int64 {
                                    type union {
                                        type enumeration {
                                            enum "no-limit"                     { value 0; }
                                        }
                                        type int64 {
                                            range "1..max";
                                        }
                                    }
                                    units "bytes";
                                    description "Maximum allowed amount of memory that can be allocated for a group.";
                                }

                                leaf leaf-percent-union-decimal64-string {
                                    type union {
                                        type decimal64 {
                                            range "0..100";
                                            fraction-digits 2;
                                        }
                                        type string {
                                            length "5";
                                        }
                                    }
                                    units "percent";
                                    description "Relative amount of time used by the busiest task/core.";
                                }

                            } // container container-zzz-with-super-long-name-even-longer-than-previous-long-name

                        } // container container-yyyy-with-even-longer-than-very-long-name

                    } // container container-xxxx-with-very-long-name

                } // list list-2-keys-string-int32

                list list-2-keys-int32-int32 {
                    key "key1 key2";
                    description "Named list with 2 keys - int32, int32.";

                    leaf key1 {
                        type int32;
                        description
                            "1/2 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    leaf key2 {
                        type int32;
                        description
                            "2/2 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    container container-no-nmi {
                        description "no NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-no-nmi

                    container container-nmi {
                        description "NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-nmi

                    container container-xxxx-with-very-long-name {
                        description "Test container for testing.";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-yyyy-with-even-longer-than-very-long-name {
                            description "Test container for testing.";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                            container container-zzz-with-super-long-name-even-longer-than-previous-long-name {
                                description "Test container for testing.";

                                leaf leaf-union-address {
                                    type union {
                                        type types-sros:ip-address;
                                        type types-sros:ipv6-address;
                                        type yang:mac-address;
                                    }
                                    description "Ip, Ipv6, Mac address.";
                                }

                                leaf leaf-bytes-union-enum-int64 {
                                    type union {
                                        type enumeration {
                                            enum "no-limit"                     { value 0; }
                                        }
                                        type int64 {
                                            range "1..max";
                                        }
                                    }
                                    units "bytes";
                                    description "Maximum allowed amount of memory that can be allocated for a group.";
                                }

                                leaf leaf-percent-union-decimal64-string {
                                    type union {
                                        type decimal64 {
                                            range "0..100";
                                            fraction-digits 2;
                                        }
                                        type string {
                                            length "5";
                                        }
                                    }
                                    units "percent";
                                    description "Relative amount of time used by the busiest task/core.";
                                }

                            } // container container-zzz-with-super-long-name-even-longer-than-previous-long-name

                        } // container container-yyyy-with-even-longer-than-very-long-name

                    } // container container-xxxx-with-very-long-name

                } // list list-2-keys-int32-int32

                list list-2-keys-string-string {
                    key "key1 key2";
                    description "Named list with 2 keys - string, string.";

                    leaf key1 {
                        type string;
                        description
                            "1/2 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    leaf key2 {
                        type string;
                        description
                            "2/2 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    container container-no-nmi {
                        description "no NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-no-nmi

                    container container-nmi {
                        description "NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-nmi

                    container container-xxxx-with-very-long-name {
                        description "Test container for testing.";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-yyyy-with-even-longer-than-very-long-name {
                            description "Test container for testing.";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                            container container-zzz-with-super-long-name-even-longer-than-previous-long-name {
                                description "Test container for testing.";

                                leaf leaf-union-address {
                                    type union {
                                        type types-sros:ip-address;
                                        type types-sros:ipv6-address;
                                        type yang:mac-address;
                                    }
                                    description "Ip, Ipv6, Mac address.";
                                }

                                leaf leaf-bytes-union-enum-int64 {
                                    type union {
                                        type enumeration {
                                            enum "no-limit"                     { value 0; }
                                        }
                                        type int64 {
                                            range "1..max";
                                        }
                                    }
                                    units "bytes";
                                    description "Maximum allowed amount of memory that can be allocated for a group.";
                                }

                                leaf leaf-percent-union-decimal64-string {
                                    type union {
                                        type decimal64 {
                                            range "0..100";
                                            fraction-digits 2;
                                        }
                                        type string {
                                            length "5";
                                        }
                                    }
                                    units "percent";
                                    description "Relative amount of time used by the busiest task/core.";
                                }

                            } // container container-zzz-with-super-long-name-even-longer-than-previous-long-name

                        } // container container-yyyy-with-even-longer-than-very-long-name

                    } // container container-xxxx-with-very-long-name

                } // list list-2-keys-string-string

                list list-3-keys-string-int32-string {
                    key "key1 key2 key3";
                    description "Named list with 3 keys - string, int32, string.";

                    leaf key1 {
                        type string;
                        description
                            "1/3 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    leaf key2 {
                        type int32;
                        description
                            "2/3 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    leaf key3 {
                        type string;
                        description
                            "3/3 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    container container-no-nmi {
                        description "no NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-no-nmi

                    container container-nmi {
                        description "NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-nmi

                    container container-xxxx-with-very-long-name {
                        description "Test container for testing.";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-yyyy-with-even-longer-than-very-long-name {
                            description "Test container for testing.";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                            container container-zzz-with-super-long-name-even-longer-than-previous-long-name {
                                description "Test container for testing.";

                                leaf leaf-union-address {
                                    type union {
                                        type types-sros:ip-address;
                                        type types-sros:ipv6-address;
                                        type yang:mac-address;
                                    }
                                    description "Ip, Ipv6, Mac address.";
                                }

                                leaf leaf-bytes-union-enum-int64 {
                                    type union {
                                        type enumeration {
                                            enum "no-limit"                     { value 0; }
                                        }
                                        type int64 {
                                            range "1..max";
                                        }
                                    }
                                    units "bytes";
                                    description "Maximum allowed amount of memory that can be allocated for a group.";
                                }

                                leaf leaf-percent-union-decimal64-string {
                                    type union {
                                        type decimal64 {
                                            range "0..100";
                                            fraction-digits 2;
                                        }
                                        type string {
                                            length "5";
                                        }
                                    }
                                    units "percent";
                                    description "Relative amount of time used by the busiest task/core.";
                                }

                            } // container container-zzz-with-super-long-name-even-longer-than-previous-long-name

                        } // container container-yyyy-with-even-longer-than-very-long-name

                    } // container container-xxxx-with-very-long-name

                } // list list-3-keys-string-int32-string

                list list-named-3-keys-string-int32-int32 {
                    key "key1-named key2 key3";
                    description "Named list with 3 keys - string, int32, int32.";

                    leaf key1-named {
                        type string;
                        description
                            "1/3 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    leaf key2 {
                        type int32;
                        description
                            "2/3 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    leaf key3 {
                        type int32;
                        description
                            "3/3 part of key for this list.

                             Long description - Lorem ipsum dolor sit amet, consectetur adipiscing elit, sed do eiusmod tempor incididunt ut labore et dolore magna aliqua. Ut enim ad minim veniam, quis nostrud exercitation ullamco laboris nisi ut aliquip ex ea commodo consequat. Duis aute irure dolor in reprehenderit in voluptate velit esse cillum dolore eu fugiat nulla pariatur. Excepteur sint occaecat cupidatat non proident, sunt in culpa qui officia deserunt mollit anim id est laborum.";
                    }

                    container container-no-nmi {
                        description "no NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-no-nmi

                    container container-nmi {
                        description "NMI container";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-nmi-presence-1 {
                            description "Description of presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-1

                        container container-nmi-presence-2 {
                            description "Description of presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-presence-2

                        container container-nmi-non-presence-2 {
                            description "Description of non presence container 2";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-2

                        container container-nmi-non-presence-1 {
                            description "Description of non presence container 1";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                        } // container container-nmi-non-presence-1

                    } // container container-nmi

                    container container-xxxx-with-very-long-name {
                        description "Test container for testing.";

                        leaf leaf-union-address {
                            type union {
                                type types-sros:ip-address;
                                type types-sros:ipv6-address;
                                type yang:mac-address;
                            }
                            description "Ip, Ipv6, Mac address.";
                        }

                        leaf leaf-bytes-union-enum-int64 {
                            type union {
                                type enumeration {
                                    enum "no-limit"                     { value 0; }
                                }
                                type int64 {
                                    range "1..max";
                                }
                            }
                            units "bytes";
                            description "Maximum allowed amount of memory that can be allocated for a group.";
                        }

                        leaf leaf-percent-union-decimal64-string {
                            type union {
                                type decimal64 {
                                    range "0..100";
                                    fraction-digits 2;
                                }
                                type string {
                                    length "5";
                                }
                            }
                            units "percent";
                            description "Relative amount of time used by the busiest task/core.";
                        }

                        container container-yyyy-with-even-longer-than-very-long-name {
                            description "Test container for testing.";

                            leaf leaf-union-address {
                                type union {
                                    type types-sros:ip-address;
                                    type types-sros:ipv6-address;
                                    type yang:mac-address;
                                }
                                description "Ip, Ipv6, Mac address.";
                            }

                            leaf leaf-bytes-union-enum-int64 {
                                type union {
                                    type enumeration {
                                        enum "no-limit"                     { value 0; }
                                    }
                                    type int64 {
                                        range "1..max";
                                    }
                                }
                                units "bytes";
                                description "Maximum allowed amount of memory that can be allocated for a group.";
                            }

                            leaf leaf-percent-union-decimal64-string {
                                type union {
                                    type decimal64 {
                                        range "0..100";
                                        fraction-digits 2;
                                    }
                                    type string {
                                        length "5";
                                    }
                                }
                                units "percent";
                                description "Relative amount of time used by the busiest task/core.";
                            }

                            container container-zzz-with-super-long-name-even-longer-than-previous-long-name {
                                description "Test container for testing.";

                                leaf leaf-union-address {
                                    type union {
                                        type types-sros:ip-address;
                                        type types-sros:ipv6-address;
                                        type yang:mac-address;
                                    }
                                    description "Ip, Ipv6, Mac address.";
                                }

                                leaf leaf-bytes-union-enum-int64 {
                                    type union {
                                        type enumeration {
                                            enum "no-limit"                     { value 0; }
                                        }
                                        type int64 {
                                            range "1..max";
                                        }
                                    }
                                    units "bytes";
                                    description "Maximum allowed amount of memory that can be allocated for a group.";
                                }

                                leaf leaf-percent-union-decimal64-string {
                                    type union {
                                        type decimal64 {
                                            range "0..100";
                                            fraction-digits 2;
                                        }
                                        type string {
                                            length "5";
                                        }
                                    }
                                    units "percent";
                                    description "Relative amount of time used by the busiest task/core.";
                                }

                            } // container container-zzz-with-super-long-name-even-longer-than-previous-long-name

                        } // container container-yyyy-with-even-longer-than-very-long-name

                    } // container container-xxxx-with-very-long-name

                } // list list-named-3-keys-string-int32-int32

            } // container container-structures

            container container-units {
                description "Test container for units testing.";

                container container-misc {

                    leaf leaf-centipercents {
                        type uint32 {
                            range "0..10000";
                        }
                        units "centipercent";
                        description "Indicates the current relative adjustment of the receive decision threshold voltage.";
                    }

                    leaf leaf-celsius {
                        type int32;
                        units "degrees celsius";
                        description
                            "The temperature threshold for this power supply
                             tray in degrees celsius.";
                    }

                } // container container-misc

            } // container container-units

            container resources {
                description "Test container for resources";

                list memory {
                    key "name";

                    leaf name {
                        type string;
                    }

                    leaf alloc-success {
                        type boolean;
                        description "Successful allocation";
                    }

                } // list memory

            } // container resources

            list persistent-index {
                key "application name";
                description
                    "Index value is firstly get from queue. If queue is empty, value comes from iterator.

                     You can manipulate with queue by command:
                      - 'shell DEBUG_testPersistentIndexQueueAdd <int>' - add value to queue
                      - 'shell DEBUG_testPersistentIndexQueueDump' - print queue
                      - 'shell DEBUG_testPersistentIndexQueueClear' - remove all elements from queue.";

                leaf application {
                    type enumeration {
                        enum "test"                         { value 1; }
                        enum "testapp"                      { value 2; }
                    }
                }

                leaf name {
                    type string {
                        length "1..512";
                    }
                }

                leaf persistent-id-value {
                    type int32;
                }

            } // list persistent-index

            list persistent-index-with-autorange {
                key "test-name";
                description "Persisten index withautorange.";

                leaf test-name {
                    type string {
                        length "1..512";
                    }
                }

                leaf oper-persisten-id {
                    type uint32;
                }

            } // list persistent-index-with-autorange

            container md-auto-id {
                description "Id ranges for MD Auto assignment";

                container persistent-id-range {

                    leaf used-md-auto-id-for-test {
                        type uint32 {
                            range "0..2147483647";
                        }
                    }

                } // container persistent-id-range

            } // container md-auto-id

        } // container test

    } // grouping state-test

}
