submodule nokia-state-isa {

    yang-version "1.1";

    belongs-to nokia-state { prefix "state"; }

    import ietf-yang-types                { prefix "yang"; }
    import nokia-sros-yang-extensions     { prefix "sros-ext"; }
    import nokia-types-isa                { prefix "types-isa"; }
    import nokia-types-l2tp               { prefix "types-l2tp"; }
    import nokia-types-nat                { prefix "types-nat"; }
    import nokia-types-redundancy         { prefix "types-redundancy"; }
    import nokia-types-sros               { prefix "types-sros"; }

    include nokia-state-card;
    include nokia-state-isa-video-group;

    sros-ext:sros-major-release "rel16";

    organization "Nokia";

    contact
        "Nokia SR OS Support
         Web: <http://www.nokia.com>";

    description
        "Nokia YANG Data model with operational state for ISA configuration on SR OS based routers.

         Copyright 2016 Nokia. All rights reserved. Reproduction of this document
         is authorized on the condition that the foregoing copyright notice is included.

         This nokia-state-isa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-05-03";

    grouping state-isa {
        container isa {
            description "Enter the isa context";

            list tunnel-group {
                key "id";
                description "Enter the tunnel-group context";

                leaf id {
                    type types-redundancy:tunnel-group-id;
                    description "The unique identifier of the tunnel group.";
                }

                leaf oper-state {
                    type types-sros:oper-state;
                    description "The operational status of ISA tunnel group.";
                }

                leaf active-isa {
                    type types-isa:slot-mda;
                    description "The active ISA that is being used for this module group.";
                }

                leaf tunnel-count {
                    type uint32;
                    description "The number of IPsec tunnels being used for this module group.";
                }

                leaf max-tunnel {
                    type uint32;
                    description
                        "The maximum number of IPsec tunnels available for this module
                         group.";
                }

                leaf oper-flags {
                    type bits {
                        bit admin-down                     { position 0; }
                        bit no-active                      { position 1; }
                        bit no-resources                   { position 2; }
                        bit mc-admin-down                  { position 3; }
                    }
                    description "The operational flags to determine the ISA tunnel group.";
                }

                leaf ip-tunnel-count {
                    type uint32;
                    description "The number of IP tunnels being used for this module group.";
                }

                leaf ip-max-tunnel {
                    type uint32;
                    description
                        "The maximum number of IP tunnels available for this module
                         group.";
                }

                choice redundancy {
                    description "Redundancy mode for ISAs in this tunnel group";
                    case multi-active {

                        container multi-active {
                            description "Enter the multi-active context";

                            list isa {
                                key "isa-id";
                                description "Enter the isa context";

                                leaf isa-id {
                                    type types-isa:slot-mda;
                                    description "The ISA associated with this tunnel group.";
                                }

                                leaf tunnel-group-in-use {
                                    type boolean;
                                    description
                                        "Activate this ISA in the Integrated Service Adaptor (ISA)
                                         tunnel group. The value is only meaningful when
                                         multi-active is true.";
                                }

                            } // list isa

                        } // container multi-active

                    }
                }
            } // list tunnel-group

            container nat-mda {
                description "NAT ISA";

                list resources {
                    key "mda-id resource";
                    description "Resource consumption per NAT ISA MDA";

                    leaf mda-id {
                        type types-isa:slot-mda;
                        description "An MDA in the NAT ISA Group";
                    }

                    leaf resource {
                        type uint32;
                        description "Resource that is monitored";
                    }

                    leaf description {
                        type string {
                            length "0..64";
                        }
                        description "The human-readable identifier of the resource.";
                    }

                    leaf value {
                        type yang:gauge64;
                        description "Actual consumed value";
                    }

                    leaf max {
                        type uint64;
                        description "The max value this resource can have, depending on the configuration";
                    }

                    leaf peak {
                        type yang:gauge64;
                        description "The peak value for the resource";
                    }

                    leaf peak-timestamp {
                        type types-sros:date-time;
                        description "The timestamp when the peak value was observed";
                    }

                    leaf limited {
                        type boolean;
                        description "Indicates that the max value is limited";
                    }

                } // list resources

            } // container nat-mda

            list nat-group {
                key "id";
                description "Enter the nat-group context";

                leaf id {
                    type uint32 {
                        range "1..4";
                    }
                    description "Nat-group identifier";
                }

                leaf oper-state {
                    type types-sros:oper-state;
                    description
                        "The value of tmnxNatIsaGrpOperState indicates
                         the operational status of this NAT ISA group";
                }

                leaf degraded {
                    type boolean;
                    description
                        "indicates if this NAT ISA group is degraded,
                         while operationally still in service";
                }

                list mda {
                    key "mda-id";
                    description "Enter the mda context";

                    leaf mda-id {
                        type types-isa:slot-mda;
                        description "MDA ID for ISA NAT group";
                    }

                    leaf layer-2-hosts-bypassed {
                        type uint32;
                        description "number of Layer-2 aware NAT hosts being bypassed for this ISA MDA";
                    }

                    leaf oper-state {
                        type types-isa:nat-mda-operational-state;
                        description "the operational state of this NAT ISA MDA";
                    }

                    leaf allocated-resources {
                        type uint32 {
                            range "0..100";
                        }
                        description "the ratio of allocated resources to total resources on this NAT ISA MDA";
                    }

                    container statistics {
                        description "ISA statistics";

                        container nat {
                            description "NAT statistics per MDA";

                            container dropped {
                                description "NAT related drop counters";

                                container general {
                                    description "General drop reasons";

                                    leaf arp {
                                        type yang:counter64;
                                        description "ARP frames are ignored";
                                    }

                                    leaf checksum-calculation-error {
                                        type yang:counter64;
                                        description "Error while calculating L4 checksum before transmitting";
                                    }

                                    leaf send-error {
                                        type yang:counter64;
                                        description "Packet send error";
                                    }

                                    leaf no-copy-buffer {
                                        type yang:counter64;
                                        description "No buffer to copy frame";
                                    }

                                    leaf mtu-exceeded {
                                        type yang:counter64;
                                        description "Egress MTU exceeded";
                                    }

                                    leaf multicast {
                                        type yang:counter64;
                                        description "Multicast dropped";
                                    }

                                } // container general

                                container receive-errors {
                                    description "Errors in incoming frame format";

                                    leaf l2-error {
                                        type yang:counter64;
                                        description "L2 parse error";
                                    }

                                    leaf l3-not-ip {
                                        type yang:counter64;
                                        description "L3 is not IPv4 or IPv6";
                                    }

                                    leaf ip-invalid-checksum {
                                        type yang:counter64;
                                        description "IPv4 invalid checksum";
                                    }

                                    leaf ip-malformed-header {
                                        type yang:counter64;
                                        description "IP malformed header";
                                    }

                                    leaf ip-malformed-packet {
                                        type yang:counter64;
                                        description "IP malformed packet";
                                    }

                                    leaf ip-zero-ttl {
                                        type yang:counter64;
                                        description "IP zero ttl";
                                    }

                                    leaf ip-opts-or-ext-headers {
                                        type yang:counter64;
                                        description "IPv4 options or IPv6 extension headers";
                                    }

                                    leaf ip-parse-error {
                                        type yang:counter64;
                                        description "IP parse error";
                                    }

                                    leaf ipv6-fragments-unsupported {
                                        type yang:counter64;
                                        description "IPv6 fragments unsupported";
                                    }

                                    leaf ipv6-extension-header-parse-error {
                                        type yang:counter64;
                                        description "IPv6 extension headers parse error";
                                    }

                                    leaf dslite-unsupported-next-header {
                                        type yang:counter64;
                                        description "Dual-stack-lite next header unsupported";
                                    }

                                    leaf l4-unsupported-protocol {
                                        type yang:counter64;
                                        description "Unsupported L4 protocol";
                                    }

                                    leaf tcp-udp-malformed-header {
                                        type yang:counter64;
                                        description "TCP/UDP malformed header";
                                    }

                                    leaf tcp-udp-invalid-checksum {
                                        type yang:counter64;
                                        description "TCP/UDP invalid checksum";
                                    }

                                    leaf icmp-embedded-ipv6-extension-header-parse-error {
                                        type yang:counter64;
                                        description "ICMP embedded IPv6 extension header parse error";
                                    }

                                    leaf other-parse-error {
                                        type yang:counter64;
                                        description "Other parse error";
                                    }

                                } // container receive-errors

                                container flow {
                                    description "NAT flow drop reasons";

                                    leaf no-matching-flow {
                                        type yang:counter64;
                                        description "No matching flow";
                                    }

                                    leaf forwarding-blocked {
                                        type yang:counter64;
                                        description
                                            "Management core has blocked new flow creation or forwarding.
                                             Reasons include policies or port-blocks being released.";
                                    }

                                    leaf tcp-resetting {
                                        type yang:counter64;
                                        description "TCP flow is in reset state but not yet cleaned up";
                                    }

                                } // container flow

                                container flow-creation-failed {
                                    description "NAT flow could not be created";

                                    leaf no-resources {
                                        type yang:counter64;
                                        description "No resources";
                                    }

                                    leaf no-host-resources {
                                        type yang:counter64;
                                        description "Could not create host";
                                    }

                                    leaf no-ip-or-port-resources {
                                        type yang:counter64;
                                        description "Could not allocate ip or port-range";
                                    }

                                    leaf max-flows-exceeded {
                                        type yang:counter64;
                                        description "Max number of flows exceeded";
                                    }

                                    leaf ipv6-downstream-prohibited {
                                        type yang:counter64;
                                        description "IPv6 downstream traffic prohibited";
                                    }

                                    leaf address-dependent-filtering {
                                        type yang:counter64;
                                        description "Address dependent filtering";
                                    }

                                    leaf firewall-address-dependent-filtering {
                                        type yang:counter64;
                                        description "Firewall address dependent filtering";
                                    }

                                    leaf transient-no-policy {
                                        type yang:counter64;
                                        description "Policy could temporarily not be used";
                                    }

                                    leaf unmatched-policy {
                                        type yang:counter64;
                                        description "Matched policy not in use by subscriber";
                                    }

                                    leaf conflicting-policies {
                                        type yang:counter64;
                                        description "Conflicting policies";
                                    }

                                    leaf port-range-log-failed {
                                        type yang:counter64;
                                        description "Logging of port range allocation failed";
                                    }

                                    leaf flow-log-failed {
                                        type yang:counter64;
                                        description "Logging of flow creation failed";
                                    }

                                    leaf multiple-host-or-subscriber-ip {
                                        type yang:counter64;
                                        description "No multiple host or subscriber IPs allowed";
                                    }

                                    leaf destination-nat-destination-mismatch {
                                        type yang:counter64;
                                        description "Destination NAT destination IP mismatch";
                                    }

                                    leaf destination-nat-foreign-mismatch {
                                        type yang:counter64;
                                        description "Destination NAT foreign IP mismatch";
                                    }

                                    leaf ambiguous-flow-key {
                                        type yang:counter64;
                                        description "Ambiguous flow key";
                                    }

                                    leaf requested-port-not-in-host-range {
                                        type yang:counter64;
                                        description "Requested port not in host port range";
                                    }

                                    leaf destination-not-routable {
                                        type yang:counter64;
                                        description "Destination IP is not routable";
                                    }

                                    leaf dslite-unknown-aftr {
                                        type yang:counter64;
                                        description "Dual-stack-lite unknown AFTR address";
                                    }

                                    leaf pppoe-uplink-down {
                                        type yang:counter64;
                                        description "PPPoE uplink down";
                                    }

                                    leaf subscriber-id-unknown {
                                        type yang:counter64;
                                        description "Subscriber-id unknown";
                                    }

                                    leaf tcp-unexpected-rst {
                                        type yang:counter64;
                                        description "No flow creation on TCP RST";
                                    }

                                    leaf tcp-unexpected-fin {
                                        type yang:counter64;
                                        description "No flow creation on TCP FIN";
                                    }

                                    leaf tcp-unexpected-flags {
                                        type yang:counter64;
                                        description "No flow creation for invalid flags combinations";
                                    }

                                } // container flow-creation-failed

                                container icmp {
                                    description "ICMP";

                                    leaf unsupported-type-v4 {
                                        type yang:counter64;
                                        description "ICMP type unsupported";
                                    }

                                    leaf unsupported-type-v6 {
                                        type yang:counter64;
                                        description "ICMPv6 type unsupported";
                                    }

                                    leaf unsupported-type-for-translation {
                                        type yang:counter64;
                                        description "ICMP type unsupported for 4 to 6 translation";
                                    }

                                    leaf unsupported-length-for-translation {
                                        type yang:counter64;
                                        description "ICMP length error for 4 to 6 translation";
                                    }

                                    leaf unsupported-local {
                                        type yang:counter64;
                                        description "ICMP to l2aware-host gateway address unsupported";
                                    }

                                    leaf invalid-checksum {
                                        type yang:counter64;
                                        description "ICMP/ICMPv6 invalid checksum";
                                    }

                                    leaf embedded-invalid-checksum {
                                        type yang:counter64;
                                        description "ICMP invalid embedded IP checksum";
                                    }

                                    leaf unsupported-embedded-l3 {
                                        type yang:counter64;
                                        description "ICMP/ICMPv6 invalid embedded IP";
                                    }

                                    leaf unsupported-embedded-l4 {
                                        type yang:counter64;
                                        description "ICMP/ICMPv6 invalid embedded L4";
                                    }

                                    leaf too-short {
                                        type yang:counter64;
                                        description "ICMP/ICMPv6 too short";
                                    }

                                    leaf invalid-length {
                                        type yang:counter64;
                                        description "ICMP/ICMPv6 invalid length";
                                    }

                                    leaf fragmented {
                                        type yang:counter64;
                                        description "ICMP/ICMPv6 fragmentation";
                                    }

                                    leaf icmp6-packet-too-big {
                                        type yang:counter64;
                                        description "ICMP6 Packet-Too-Big with mtu < 1280";
                                    }

                                } // container icmp

                                container nat64 {
                                    description "NAT64";

                                    leaf disabled {
                                        type yang:counter64;
                                        description "NAT64 disabled";
                                    }

                                    leaf invalid-source-address {
                                        type yang:counter64;
                                        description "NAT64 invalid source address";
                                    }

                                    leaf fragment-zero-checksum {
                                        type yang:counter64;
                                        description "NAT64 fragment has zero checksum";
                                    }

                                    leaf ipv4-zero-checksum {
                                        type yang:counter64;
                                        description "NAT64 IPv4 zero checksum";
                                    }

                                    leaf icmp-fragment-unsupported {
                                        type yang:counter64;
                                        description "NAT64 ICMP fragments unsupported";
                                    }

                                    leaf unknown-next-header {
                                        type yang:counter64;
                                        description "NAT64 unknown next header";
                                    }

                                    leaf embedded-ipv4-options {
                                        type yang:counter64;
                                        description "NAT64 ICMP embedded IPv4 options";
                                    }

                                } // container nat64

                                container fragments {
                                    description "Fragments";

                                    leaf too-many-fragmented-packets {
                                        type yang:counter64;
                                        description "Too many fragmented packets";
                                    }

                                    leaf too-many-fragment-buffers {
                                        type yang:counter64;
                                        description "Fragmentation buffers exhausted";
                                    }

                                    leaf too-many-fragment-holes {
                                        type yang:counter64;
                                        description "Too many fragment holes";
                                    }

                                    leaf too-many-fragments-per-packet {
                                        type yang:counter64;
                                        description "Too many fragments for IP packet";
                                    }

                                    leaf too-many-fragment-lists-for-flow {
                                        type yang:counter64;
                                        description "Too many fragment lists for flow";
                                    }

                                    leaf fragment-list-expired {
                                        type yang:counter64;
                                        description "Fragment list expired";
                                    }

                                    leaf fragment-list-cleanup-in-progress {
                                        type yang:counter64;
                                        description "Fragment list cleanup in progress";
                                    }

                                    leaf reassembly-failed {
                                        type yang:counter64;
                                        description "Reassembly failed";
                                    }

                                } // container fragments

                                container radius {
                                    description "RADIUS";

                                    leaf error {
                                        type yang:counter64;
                                        description "Error while processing RADIUS packet";
                                    }

                                    leaf no-send-resources {
                                        type yang:counter64;
                                        description "No resources to send RADIUS packet";
                                    }

                                } // container radius

                                container upnp {
                                    description "UPnP";

                                    leaf ssdp {
                                        type yang:counter64;
                                        description "SSDP dropped";
                                    }

                                    leaf control {
                                        type yang:counter64;
                                        description "UPnP control dropped";
                                    }

                                } // container upnp

                                container service-chaining {
                                    description "Service-Chaining";

                                    leaf tx-error {
                                        type yang:counter64;
                                        description "Transmit error";
                                    }

                                    leaf rx-error {
                                        type yang:counter64;
                                        description "Receive error";
                                    }

                                    leaf rx-unsupported {
                                        type yang:counter64;
                                        description "Unhandled frames";
                                    }

                                    leaf filter-action-drop {
                                        type yang:counter64;
                                        description "Frames dropped by vas-filter";
                                    }

                                } // container service-chaining

                            } // container dropped

                            container flow {
                                description "NAT flow statistics";

                                leaf new-flow {
                                    type yang:counter64;
                                    description "New flow created";
                                }

                                leaf found-flow {
                                    type yang:counter64;
                                    description "Frame matched existing flow";
                                }

                                leaf tcp-closed {
                                    type yang:counter64;
                                    description "Flow terminated by TCP session close";
                                }

                                container timeouts {
                                    description "NAT flow timeouts";

                                    leaf tcp-expired {
                                        type yang:counter64;
                                        description "TCP flow expired";
                                    }

                                    leaf udp-expired {
                                        type yang:counter64;
                                        description "UDP flow expired";
                                    }

                                    leaf icmp-expired {
                                        type yang:counter64;
                                        description "ICMP/ICMPv6 flow expired";
                                    }

                                    leaf gre-expired {
                                        type yang:counter64;
                                        description "GRE flow expired";
                                    }

                                    leaf ipv6-any-l4-expired {
                                        type yang:counter64;
                                        description "Any IPv6 L4 flow expired";
                                    }

                                } // container timeouts

                            } // container flow

                            container icmp {
                                description "ICMP";

                                leaf to-local {
                                    type yang:counter64;
                                    description "ICMP to local address";
                                }

                            } // container icmp

                            container dslite {
                                description "Dual-Stack Lite";

                                leaf forward {
                                    type yang:counter64;
                                    description "IPv6 dual-stack-lite frame forwarded";
                                }

                            } // container dslite

                            container fragmentation {
                                description "Fragmentation";

                                leaf ipv6 {
                                    type yang:counter64;
                                    description "IPv6 frame was fragmented";
                                }

                            } // container fragmentation

                            container reassembly {
                                description "Reassembly";

                                leaf packets {
                                    type yang:counter64;
                                    description "Reassembled frames";
                                }

                            } // container reassembly

                            container flow-log {
                                description "Flow logging";

                                leaf logged-flow-create {
                                    type yang:counter64;
                                    description "Flow create logged";
                                }

                                leaf logged-flow-delete {
                                    type yang:counter64;
                                    description "Flow delete logged";
                                }

                                leaf tx-packet {
                                    type yang:counter64;
                                    description "Transmitted flow log frames";
                                }

                                leaf rate-limit-drop {
                                    type yang:counter64;
                                    description "Flow log frames dropped by rate limiting";
                                }

                            } // container flow-log

                            container radius {
                                description "RADIUS";

                                leaf to-local {
                                    type yang:counter64;
                                    description "Frame handled by local radius client";
                                }

                            } // container radius

                            container subscriber-id-cache {
                                description "Subscriber id cache";

                                leaf cached {
                                    type yang:counter64;
                                    description "Subscriber-id cached";
                                }

                                leaf delayed {
                                    type yang:counter64;
                                    description "Subscriber-id delayed";
                                }

                                leaf cache-timeout {
                                    type yang:counter64;
                                    description "Subscriber-id timeout";
                                }

                            } // container subscriber-id-cache

                            container fragments {
                                description "Fragments";

                                leaf rx-large-scale {
                                    type yang:counter64;
                                    description "Fragments received on large-scale nat interface";
                                }

                                leaf rx-dual-stack-lite {
                                    type yang:counter64;
                                    description "Fragments received on dual-stack-lite interface";
                                }

                                leaf rx-dormant {
                                    type yang:counter64;
                                    description "Fragments received on dormant interface";
                                }

                                leaf rx-l2aware {
                                    type yang:counter64;
                                    description "Fragments received on l2aware interface";
                                }

                                leaf rx-outside {
                                    type yang:counter64;
                                    description "Fragments received on outside interface";
                                }

                                leaf tx-large-scale {
                                    type yang:counter64;
                                    description "Fragments transmitted on large-scale nat interface";
                                }

                                leaf tx-dual-stack-lite {
                                    type yang:counter64;
                                    description "Fragments transmitted on dual-stack-lite interface";
                                }

                                leaf tx-dormant {
                                    type yang:counter64;
                                    description "Fragments transmitted on dormant interface";
                                }

                                leaf tx-l2aware {
                                    type yang:counter64;
                                    description "Fragments transmitted on l2aware interface";
                                }

                                leaf tx-nat64 {
                                    type yang:counter64;
                                    description "Fragments transmitted on nat64 interface";
                                }

                                leaf tx-outside {
                                    type yang:counter64;
                                    description "Fragments transmitted on outside interface";
                                }

                            } // container fragments

                            container upnp {
                                description "UPnP";

                                leaf ssdp-rx {
                                    type yang:counter64;
                                    description "SSDP frames received";
                                }

                                leaf ssdp-tx {
                                    type yang:counter64;
                                    description "SSDP frames transmitted";
                                }

                                leaf control-rx {
                                    type yang:counter64;
                                    description "UPnP control frames received";
                                }

                                leaf control-tx {
                                    type yang:counter64;
                                    description "UPnP control frames transmitted";
                                }

                                leaf rate-limited-request {
                                    type yang:counter64;
                                    description "UPnP query rate limited";
                                }

                                leaf pinhole-without-default-policy {
                                    type yang:counter64;
                                    description "Attempt to create pinhole without default policy";
                                }

                                leaf pinhole-without-source-nat {
                                    type yang:counter64;
                                    description "Attempt to create pinhole with source-nat disabled";
                                }

                            } // container upnp

                            container service-chaining {
                                description "Service-Chaining";

                                leaf rx {
                                    type yang:counter64;
                                    description "Service-chaining frames received";
                                }

                                leaf tx {
                                    type yang:counter64;
                                    description "Service-chaining frames transmitted";
                                }

                            } // container service-chaining

                        } // container nat

                        container ip-forwarding {
                            description "IP forwarding statistics per MDA";

                            leaf fragments {
                                type yang:counter64;
                                description "Fragments handled";
                            }

                            leaf reassembled-packets {
                                type yang:counter64;
                                description "Frames reassembled";
                            }

                            leaf forwarded-packets {
                                type yang:counter64;
                                description "Frames forwarded";
                            }

                            container receive-errors {
                                description "Receive errors";

                                leaf l2-error {
                                    type yang:counter64;
                                    description "L2 parse error";
                                }

                                leaf l3-not-ip {
                                    type yang:counter64;
                                    description "L3 is not IPv4 or IPv6";
                                }

                                leaf ip-invalid-checksum {
                                    type yang:counter64;
                                    description "IPv4 invalid checksum";
                                }

                                leaf ip-malformed-header {
                                    type yang:counter64;
                                    description "IP malformed header";
                                }

                                leaf ip-malformed-packet {
                                    type yang:counter64;
                                    description "IP malformed packet";
                                }

                                leaf ip-zero-ttl {
                                    type yang:counter64;
                                    description "IP zero ttl";
                                }

                                leaf ip-opts-or-ext-headers {
                                    type yang:counter64;
                                    description "IPv4 options or IPv6 extension headers";
                                }

                                leaf ip-fragment-unsupported {
                                    type yang:counter64;
                                    description "IP fragment unsupported";
                                }

                                leaf ip-error {
                                    type yang:counter64;
                                    description "IP parse error";
                                }

                                leaf tcp-udp-malformed-header {
                                    type yang:counter64;
                                    description "TCP/UDP malformed header";
                                }

                                leaf tcp-udp-invalid-checksum {
                                    type yang:counter64;
                                    description "TCP/UDP invalid checksum";
                                }

                                leaf other {
                                    type yang:counter64;
                                    description "Other parse error";
                                }

                            } // container receive-errors

                            container reassembly-errors {
                                description "Reassembly errors";

                                leaf too-many-fragmented-packets {
                                    type yang:counter64;
                                    description "Too many fragmented packets";
                                }

                                leaf too-many-fragment-buffers {
                                    type yang:counter64;
                                    description "Too many fragment buffers";
                                }

                                leaf too-many-fragment-holes {
                                    type yang:counter64;
                                    description "Too many fragment holes";
                                }

                                leaf fragment-filtered {
                                    type yang:counter64;
                                    description "Fragments filtered";
                                }

                                leaf fragment-not-supported {
                                    type yang:counter64;
                                    description "Fragment not supported";
                                }

                                leaf fragment-list-expired {
                                    type yang:counter64;
                                    description "Fragment list expired";
                                }

                                leaf fragment-list-cleanup-in-progress {
                                    type yang:counter64;
                                    description "Fragment list cleanup in progress";
                                }

                                leaf reassembly-failed {
                                    type yang:counter64;
                                    description "Reassembly failed";
                                }

                            } // container reassembly-errors

                        } // container ip-forwarding

                        container pppoe-client {
                            description "PPPoE-client statistics per MDA";

                            leaf rx-error-l2 {
                                type yang:counter64;
                                description "Number of packets received with layer 2 parse errors";
                            }

                            leaf rx-error-invalid-headers {
                                type yang:counter64;
                                description "Number of packets received with invalid PPPoE headers";
                            }

                            leaf rx-error-invalid-magic {
                                type yang:counter64;
                                description "Number of LCP echo-request or echo-reply packets received with an invalid magic number";
                            }

                            leaf rx-error-no-session {
                                type yang:counter64;
                                description "Number of LCP echo or data packets received without an associated session";
                            }

                            leaf rx-discovery {
                                type yang:counter64;
                                description "Number of PPPoE discovery packets received";
                            }

                            leaf rx-ppp-control {
                                type yang:counter64;
                                description "Number of PPP control packets received";
                            }

                            leaf rx-lcp-echo-request {
                                type yang:counter64;
                                description "Number of LCP echo-request packets received";
                            }

                            leaf rx-lcp-echo-reply {
                                type yang:counter64;
                                description "Number of LCP echo-reply packets received";
                            }

                            leaf tx-lcp-echo-request {
                                type yang:counter64;
                                description "Number of LCP echo-request packets transmitted";
                            }

                            leaf tx-lcp-echo-reply {
                                type yang:counter64;
                                description "Number of LCP echo-reply packets transmitted";
                            }

                        } // container pppoe-client

                    } // container statistics

                } // list mda

                list member {
                    key "id";
                    description "Information about a NAT group member";

                    leaf id {
                        type types-nat:bb-group-member;
                        description "Nat-group member identifier";
                    }

                    leaf state {
                        type enumeration {
                            enum "inactive"                     { value 1; }
                            enum "active"                       { value 2; }
                            enum "needs-reset"                  { value 3; }
                            enum "resetting"                    { value 4; }
                            enum "needs-reconcile"              { value 5; }
                            enum "reconciling"                  { value 6; }
                            enum "needs-audit"                  { value 7; }
                            enum "auditing"                     { value 8; }
                            enum "failed-bypass"                { value 9; }
                            enum "active-bypass"                { value 10; }
                        }
                        description "The state of the MDA associated with this member";
                    }

                    leaf associated-mda {
                        type types-isa:slot-mda;
                        description "MDA on which this member resides";
                    }

                    leaf reserved-outside-ip-addresses {
                        type yang:gauge32;
                        description "The number of outside IP addresses reserved for the MDA associated with this member";
                    }

                    leaf outside-port-blocks {
                        type yang:gauge32;
                        description "The number of outside port blocks reserved for the MDA associated with this member";
                    }

                    leaf session-usage {
                        type types-isa:nat-usage-level;
                        description "The session usage of the MDA associated with this member";
                    }

                    leaf high-session-usage {
                        type boolean;
                        description
                            "Indicates if the session usage of the MDA associated with this member is high
                             according to the values of watermark definitions";
                    }

                    leaf prioritized-sessions {
                        type yang:gauge32;
                        description "The current number of active prioritized sessions of the MDA associated with this member";
                    }

                    list resources {
                        key "resource";
                        description "Resource consumption per NAT group member";

                        leaf resource {
                            type uint32;
                            description "Resource that is monitored";
                        }

                        leaf description {
                            type string {
                                length "0..64";
                            }
                            description "The human-readable identifier of the resource.";
                        }

                        leaf value {
                            type yang:gauge64;
                            description "Actual consumed value";
                        }

                        leaf max {
                            type uint64;
                            description "The max value this resource can have, depending on the configuration";
                        }

                        leaf peak {
                            type yang:gauge64;
                            description "The peak value for the resource";
                        }

                        leaf peak-timestamp {
                            type types-sros:date-time;
                            description "The timestamp when the peak value was observed";
                        }

                    } // list resources

                } // list member

            } // list nat-group

            list wlan-gw-group {
                key "id";
                description "Enter the wlan-gw-group context";

                leaf id {
                    type types-isa:wlan-gw-group-id;
                    description "Unique value which to identify the WLAN-GW group within a chassis in system";
                }

                leaf oper-state {
                    type types-sros:oper-state;
                    description "Operational status of a WLAN-GW group";
                }

                leaf degraded {
                    type boolean;
                    description
                        "Indicates if the WLAN-GW group is degraded,
                         while operationally still in service.";
                }

                list iom {
                    key "slot-number";
                    description "Enter the iom context";

                    leaf slot-number {
                        type leafref {
                            path "../../../../card/slot-number";
                        }
                        description "IOM slot to use in the WLAN-GW group";
                    }

                    leaf oper-state {
                        type types-isa:wlan-gw-isa-iom-oper-state;
                        description "Operational status of a WLAN-GW group IOM";
                    }

                } // list iom

                list member {
                    key "id";
                    description "Statistics about a member of a WLAN-Gateway ISA Group";

                    leaf id {
                        type uint32;
                        description "Unique value which identifies the member within a WLAN-GW group";
                    }

                    leaf mda {
                        type types-isa:slot-mda;
                        description "Indicate the MDA associated with this member";
                    }

                    leaf num-tunnels {
                        type uint32;
                        description
                            "Number of tunnels processed by the MDA associated with this
                             member";
                    }

                    leaf num-ues {
                        type uint32;
                        description
                            "Number of UEs processed by the MDA associated with this
                             member";
                    }

                    leaf num-active-tunnel-shapers {
                        type uint32;
                        description
                            "Number of activated Tunnel Shapers associated with this ISA
                             group member";
                    }

                    leaf num-pending-tunnel-shapers {
                        type uint32;
                        description
                            "Number of pending Tunnel Shapers associated with this ISA group
                             member";
                    }

                    leaf num-failed-tunnel-shapers {
                        type uint32;
                        description
                            "Number of tunnel Qos infrastructure configuration instances on
                             the MDA associated with this ISA group member that have a
                             resource issue";
                    }

                    container statistics {

                        list packet-errors {
                            key "counter-id";
                            description "WLAN-GW packet counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list packet-errors

                        list host-errors {
                            key "counter-id";
                            description "WLAN-GW host counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list host-errors

                        list db-errors {
                            key "counter-id";
                            description "WLAN-GW db counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list db-errors

                        list forwarding {
                            key "counter-id";
                            description "WLAN-GW forwarding counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list forwarding

                        list reassembly {
                            key "counter-id";
                            description "WLAN-GW reassembly counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list reassembly

                        list aa {
                            key "counter-id";
                            description "WLAN-GW aa counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list aa

                        list radius {
                            key "counter-id";
                            description "WLAN-GW radius counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list radius

                        list arp {
                            key "counter-id";
                            description "WLAN-GW arp counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list arp

                        list dhcp4 {
                            key "counter-id";
                            description "WLAN-GW dhcp counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list dhcp4

                        list dhcp6 {
                            key "counter-id";
                            description "WLAN-GW dhcp6 counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list dhcp6

                        list icmp4 {
                            key "counter-id";
                            description "WLAN-GW icmp counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list icmp4

                        list icmp6 {
                            key "counter-id";
                            description "WLAN-GW icmp6 counters";

                            leaf counter-id {
                                type uint32;
                                description "The counter";
                            }

                            leaf description {
                                type string {
                                    length "0..64";
                                }
                                description "The human-readable identifier of the statistic.";
                            }

                            leaf value {
                                type yang:counter64;
                                description "The counter value";
                            }

                        } // list icmp6

                        container resources {
                            description "WLAN-GW resource counters";

                            container destinations {
                                description "WLAN-GW destinations, or group interfaces";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container destinations

                            container vlan-ranges {
                                description "Number of VLAN ranges";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container vlan-ranges

                            container ues {
                                description "Number of UEs";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container ues

                            container http-redirect-policies {
                                description "Number of HTTP redirect policies";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container http-redirect-policies

                            container filters {
                                description "Number of DSM filters";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container filters

                            container policers {
                                description "Number of ISA policers";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container policers

                            container mirrors {
                                description "Number of mirror destinations";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container mirrors

                            container slaac-subnets {
                                description "Number of SLAAC subnets for local address assignment";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container slaac-subnets

                            container dhcp6-subnets {
                                description "Number of DHCPv6 NA subnets for local address assignment";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container dhcp6-subnets

                            container dhcp-subnets {
                                description "Number of IPv4 subnets for local address assignment";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container dhcp-subnets

                            container xconnect-router-instances {
                                description "Number of router instances available to terminate cross-connect tunnels";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container xconnect-router-instances

                            container bridge-domains {
                                description "Number of vRGW bridged domains (BDs)";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container bridge-domains

                            container virtual-network-identifier {
                                description "Number of VNIs";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container virtual-network-identifier

                            container bridge-domain-filters {
                                description "Number of BD filters";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container bridge-domain-filters

                            container radius-proxy-servers {
                                description "Number of Radius Proxy Servers";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container radius-proxy-servers

                            container radius-proxy-contexts {
                                description "Number of in-progress radius proxy transactions";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container radius-proxy-contexts

                            container application-profiles {
                                description "Number of application profiles used for application assurance";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container application-profiles

                            container aa-ues {
                                description "Number of UEs with application assurance enabled";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container aa-ues

                            container fragment-lists {
                                description "Number of incomplete packets with unreceived fragments";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-lists

                            container fragment-holes {
                                description "Number of unreceived segments in incomplete packets";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-holes

                            container fragment-buffers {
                                description "Number of received fragments of incomplete packets";

                                leaf max {
                                    type yang:counter64;
                                    description "Maximum possible value of this resource";
                                }

                                leaf value {
                                    type yang:counter64;
                                    description "Actual value of this resource";
                                }

                                leaf peak {
                                    type yang:counter64;
                                    description "Peak value of this resource";
                                }

                                leaf peak-timestamp {
                                    type types-sros:date-time;
                                    description "The time the system reached the peak value of this resource";
                                }

                            } // container fragment-buffers

                        } // container resources

                    } // container statistics

                } // list member

            } // list wlan-gw-group

            list lns-group {
                key "id";
                description "Enter the lns-group context";

                leaf id {
                    type types-l2tp:lns-group-id;
                    description "Tunnel group ID";
                }

                leaf oper-state {
                    type types-sros:oper-state;
                    description "Operational state.";
                }

                list mda {
                    key "mda-id";
                    description "Enter the mda context";

                    leaf mda-id {
                        type types-isa:slot-mda;
                        description "MDA ID for the ISA LNS group";
                    }

                    leaf oper-state {
                        type types-l2tp:isa-mda-oper-state;
                        description "The operation state of the ISA MDA";
                    }

                    leaf sessions {
                        type yang:gauge32;
                        description "The number of sessions handled by the ISA MDA";
                    }

                    list statistics {
                        key "counter";
                        description "The statistics of an ISA LNS group MDA";

                        leaf counter {
                            type uint32 {
                                range "0..70";
                            }
                            description "The counter";
                        }

                        leaf description {
                            type string {
                                length "0..70";
                            }
                            description "The human-readable identifier of the statistic.";
                        }

                        leaf value {
                            type yang:counter64;
                            description "The counter value";
                        }

                    } // list statistics

                } // list mda

            } // list lns-group

            uses state-isa-video-group;
        } // container isa

    } // grouping state-isa

}
