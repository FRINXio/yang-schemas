submodule nokia-state-isa-video-group {

    yang-version "1.1";

    belongs-to nokia-state { prefix "state"; }

    import ietf-yang-types                { prefix "yang"; }
    import nokia-sros-yang-extensions     { prefix "sros-ext"; }
    import nokia-types-isa                { prefix "types-isa"; }
    import nokia-types-sros               { prefix "types-sros"; }


    sros-ext:sros-major-release "rel16";

    organization "Nokia";

    contact
        "Nokia SR OS Support
         Web: <http://www.nokia.com>";

    description
        "Nokia YANG Data model with operational state for ISA Video Group configuration on SR OS based routers.

         Copyright 2016 Nokia. All rights reserved. Reproduction of this document
         is authorized on the condition that the foregoing copyright notice is included.

         This nokia-state-isa-video-group YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-08-02";

    grouping state-isa-video-group {
        list video-group {
            key "video-group-id";
            description "Enter the video-group context";

            leaf video-group-id {
                type uint32 {
                    range "1..4";
                }
                description "Video group identifier";
            }

            leaf oper-state {
                type types-sros:oper-state;
                description "Oerational state of the ISA video group.";
            }

            list mda {
                key "mda-id";
                description "Enter the mda context";

                leaf mda-id {
                    type types-isa:slot-mda;
                    description "MDA identifier";
                }

                leaf admin-state {
                    type types-sros:admin-state;
                    description
                        "The value indicates the administrative
                         state of the video group on this MDA.";
                }

                leaf oper-state {
                    type types-sros:oper-state;
                    description
                        "The value indicates the current operational
                         state of the video group on this MDA.";
                }

                leaf used-memory {
                    type yang:gauge32;
                    units "bytes";
                    description
                        "The value indicates the amount of cache
                         being used by the video group for storing the video stream.";
                }

                leaf available-memory {
                    type yang:gauge32;
                    units "bytes";
                    description
                        "The value indicates the amount of
                         cache available on the MDA for storing the video stream.";
                }

                leaf channels {
                    type yang:gauge32;
                    description
                        "The value indicates the number of channels
                         being served on this MDA.";
                }

                leaf channel-alloc-fails {
                    type yang:counter32;
                    description
                        "The value indicates the number of
                         failed channel allocations on this MDA.";
                }

                leaf max-bw-exeeded {
                    type yang:counter32;
                    description
                        "The value indicates the number of times
                         maximum allowed bandwidth has been exceeded for each egress stream.";
                }

                leaf bw-in-use {
                    type yang:gauge32;
                    units "kilobps";
                    description
                        "The value indicates the total aggregate
                         bandwidth of the currently running egress streams.";
                }

                leaf active-rtcp-sessions {
                    type yang:gauge32;
                    description
                        "The value indicates the number
                         of active Real Time Transport Control Protocol (RTCP) sessions on
                         this MDA.";
                }

                leaf egress-stream-resets {
                    type yang:counter32;
                    description
                        "The value indicates the number of
                         egress stream resets on this MDA. An egress stream reset occurs when
                         there are no packets to transmit on the MDA.";
                }

                leaf ingress-steram-resets {
                    type yang:counter32;
                    description
                        "The value indicates the number of
                         ingress stream resets on this MDA. An ingress stream reset occurs when
                         the ingress stream stopped coming in for more than one second.";
                }

                leaf ads-stream-resets {
                    type yang:counter32;
                    description
                        "The value indicates the number of ad
                         stream resets on this MDA. An ad stream reset occurs when the ingress
                         ad stream stops.";
                }

                leaf ad-stream-aborts {
                    type yang:counter32;
                    description
                        "The value indicates the number of ad
                         stream aborts on this MDA. An ad stream abort could happen when an
                         egress reset happens.";
                }

                leaf ssr-collisions {
                    type yang:counter32;
                    description
                        "The value indicates the number of
                         synchronization source (SSRC) id collisions on this MDA.";
                }

                leaf rx-data-packets {
                    type yang:counter64;
                    description
                        "The value indicates the number of data
                         packets received on this MDA.";
                }

                leaf rx-data-packets-low-32 {
                    type yang:counter32;
                    description
                        "The value indicates the lower 32
                         bits of the value of tmnxVdoGrpMdaRxDataPackets.";
                }

                leaf rx-data-packets-high-32 {
                    type yang:counter32;
                    description
                        "The value indicates the higher 32
                         bits of the value of tmnxVdoGrpMdaRxDataPackets.";
                }

                leaf rx-data-octets {
                    type yang:counter64;
                    description
                        "The value indicates the number of data
                         octets received on this MDA.";
                }

                leaf rx-data-octets-low-32 {
                    type yang:counter32;
                    description
                        "The value indicates the lower 32
                         bits of the value of tmnxVdoGrpMdaRxDataOctets.";
                }

                leaf rx-data-octets-high-32 {
                    type yang:counter32;
                    description
                        "The value indicates the higher 32
                         bits of the value of tmnxVdoGrpMdaRxDataOctets.";
                }

                leaf rx-data-packet-errors {
                    type yang:counter64;
                    description
                        "The value indicates the number of
                         malformed or non-RTP (Real Time Transport Protocol) packets received
                         on this MDA.";
                }

                leaf rx-data-pkt-errs-low-32 {
                    type yang:counter32;
                    description
                        "The value indicates the lower 32
                         bits of the value of tmnxVdoGrpMdaRxDataPacketErrors.";
                }

                leaf rx-data-pkt-errs-high-32 {
                    type yang:counter32;
                    description
                        "The value indicates the higher 32
                         bits of the value of tmnxVdoGrpMdaRxDataPacketErrors.";
                }

                leaf tx-data-packets {
                    type yang:counter64;
                    description
                        "The value indicates the number of data
                         packets transmitted on this MDA.";
                }

                leaf tx-data-packets-low-32 {
                    type yang:counter32;
                    description
                        "The value indicates the lower 32
                         bits of the value of tmnxVdoGrpMdaTxDataPackets.";
                }

                leaf tx-data-packets-high-32 {
                    type yang:counter32;
                    description
                        "The value indicates the higher 32
                         bits of the value of tmnxVdoGrpMdaTxDataPackets.";
                }

                leaf tx-data-octets {
                    type yang:counter64;
                    description
                        "The value indicates the number of data
                         octets transmitted on this MDA.";
                }

                leaf tx-data-octets-low-32 {
                    type yang:counter32;
                    description
                        "The value indicates the lower 32
                         bits of the value of tmnxVdoGrpMdaTxDataOctets.";
                }

                leaf tx-data-octets-high-32 {
                    type yang:counter32;
                    description
                        "The value indicates the higher 32
                         bits of the value of tmnxVdoGrpMdaTxDataOctets.";
                }

                leaf tx-data-packet-errors {
                    type yang:counter64;
                    description
                        "The value indicates the number of
                         failed data packets due to lack of resources to be transmitted on
                         this MDA.";
                }

                leaf tx-data-pkt-errs-low-32 {
                    type yang:counter32;
                    description
                        "The value indicates the lower 32
                         bits of the value of tmnxVdoGrpMdaTxDataPacketErrors.";
                }

                leaf tx-data-pkt-errs-high-32 {
                    type yang:counter32;
                    description
                        "The value indicates the higher 32
                         bits of the value of tmnxVdoGrpMdaTxDataPacketErrors.";
                }

                leaf rtcp-perse-errors {
                    type yang:counter32;
                    description
                        "The value indicates the number of
                         Real-time Transport Control Protocol (RTCP) packet parsing errors on
                         this MDA.";
                }

                leaf rtcp-config-errors {
                    type yang:counter32;
                    description
                        "The value indicates the number of
                         Real-time Transport Control Protocol (RTCP) config errors on
                         this MDA. These errors occur when there is inconsistency between the
                         RTCP values and the configured values.";
                }

                leaf rtcp-ipc-errors {
                    type yang:counter32;
                    description
                        "The value indicates the number of
                         Real-time Transport Control Protocol (RTCP) inter-process communication
                         message processing errors on this MDA.";
                }

                leaf rtcp-sg-errors {
                    type yang:counter32;
                    description
                        "The value indicates the number of
                         Real-time Transport Control Protocol (RTCP) channel errors on
                         this MDA. These errors occur when a channel is not found for a given
                         interface to process RTCP packets.";
                }

                leaf rtcp-sub-errors {
                    type yang:counter32;
                    description
                        "The value indicates the number of
                         Real-time Transport Control Protocol (RTCP) subscriber parameter errors
                         on this MDA. These errors occur when the subscriber calculations
                         exceed the maximum allowed bandwidth.";
                }

                leaf rtcp-int-errors {
                    type yang:counter32;
                    description
                        "The value indicates the number of
                         Real-time Transport Control Protocol (RTCP) interface related errors
                         on this MDA.";
                }

                leaf tx-lost-packets {
                    type yang:counter32;
                    description
                        "The value indicates the number of
                         packets not found in the video MDA buffer for retransmission. When a
                         retransmission request arrives, packets are checked in the buffer and
                         if they are not found, the value of this object is incremented.";
                }

                leaf request-rtp-pkts {
                    type yang:counter32;
                    description
                        "The value indicates the number of
                         Real-time Transport Protocol (RTP) packets requested in the Real-time
                         Transport Control Protocol (RTCP) feedback (FB) messages received on
                         this MDA.";
                }

                leaf high-pkt-pool-limit-hit {
                    type yang:counter32;
                    description
                        "The value indicates the number of
                         times the high packet pool limit has been hit. A high value of this
                         object indicates potential failure in ingress packet storage.";
                }

                leaf malloc-failures {
                    type yang:counter32;
                    description
                        "The value indicates the number of
                         memory allocation failures on the management core of the video MDA.";
                }

                leaf dent-dropped-pkts {
                    type yang:counter32;
                    description
                        "The value indicates the number of
                         packets dropped by the video MDA due to denting.";
                }

                leaf bw-peak {
                    type yang:gauge32;
                    units "kilobps";
                    description
                        "The value indicates the maximum bandwidth
                         of the currently running egress streams since the last clear event.";
                }

                leaf cur-total-ret-bw {
                    type yang:gauge32;
                    units "kilobps";
                    description
                        "The value indicates the current total
                         Retransmission (RET) bandwidth in use.";
                }

                leaf peak-ret-bw {
                    type yang:gauge32;
                    units "kilobps";
                    description
                        "The value indicates the maximum
                         Retransmission (RET) bandwidth used since the last clear event.";
                }

                leaf cur-fcc-bw {
                    type yang:gauge32;
                    units "kilobps";
                    description
                        "The value indicates the current Fast Channel
                         Change (FCC) bandwidth in use.";
                }

                leaf fcc-drop-cnt-req {
                    type yang:gauge32;
                    description
                        "The value indicates the drop count
                         for the Fast Channel Change (FCC) requests due to reserved
                         Retransmission (RET) bandwidth.";
                }

                leaf mc-rtcp {
                    type yang:counter64;
                    description
                        "The value indicates the number of
                         multicast retransmissions done in response to Real Time Transport
                         Control Protocol (RTCP) requests.";
                }

                leaf mc-rtcp-low-32 {
                    type yang:counter32;
                    description
                        "The value indicates the lower 32
                         bits of the value of tmnxVdoGrpMdaMcRtcp.";
                }

                leaf mc-rtcp-high-32 {
                    type yang:counter32;
                    description
                        "The value indicates the higher 32
                         bits of the value of tmnxVdoGrpMdaMcRtcp.";
                }

                leaf mc-rudp {
                    type yang:counter64;
                    description
                        "The value indicates the number of
                         multicast retransmissions done in response to Reliable User Datagram
                         Protocol (RUDP) requests.";
                }

                leaf mc-rudp-low-32 {
                    type yang:counter32;
                    description
                        "The value indicates the lower 32
                         bits of the value of tmnxVdoGrpMdaMcRudp.";
                }

                leaf mc-rudp-high-32 {
                    type yang:counter32;
                    description
                        "The value indicates the higher 32
                         bits of the value of tmnxVdoGrpMdaMcRudp.";
                }

                leaf mc-ret-req-crt {
                    type yang:counter64;
                    description
                        "The value indicates the total number
                         of mcast retransmission requests created in response to the unicast
                         retransmission requests.";
                }

                leaf mc-ret-req-crt-low-32 {
                    type yang:counter32;
                    description
                        "The value indicates the lower 32
                         bits of the value of tmnxVdoGrpMdaMcRetReqCrt.";
                }

                leaf mc-ret-req-crt-high-32 {
                    type yang:counter32;
                    description
                        "The value indicates the higher 32
                         bits of the value of tmnxVdoGrpMdaMcRetReqCrt.";
                }

                leaf ret-req-qnc {
                    type yang:counter64;
                    description
                        "The value indicates the total
                         number of unicast retransmission requests queued with the mulicast
                         retransmission.";
                }

                leaf ret-req-qnc-low-32 {
                    type yang:counter32;
                    description
                        "The value indicates the lower 32
                         bits of the value of tmnxVdoGrpMdaRetReqQnc.";
                }

                leaf ret-req-qnc-high-32 {
                    type yang:counter32;
                    description
                        "The value indicates the higher 32
                         bits of the value of tmnxVdoGrpMdaRetReqQnc.";
                }

                leaf pkt-lost-in-seq-10 {
                    type yang:counter32;
                    description
                        "The value indicates the total number
                         of packets within sequences of 2 to 10 consecutive lost packets of the
                         video group on this MDA.";
                }

                leaf pkt-lost-in-seq-20 {
                    type yang:counter32;
                    description
                        "The value indicates the total number
                         of packets within sequences of 11 to 20 consecutive lost packets of the
                         video group on this MDA.";
                }

                leaf pkt-lost-in-seq-30 {
                    type yang:counter32;
                    description
                        "The value indicates the total number
                         of packets within sequences of 21 to 30 consecutive lost packets of the
                         video group on this MDA.";
                }

                leaf pkt-lost-in-seq-40 {
                    type yang:counter32;
                    description
                        "The value indicates the total number
                         of packets within sequences of 31 to 40 consecutive lost packets of the
                         video group on this MDA.";
                }

                leaf pkt-lost-in-seq-more {
                    type yang:counter32;
                    description
                        "The value indicates the total number
                         of packets within sequences of 41 or more consecutive lost packets of
                         the video group on this MDA.";
                }

                leaf peak-fcc-bw {
                    type yang:gauge32;
                    units "kilobps";
                    description
                        "The value indicates the peak value of
                         bandwidth for Fast Channel Change (FCC) requests since the last
                         reboot/clear.";
                }

                leaf peak-fcc-bw-time {
                    type yang:date-and-time;
                    description
                        "The value indicates the time (timestamp)
                         when tmnxVdoGrpMdaPeakFccBw occurred since the last reboot/clear.";
                }

                leaf peak-abs-ret-bw {
                    type yang:gauge32;
                    units "kilobps";
                    description
                        "The value indicates the absolute peak value of
                         bandwidth for Retransmission requests (RET) since the last reboot/clear.";
                }

                leaf peak-abs-ret-bw-time {
                    type yang:date-and-time;
                    description
                        "The value indicates the time (timestamp)
                         when tmnxVdoGrpMdaPeakAbsRetBw occurred since the last reboot/clear..";
                }

                leaf peak-fcc-session {
                    type yang:gauge32;
                    description
                        "The value indicates the peak number of
                         Fast Channel Change (FCC) sessions since the last reboot/clear.";
                }

                leaf peak-fcc-session-time {
                    type yang:date-and-time;
                    description
                        "The value indicates the time (timestamp)
                         when tmnxVdoGrpMdaPeakFccSession occurred since the last reboot/clear.";
                }

                leaf peak-ret-session {
                    type yang:gauge32;
                    description
                        "The value indicates the peak number of
                         Retransmission (RET) sessions since the last reboot/clear.";
                }

                leaf peak-ret-session-time {
                    type yang:date-and-time;
                    description
                        "The value indicates the time (timestamp)
                         when tmnxVdoGrpMdaPeakRetSession occurred since the last reboot/clear.";
                }

                leaf peak-fcc-ret-to-bw {
                    type yang:gauge32;
                    description
                        "The value indicates the total peak value
                         of bandwidth for Channel Change (FCC) and Retransmission (RET) requests
                         since the last reboot/clear.";
                }

                leaf peak-fcc-ret-tot-bw-time {
                    type yang:date-and-time;
                    description
                        "The value indicates the time (timestamp)
                         when tmnxVdoGrpMdaPeakFccRetTotBw occurred since the last reboot/clear.";
                }

                leaf peak-fcc-ret-to-sess {
                    type yang:gauge32;
                    description
                        "The value indicates the total peak number
                         of sessions for Fast Channel Change (FCC) and Retransmission (RET) since the last
                         reboot/clear.";
                }

                leaf peak-fcc-ret-tot-se-time {
                    type yang:date-and-time;
                    description
                        "The value indicates the time (timestamp)
                         when tmnxVdoGrpMdaPeakFccRetTotSess occurred since the last reboot/clear.";
                }

                leaf cur-abs-ret-bw {
                    type yang:gauge32;
                    units "kilobps";
                    description
                        "The value indicates the current Retransmission
                         (RET) bandwidth in use.";
                }

                leaf cur-fcc-ret-total-bw {
                    type yang:gauge32;
                    units "kilobps";
                    description
                        "The value indicates the current total
                         Fast Channel Change (FCC) and  Retransmission (RET) bandwidth in use.";
                }

                leaf act-fcc-sess {
                    type yang:gauge32;
                    description
                        "The value indicates the number of active
                         Real Time Transport Control Protocol (RTCP) sessions allocated for
                         Fast Channel Change (FCC) on this MDA.";
                }

                leaf act-ret-sess {
                    type yang:gauge32;
                    description
                        "The value indicates the number of active
                         Real Time Transport Control Protocol (RTCP) sessions allocated for
                         Retransmission (RET) on this MDA.";
                }

                leaf act-fcc-ret-total-sess {
                    type yang:gauge32;
                    description
                        "The value indicates the number of
                         active Real Time Transport Control Protocol (RTCP) sessions allocated
                         for Fast Channel Change (FCC) and Retransmission (RET) on this MDA.";
                }

            } // list mda

        } // list video-group

    } // grouping state-isa-video-group

}
