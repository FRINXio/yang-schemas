submodule nokia-state-log {

    yang-version "1.1";

    belongs-to nokia-state { prefix "state"; }

    import ietf-yang-types                { prefix "yang"; }
    import nokia-sros-yang-extensions     { prefix "sros-ext"; }
    import nokia-types-application-assurance { prefix "types-application-assurance"; }
    import nokia-types-card               { prefix "types-card"; }
    import nokia-types-log                { prefix "types-log"; }
    import nokia-types-services           { prefix "types-services"; }
    import nokia-types-sros               { prefix "types-sros"; }


    sros-ext:sros-major-release "rel16";

    organization "Nokia";

    contact
        "Nokia SR OS Support
         Web: <http://www.nokia.com>";

    description
        "Nokia YANG Data model with operational state for event stream logging on SR OS based routers.

         Copyright 2016 Nokia. All rights reserved. Reproduction of this document
         is authorized on the condition that the foregoing copyright notice is included.

         This nokia-state-log YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-07-05";

    grouping state-log {
        container log {
            description "Enter the log context";

            list accounting-policy {
                key "policy-id";
                description "Enter the accounting-policy context";

                leaf policy-id {
                    type types-log:log-policy-id;
                    description "Accounting policy unique ID";
                }

                leaf oper-state {
                    type types-sros:oper-state;
                    description
                        "The value of the this object indicates the operational
                         state of the accounting policy.";
                }

                leaf port-type {
                    type types-log:accounting-port-type;
                    description
                        "Indicates the type of facility associated with the specified
                         accounting policy's record type.";
                }

                leaf data-loss-count {
                    type yang:counter32;
                    description
                        "Indicates the number of times a log accounting data loss trap was
                         raised against this application policy.";
                }

                leaf last-data-loss-time {
                    type yang:date-and-time;
                    description
                        "Indicates the last time, since system startup that log accounting
                         data loss trap was raised against this application policy.";
                }

                container associations {
                    description "Specify log acounting-policy associations.";

                    list access {
                        key "service-name sap-id";
                        description "PortType access referencing the accounting-policy";

                        leaf service-name {
                            type types-sros:named-item-64;
                            description "Acc-policy is associated with service-name";
                        }

                        leaf sap-id {
                            type types-sros:sap;
                            description "Acc-policy is associated with the SAP ID.";
                        }

                    } // list access

                    list network {
                        key "port-id";
                        description "PortType network referencing the accounting-policy";

                        leaf port-id {
                            type types-sros:port;
                            description "The host port of the PXC.";
                        }

                    } // list network

                    list sdp {
                        key "sdp-id";
                        description "PortType sdp referencing the accounting-policy";

                        leaf sdp-id {
                            type types-services:sdp-id;
                            description "Service Distribution Point (SDP) identifier.";
                        }

                    } // list sdp

                    list sdp-bind {
                        key "service-name sdp-bind-id";
                        description "PortType sdp-bind referencing the accounting-policy";

                        leaf service-name {
                            type types-sros:named-item-64;
                            description "Acc-policy is associated with service-name";
                        }

                        leaf sdp-bind-id {
                            type types-services:sdp-bind-id;
                            description "Acc-policy is associated with the SDP ID.";
                        }

                    } // list sdp-bind

                    list subscriber {
                        key "profile-name";
                        description "PortType subscriber referencing the accounting-policy";

                        leaf profile-name {
                            type types-sros:named-item;
                            description "Acc-policy is associated with profile";
                        }

                    } // list subscriber

                    list aa-performance {
                        key "aa-assur-isa-group-id";
                        description "PortType appAssure for isa aa-performance port-name referencing the accounting-policy";

                        leaf aa-assur-isa-group-id {
                            type uint32;
                            description "Acc-policy is associated with the isa.";
                        }

                    } // list aa-performance

                    list application-assurance {
                        key "aa-group-id aa-partition-id category-name";
                        description "PortType appAssure referencing the accounting-policy";

                        leaf aa-group-id {
                            type types-application-assurance:isa-aa-grp-id;
                            description "Specifies an identfifer that uniquely identifies an AA group within the system.";
                        }

                        leaf aa-partition-id {
                            type types-application-assurance:aa-grp-part-id;
                            description "The identifier which uniquely identifies the partition within the parent AA group.";
                        }

                        leaf category-name {
                            type types-application-assurance:partition-stats-category;
                            description
                                "Specifiesan Identifier which uniquely identfies a statistics category
                                 within a AA partition";
                        }

                    } // list application-assurance

                    list qgrp-ingress {
                        key "port-id group-name";
                        description "Qgrp ingress referencing the accounting-policy";

                        leaf port-id {
                            type types-sros:port;
                            description "Acc-policy is associated with qgrp with port";
                        }

                        leaf group-name {
                            type types-sros:named-item;
                            description "Acc-policy is associated with qgrp with group name";
                        }

                        leaf mode {
                            type types-log:access-network;
                            description "Acc-policy is associated with qgrp with mode";
                        }

                    } // list qgrp-ingress

                    list qgrp-egress {
                        key "port-id group-name instance-id";
                        description "Qgrp egress referencing the accounting-policy";

                        leaf port-id {
                            type types-sros:port;
                            description "Acc-policy is associated with qgrp with port";
                        }

                        leaf group-name {
                            type types-sros:named-item;
                            description "Acc-policy is associated with qgrp with group name";
                        }

                        leaf instance-id {
                            type uint16 {
                                range "1..65535";
                            }
                            description "Specifies the instance identifier.";
                        }

                        leaf mode {
                            type types-log:access-network;
                            description "Acc-policy is associated with qgrp with mode";
                        }

                    } // list qgrp-egress

                    list qgrp-net-egress {
                        key "port-id group-name instance-id";
                        description "Qgrp net egress referencing the accounting-policy";

                        leaf port-id {
                            type types-sros:port;
                            description "Acc-policy is associated with qgrp with port";
                        }

                        leaf group-name {
                            type types-sros:named-item;
                            description "Acc-policy is associated with qgrp with group name";
                        }

                        leaf instance-id {
                            type uint16 {
                                range "1..65535";
                            }
                            description "Specifies the instance identifier.";
                        }

                        leaf mode {
                            type types-log:access-network;
                            description "Acc-policy is associated with qgrp with mode";
                        }

                    } // list qgrp-net-egress

                    list qgrp-card-acc {
                        key "slot-number fp-number group-name instance-id";
                        description "Qgrp card referencing the accounting-policy";

                        leaf slot-number {
                            type types-card:card-slot;
                            description "Acc-policy is associated with qgrp with cardId";
                        }

                        leaf fp-number {
                            type uint32;
                            description "Acc-policy is associated with qgrp with fp number.";
                        }

                        leaf group-name {
                            type types-sros:named-item;
                            description "Acc-policy is associated with qgrp with group name";
                        }

                        leaf instance-id {
                            type uint32;
                            description "Acc-policy is associated with qgrp with instance Id.";
                        }

                        leaf mode {
                            type types-log:access-network;
                            description "Acc-policy is associated with qgrp with mode";
                        }

                    } // list qgrp-card-acc

                    list qgrp-card-net {
                        key "slot-number fp-number group-name instance-id";
                        description "Qgrp card referencing the accounting-policy";

                        leaf slot-number {
                            type types-card:card-slot;
                            description "Acc-policy is associated with qgrp with cardId";
                        }

                        leaf fp-number {
                            type uint32;
                            description "Acc-policy is associated with qgrp with fp number.";
                        }

                        leaf group-name {
                            type types-sros:named-item;
                            description "Acc-policy is associated with qgrp with group name";
                        }

                        leaf instance-id {
                            type uint32;
                            description "Acc-policy is associated with qgrp with instance Id.";
                        }

                        leaf mode {
                            type types-log:access-network;
                            description "Acc-policy is associated with qgrp with mode";
                        }

                    } // list qgrp-card-net

                    list saa {
                        key "owner test";
                        description "Saa referencing the accounting-policy";

                        leaf owner {
                            type types-sros:named-item;
                            description "Acc-policy is associated with saa with owner name";
                        }

                        leaf test {
                            type types-sros:named-item;
                            description "Acc-policy is associated with saa with test name";
                        }

                    } // list saa

                    list ldp-lsp-egress {
                        key "router-instance fec-prefix";
                        description "Ldp lsp egress referencing the accounting-policy";

                        leaf router-instance {
                            type types-sros:named-item-64;
                            description
                                "The administrative name for this virtual router.

                                 The router name must be unique among all virtual routers in the system.";
                        }

                        leaf fec-prefix {
                            type types-sros:ip-prefix;
                            description "Configure ip-prefix.";
                        }

                    } // list ldp-lsp-egress

                    list mpls-lsp-ingress {
                        key "router-instance sender lsp-name";
                        description "Mpls lsp ingress referencing the accounting-policy";

                        leaf router-instance {
                            type types-sros:named-item-64;
                            description
                                "The administrative name for this virtual router.

                                 The router name must be unique among all virtual routers in the system.";
                        }

                        leaf sender {
                            type types-sros:ip-address;
                            description "Sender-address of mpls-lsp-ingress";
                        }

                        leaf lsp-name {
                            type types-sros:named-item-64;
                            description "Lsp-name for mpls";
                        }

                    } // list mpls-lsp-ingress

                    list mpls-lsp-egress {
                        key "router-instance lsp-name";
                        description "Mpls-lsp-egress referencing the accounting-policy";

                        leaf router-instance {
                            type types-sros:named-item-64;
                            description
                                "The administrative name for this virtual router.

                                 The router name must be unique among all virtual routers in the system.";
                        }

                        leaf lsp-name {
                            type types-sros:named-item-64;
                            description "Lsp-name for mpls";
                        }

                    } // list mpls-lsp-egress

                    list video {
                        key "service-name interface-name";
                        description "PortType video referencing the accounting-policy";

                        leaf service-name {
                            type types-sros:named-item-64;
                            description "Acc-policy is associated with service-name";
                        }

                        leaf interface-name {
                            type types-sros:interface-name {
                                length "1..29";
                            }
                            description "[29 chars max] (must start with a letter).";
                        }

                    } // list video

                    list ethernet {
                        key "port-id";
                        description "PortType ethernet referencing the accounting-policy";

                        leaf port-id {
                            type types-sros:port;
                            description "The host port of the PXC.";
                        }

                    } // list ethernet

                    list oam-pm {
                        key "session-name measurment-interval-duration";
                        description "PortType oam pm referencing the accounting-policy";

                        leaf session-name {
                            type types-sros:named-item;
                            description "Acc-policy is associated with oam pm with sesion name";
                        }

                        leaf measurment-interval-duration {
                            type types-log:measurment-interval-duration;
                            description "Acc-policy is associated with oam pm with measurment interval duration";
                        }

                    } // list oam-pm

                } // container associations

            } // list accounting-policy

            container log-events {
                description "Enter the log-events context";

                list adp {
                    key "event";
                    description "Enter the adp context";

                    leaf event {
                        type types-log:adp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list adp

                list application-assurance {
                    key "event";
                    description "Enter the application-assurance context";

                    leaf event {
                        type types-log:application-assurance-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list application-assurance

                list aps {
                    key "event";
                    description "Enter the aps context";

                    leaf event {
                        type types-log:aps-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list aps

                list atm {
                    key "event";
                    description "Enter the atm context";

                    leaf event {
                        type types-log:atm-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list atm

                list auto-prov {
                    key "event";
                    description "Enter the auto-prov context";

                    leaf event {
                        type types-log:auto-prov-events;
                        description "Events for auto-prov module.";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list auto-prov

                list bfd {
                    key "event";
                    description "Enter the bfd context";

                    leaf event {
                        type types-log:bfd-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list bfd

                list bgp {
                    key "event";
                    description "Enter the bgp context";

                    leaf event {
                        type types-log:bgp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list bgp

                list calltrace {
                    key "event";
                    description "Enter the calltrace context";

                    leaf event {
                        type types-log:calltrace-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list calltrace

                list cflowd {
                    key "event";
                    description "Enter the cflowd context";

                    leaf event {
                        type types-log:cflowd-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list cflowd

                list chassis {
                    key "event";
                    description "Enter the chassis context";

                    leaf event {
                        type types-log:chassis-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list chassis

                list debug {
                    key "event";
                    description "Enter the debug context";

                    leaf event {
                        type types-log:debug-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list debug

                list dhcp {
                    key "event";
                    description "Enter the dhcp context";

                    leaf event {
                        type types-log:dhcp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list dhcp

                list dhcps {
                    key "event";
                    description "Enter the dhcps context";

                    leaf event {
                        type types-log:dhcps-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list dhcps

                list diameter {
                    key "event";
                    description "Enter the diameter context";

                    leaf event {
                        type types-log:diameter-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list diameter

                list dynsvc {
                    key "event";
                    description "Enter the dynsvc context";

                    leaf event {
                        type types-log:dynsvc-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list dynsvc

                list efm-oam {
                    key "event";
                    description "Enter the efm-oam context";

                    leaf event {
                        type types-log:efm-oam-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list efm-oam

                list elmi {
                    key "event";
                    description "Enter the elmi context";

                    leaf event {
                        type types-log:elmi-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list elmi

                list ering {
                    key "event";
                    description "Enter the ering context";

                    leaf event {
                        type types-log:ethring-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ering

                list eth-cfm {
                    key "event";
                    description "Enter the eth-cfm context";

                    leaf event {
                        type types-log:ethcfm-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list eth-cfm

                list etun {
                    key "event";
                    description "Enter the etun context";

                    leaf event {
                        type types-log:etun-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list etun

                list filter {
                    key "event";
                    description "Enter the filter context";

                    leaf event {
                        type types-log:filter-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list filter

                list gmpls {
                    key "event";
                    description "Enter the gmpls context";

                    leaf event {
                        type types-log:gmpls-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list gmpls

                list gsmp {
                    key "event";
                    description "Enter the gsmp context";

                    leaf event {
                        type types-log:gsmp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list gsmp

                list igh {
                    key "event";
                    description "Enter the igh context";

                    leaf event {
                        type types-log:igh-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list igh

                list igmp {
                    key "event";
                    description "Enter the igmp context";

                    leaf event {
                        type types-log:igmp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list igmp

                list igmp-snooping {
                    key "event";
                    description "Enter the igmp-snooping context";

                    leaf event {
                        type types-log:igmp-snooping-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list igmp-snooping

                list ip {
                    key "event";
                    description "Enter the ip context";

                    leaf event {
                        type types-log:ip-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ip

                list ipsec {
                    key "event";
                    description "Enter the ipsec context";

                    leaf event {
                        type types-log:ipsec-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ipsec

                list isis {
                    key "event";
                    description "Enter the isis context";

                    leaf event {
                        type types-log:isis-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list isis

                list l2tp {
                    key "event";
                    description "Enter the l2tp context";

                    leaf event {
                        type types-log:l2tp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list l2tp

                list lag {
                    key "event";
                    description "Enter the lag context";

                    leaf event {
                        type types-log:lag-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list lag

                list ldap {
                    key "event";
                    description "Enter the ldap context";

                    leaf event {
                        type types-log:ldap-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ldap

                list ldp {
                    key "event";
                    description "Enter the ldp context";

                    leaf event {
                        type types-log:ldp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ldp

                list li {
                    key "event";
                    description "Enter the li context";

                    leaf event {
                        type types-log:li-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list li

                list lldp {
                    key "event";
                    description "Enter the lldp context";

                    leaf event {
                        type types-log:lldp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list lldp

                list lmp {
                    key "event";
                    description "Enter the lmp context";

                    leaf event {
                        type types-log:lmp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list lmp

                list logger {
                    key "event";
                    description "Enter the logger context";

                    leaf event {
                        type types-log:logger-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list logger

                list macsec {
                    key "event";
                    description "Enter the macsec context";

                    leaf event {
                        type types-log:macsec-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list macsec

                list mcpath {
                    key "event";
                    description "Enter the mcpath context";

                    leaf event {
                        type types-log:mcpath-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mcpath

                list mc-redundancy {
                    key "event";
                    description "Enter the mc-redundancy context";

                    leaf event {
                        type types-log:mc-redundancy-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mc-redundancy

                list mgmt-core {
                    key "event";
                    description "Enter the mgmt-core context";

                    leaf event {
                        type types-log:mgmt-core-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mgmt-core

                list mirror {
                    key "event";
                    description "Enter the mirror context";

                    leaf event {
                        type types-log:mirror-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mirror

                list mld {
                    key "event";
                    description "Enter the mld context";

                    leaf event {
                        type types-log:mld-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mld

                list mld-snooping {
                    key "event";
                    description "Enter the mld-snooping context";

                    leaf event {
                        type types-log:mld-snooping-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mld-snooping

                list mpls {
                    key "event";
                    description "Enter the mpls context";

                    leaf event {
                        type types-log:mpls-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mpls

                list mpls-tp {
                    key "event";
                    description "Enter the mpls-tp context";

                    leaf event {
                        type types-log:mpls-tp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list mpls-tp

                list msdp {
                    key "event";
                    description "Enter the msdp context";

                    leaf event {
                        type types-log:msdp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list msdp

                list nat {
                    key "event";
                    description "Enter the nat context";

                    leaf event {
                        type types-log:nat-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list nat

                list ntp {
                    key "event";
                    description "Enter the ntp context";

                    leaf event {
                        type types-log:ntp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ntp

                list oam {
                    key "event";
                    description "Enter the oam context";

                    leaf event {
                        type types-log:oam-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list oam

                list openflow {
                    key "event";
                    description "Enter the openflow context";

                    leaf event {
                        type types-log:openflow-events;
                        description "Events for openflow module.";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list openflow

                list ospf {
                    key "event";
                    description "Enter the ospf context";

                    leaf event {
                        type types-log:ospf-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ospf

                list pcap {
                    key "event";
                    description "Enter the pcap context";

                    leaf event {
                        type types-log:pcap-events;
                        description "Events for PCAP module";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list pcap

                list pim {
                    key "event";
                    description "Enter the pim context";

                    leaf event {
                        type types-log:pim-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list pim

                list pim-snooping {
                    key "event";
                    description "Enter the pim-snooping context";

                    leaf event {
                        type types-log:pim-snooping-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list pim-snooping

                list port {
                    key "event";
                    description "Enter the port context";

                    leaf event {
                        type types-log:port-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list port

                list ppp {
                    key "event";
                    description "Enter the ppp context";

                    leaf event {
                        type types-log:ppp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ppp

                list pppoe {
                    key "event";
                    description "Enter the pppoe context";

                    leaf event {
                        type types-log:pppoe-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list pppoe

                list pppoe-clnt {
                    key "event";
                    description "Enter the pppoe-clnt context";

                    leaf event {
                        type types-log:pppoe-clnt-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list pppoe-clnt

                list ptp {
                    key "event";
                    description "Enter the ptp context";

                    leaf event {
                        type types-log:ptp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ptp

                list radius {
                    key "event";
                    description "Enter the radius context";

                    leaf event {
                        type types-log:radius-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list radius

                list rip {
                    key "event";
                    description "Enter the rip context";

                    leaf event {
                        type types-log:rip-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list rip

                list ripng {
                    key "event";
                    description "Enter the ripng context";

                    leaf event {
                        type types-log:ripng-events;
                        description "Events for RIPng module.";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list ripng

                list route-policy {
                    key "event";
                    description "Enter the route-policy context";

                    leaf event {
                        type types-log:route-policy-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list route-policy

                list rpki {
                    key "event";
                    description "Enter the rpki context";

                    leaf event {
                        type types-log:rpki-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list rpki

                list rsvp {
                    key "event";
                    description "Enter the rsvp context";

                    leaf event {
                        type types-log:rsvp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list rsvp

                list satellite {
                    key "event";
                    description "Enter the satellite context";

                    leaf event {
                        type types-log:satellite-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list satellite

                list security {
                    key "event";
                    description "Enter the security context";

                    leaf event {
                        type types-log:security-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list security

                list sflow {
                    key "event";
                    description "Enter the sflow context";

                    leaf event {
                        type types-log:sflow-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list sflow

                list snmp {
                    key "event";
                    description "Enter the snmp context";

                    leaf event {
                        type types-log:snmp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list snmp

                list stp {
                    key "event";
                    description "Enter the stp context";

                    leaf event {
                        type types-log:stp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list stp

                list svcmgr {
                    key "event";
                    description "Enter the svcmgr context";

                    leaf event {
                        type types-log:svcmgr-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list svcmgr

                list system {
                    key "event";
                    description "Enter the system context";

                    leaf event {
                        type types-log:system-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list system

                list user {
                    key "event";
                    description "Enter the user context";

                    leaf event {
                        type types-log:user-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list user

                list video {
                    key "event";
                    description "Enter the video context";

                    leaf event {
                        type types-log:video-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list video

                list vrrp {
                    key "event";
                    description "Enter the vrrp context";

                    leaf event {
                        type types-log:vrrp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list vrrp

                list vrtr {
                    key "event";
                    description "Enter the vrtr context";

                    leaf event {
                        type types-log:vrtr-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list vrtr

                list wlan-gw {
                    key "event";
                    description "Enter the wlan-gw context";

                    leaf event {
                        type types-log:wlan-gw-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list wlan-gw

                list wpp {
                    key "event";
                    description "Enter the wpp context";

                    leaf event {
                        type types-log:wpp-events;
                        description "Specific log event as a trigger for one or more EHS handlers";
                    }

                    leaf event-id {
                        type types-log:log-event-id;
                        description
                            "Unique arbitrary identifier for indexing event type entries within
                             an event generator application.";
                    }

                    container statistics {
                        description "Event control statistics.";

                        leaf count {
                            type yang:counter32;
                            description "Number of times an event of this type has been generated.";
                        }

                        leaf drop {
                            type yang:counter32;
                            description "Indicates the number of times an event of this type has been dropped.";
                        }

                    } // container statistics

                } // list wpp

            } // container log-events

            container event-handling {
                description "Enter the event-handling context";

                list handler {
                    key "name";
                    description "Enter the handler context";

                    leaf name {
                        type types-sros:named-item;
                        description "File ID to use when creating a log, or accounting file";
                    }

                    leaf oper-state {
                        type types-sros:oper-state;
                        description "Indicates the operational state of the EHS Event Handler.";
                    }

                    list entry {
                        key "id";
                        description "Enter the entry context";

                        leaf id {
                            type uint32 {
                                range "1..1500";
                            }
                            description "Index of an event entry in parent EHS Event Handler";
                        }

                        leaf oper-state {
                            type types-sros:oper-state;
                            description "Indicates the operational state of the EHS Event Handler Entry.";
                        }

                        leaf last-data-loss-time {
                            type yang:date-and-time;
                            description "Indicates the time when handler entry launch execution of action.";
                        }

                    } // list entry

                } // list handler

            } // container event-handling

            container event-trigger {
                description "Enter the event-trigger context";

                list adp {
                    key "event";
                    description "Enter the adp context";

                    leaf event {
                        type types-log:adp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list adp

                list application-assurance {
                    key "event";
                    description "Enter the application-assurance context";

                    leaf event {
                        type types-log:application-assurance-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list application-assurance

                list aps {
                    key "event";
                    description "Enter the aps context";

                    leaf event {
                        type types-log:aps-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list aps

                list atm {
                    key "event";
                    description "Enter the atm context";

                    leaf event {
                        type types-log:atm-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list atm

                list auto-prov {
                    key "event";
                    description "Enter the auto-prov context";

                    leaf event {
                        type types-log:auto-prov-events;
                        description "Events for auto-prov module.";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list auto-prov

                list bfd {
                    key "event";
                    description "Enter the bfd context";

                    leaf event {
                        type types-log:bfd-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list bfd

                list bgp {
                    key "event";
                    description "Enter the bgp context";

                    leaf event {
                        type types-log:bgp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list bgp

                list calltrace {
                    key "event";
                    description "Enter the calltrace context";

                    leaf event {
                        type types-log:calltrace-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list calltrace

                list cflowd {
                    key "event";
                    description "Enter the cflowd context";

                    leaf event {
                        type types-log:cflowd-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list cflowd

                list chassis {
                    key "event";
                    description "Enter the chassis context";

                    leaf event {
                        type types-log:chassis-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list chassis

                list debug {
                    key "event";
                    description "Enter the debug context";

                    leaf event {
                        type types-log:debug-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list debug

                list dhcp {
                    key "event";
                    description "Enter the dhcp context";

                    leaf event {
                        type types-log:dhcp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list dhcp

                list dhcps {
                    key "event";
                    description "Enter the dhcps context";

                    leaf event {
                        type types-log:dhcps-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list dhcps

                list diameter {
                    key "event";
                    description "Enter the diameter context";

                    leaf event {
                        type types-log:diameter-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list diameter

                list dynsvc {
                    key "event";
                    description "Enter the dynsvc context";

                    leaf event {
                        type types-log:dynsvc-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list dynsvc

                list efm-oam {
                    key "event";
                    description "Enter the efm-oam context";

                    leaf event {
                        type types-log:efm-oam-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list efm-oam

                list elmi {
                    key "event";
                    description "Enter the elmi context";

                    leaf event {
                        type types-log:elmi-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list elmi

                list ering {
                    key "event";
                    description "Enter the ering context";

                    leaf event {
                        type types-log:ethring-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ering

                list eth-cfm {
                    key "event";
                    description "Enter the eth-cfm context";

                    leaf event {
                        type types-log:ethcfm-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list eth-cfm

                list etun {
                    key "event";
                    description "Enter the etun context";

                    leaf event {
                        type types-log:etun-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list etun

                list filter {
                    key "event";
                    description "Enter the filter context";

                    leaf event {
                        type types-log:filter-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list filter

                list gmpls {
                    key "event";
                    description "Enter the gmpls context";

                    leaf event {
                        type types-log:gmpls-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list gmpls

                list gsmp {
                    key "event";
                    description "Enter the gsmp context";

                    leaf event {
                        type types-log:gsmp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list gsmp

                list igh {
                    key "event";
                    description "Enter the igh context";

                    leaf event {
                        type types-log:igh-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list igh

                list igmp {
                    key "event";
                    description "Enter the igmp context";

                    leaf event {
                        type types-log:igmp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list igmp

                list igmp-snooping {
                    key "event";
                    description "Enter the igmp-snooping context";

                    leaf event {
                        type types-log:igmp-snooping-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list igmp-snooping

                list ip {
                    key "event";
                    description "Enter the ip context";

                    leaf event {
                        type types-log:ip-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ip

                list ipsec {
                    key "event";
                    description "Enter the ipsec context";

                    leaf event {
                        type types-log:ipsec-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ipsec

                list isis {
                    key "event";
                    description "Enter the isis context";

                    leaf event {
                        type types-log:isis-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list isis

                list l2tp {
                    key "event";
                    description "Enter the l2tp context";

                    leaf event {
                        type types-log:l2tp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list l2tp

                list lag {
                    key "event";
                    description "Enter the lag context";

                    leaf event {
                        type types-log:lag-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list lag

                list ldap {
                    key "event";
                    description "Enter the ldap context";

                    leaf event {
                        type types-log:ldap-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ldap

                list ldp {
                    key "event";
                    description "Enter the ldp context";

                    leaf event {
                        type types-log:ldp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ldp

                list li {
                    key "event";
                    description "Enter the li context";

                    leaf event {
                        type types-log:li-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list li

                list lldp {
                    key "event";
                    description "Enter the lldp context";

                    leaf event {
                        type types-log:lldp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list lldp

                list lmp {
                    key "event";
                    description "Enter the lmp context";

                    leaf event {
                        type types-log:lmp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list lmp

                list logger {
                    key "event";
                    description "Enter the logger context";

                    leaf event {
                        type types-log:logger-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list logger

                list macsec {
                    key "event";
                    description "Enter the macsec context";

                    leaf event {
                        type types-log:macsec-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list macsec

                list mcpath {
                    key "event";
                    description "Enter the mcpath context";

                    leaf event {
                        type types-log:mcpath-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mcpath

                list mc-redundancy {
                    key "event";
                    description "Enter the mc-redundancy context";

                    leaf event {
                        type types-log:mc-redundancy-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mc-redundancy

                list mgmt-core {
                    key "event";
                    description "Enter the mgmt-core context";

                    leaf event {
                        type types-log:mgmt-core-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mgmt-core

                list mirror {
                    key "event";
                    description "Enter the mirror context";

                    leaf event {
                        type types-log:mirror-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mirror

                list mld {
                    key "event";
                    description "Enter the mld context";

                    leaf event {
                        type types-log:mld-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mld

                list mld-snooping {
                    key "event";
                    description "Enter the mld-snooping context";

                    leaf event {
                        type types-log:mld-snooping-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mld-snooping

                list mpls {
                    key "event";
                    description "Enter the mpls context";

                    leaf event {
                        type types-log:mpls-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mpls

                list mpls-tp {
                    key "event";
                    description "Enter the mpls-tp context";

                    leaf event {
                        type types-log:mpls-tp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list mpls-tp

                list msdp {
                    key "event";
                    description "Enter the msdp context";

                    leaf event {
                        type types-log:msdp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list msdp

                list nat {
                    key "event";
                    description "Enter the nat context";

                    leaf event {
                        type types-log:nat-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list nat

                list ntp {
                    key "event";
                    description "Enter the ntp context";

                    leaf event {
                        type types-log:ntp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ntp

                list oam {
                    key "event";
                    description "Enter the oam context";

                    leaf event {
                        type types-log:oam-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list oam

                list openflow {
                    key "event";
                    description "Enter the openflow context";

                    leaf event {
                        type types-log:openflow-events;
                        description "Events for openflow module.";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list openflow

                list ospf {
                    key "event";
                    description "Enter the ospf context";

                    leaf event {
                        type types-log:ospf-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ospf

                list pcap {
                    key "event";
                    description "Enter the pcap context";

                    leaf event {
                        type types-log:pcap-events;
                        description "Events for PCAP module";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list pcap

                list pim {
                    key "event";
                    description "Enter the pim context";

                    leaf event {
                        type types-log:pim-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list pim

                list pim-snooping {
                    key "event";
                    description "Enter the pim-snooping context";

                    leaf event {
                        type types-log:pim-snooping-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list pim-snooping

                list port {
                    key "event";
                    description "Enter the port context";

                    leaf event {
                        type types-log:port-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list port

                list ppp {
                    key "event";
                    description "Enter the ppp context";

                    leaf event {
                        type types-log:ppp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ppp

                list pppoe {
                    key "event";
                    description "Enter the pppoe context";

                    leaf event {
                        type types-log:pppoe-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list pppoe

                list pppoe-clnt {
                    key "event";
                    description "Enter the pppoe-clnt context";

                    leaf event {
                        type types-log:pppoe-clnt-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list pppoe-clnt

                list ptp {
                    key "event";
                    description "Enter the ptp context";

                    leaf event {
                        type types-log:ptp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ptp

                list radius {
                    key "event";
                    description "Enter the radius context";

                    leaf event {
                        type types-log:radius-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list radius

                list rip {
                    key "event";
                    description "Enter the rip context";

                    leaf event {
                        type types-log:rip-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list rip

                list ripng {
                    key "event";
                    description "Enter the ripng context";

                    leaf event {
                        type types-log:ripng-events;
                        description "Events for RIPng module.";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list ripng

                list route-policy {
                    key "event";
                    description "Enter the route-policy context";

                    leaf event {
                        type types-log:route-policy-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list route-policy

                list rpki {
                    key "event";
                    description "Enter the rpki context";

                    leaf event {
                        type types-log:rpki-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list rpki

                list rsvp {
                    key "event";
                    description "Enter the rsvp context";

                    leaf event {
                        type types-log:rsvp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list rsvp

                list satellite {
                    key "event";
                    description "Enter the satellite context";

                    leaf event {
                        type types-log:satellite-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list satellite

                list security {
                    key "event";
                    description "Enter the security context";

                    leaf event {
                        type types-log:security-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list security

                list sflow {
                    key "event";
                    description "Enter the sflow context";

                    leaf event {
                        type types-log:sflow-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list sflow

                list snmp {
                    key "event";
                    description "Enter the snmp context";

                    leaf event {
                        type types-log:snmp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list snmp

                list stp {
                    key "event";
                    description "Enter the stp context";

                    leaf event {
                        type types-log:stp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list stp

                list svcmgr {
                    key "event";
                    description "Enter the svcmgr context";

                    leaf event {
                        type types-log:svcmgr-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list svcmgr

                list system {
                    key "event";
                    description "Enter the system context";

                    leaf event {
                        type types-log:system-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list system

                list user {
                    key "event";
                    description "Enter the user context";

                    leaf event {
                        type types-log:user-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list user

                list video {
                    key "event";
                    description "Enter the video context";

                    leaf event {
                        type types-log:video-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list video

                list vrrp {
                    key "event";
                    description "Enter the vrrp context";

                    leaf event {
                        type types-log:vrrp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list vrrp

                list vrtr {
                    key "event";
                    description "Enter the vrtr context";

                    leaf event {
                        type types-log:vrtr-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list vrtr

                list wlan-gw {
                    key "event";
                    description "Enter the wlan-gw context";

                    leaf event {
                        type types-log:wlan-gw-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list wlan-gw

                list wpp {
                    key "event";
                    description "Enter the wpp context";

                    leaf event {
                        type types-log:wpp-events;
                        description "Specific log event as a trigger for one or more EHS handlers";
                    }

                    leaf oper-state {
                        type types-sros:oper-state;
                        description "Indicates the operational state of the EHS Event Trigger.";
                    }

                    list entry {
                        key "id";
                        description "Enter the entry context";

                        leaf id {
                            type uint32 {
                                range "1..1500";
                            }
                            description "ID of a trigger entry in the parent EHS event trigger";
                        }

                        leaf oper-state {
                            type types-sros:oper-state;
                            description "Indicates the operational state of the EHS Event Trigger Entry.";
                        }

                    } // list entry

                } // list wpp

            } // container event-trigger

            list file {
                key "file-id";
                description "Enter the file context";

                leaf file-id {
                    type int32 {
                        range "1..99";
                    }
                    description "File ID when creating a log or accounting file";
                }

                leaf log-type {
                    type types-log:file-type;
                    description
                        "The value of log-type indicates the type of information
                         that will be written to this file.";
                }

                leaf used-by {
                    type int32 {
                        range "0..99";
                    }
                    description
                        "The value of log-id indicates the ID of the log or
                         accounting policy this file is attached to.

                         A value of zero (0)
                         indicates that this file definition is not currently used by any
                         log or accounting policy.";
                }

                leaf creation-time {
                    type yang:date-and-time;
                    description
                        "The value of creation-time is the time the currently opened
                         file version used by this file-id entry was created.

                         The value of creation-time is affected by the value of
                         stiPreferLocalTime.";
                }

                leaf current-file-name {
                    type string {
                        length "0..255";
                    }
                    description
                        "The value of path-name is the path name of the currently
                         opened file used by this file-id entry.

                         The value of path-name is affected by the value of
                         stiPreferLocalTime.";
                }

                leaf oper-location {
                    type types-log:compact-flash-drive;
                    description "Specify the location for a log file.";
                }

            } // list file

            list filter {
                key "filter-id";
                description "Enter the filter context";

                leaf filter-id {
                    type uint32 {
                        range "1..1500";
                    }
                    description "Identification number for an event log filter";
                }

                leaf applied {
                    type boolean;
                    description
                        "If 'true', this filter is attached to a log file configuration.
                         The same entry can be attached to more than one log file.";
                }

            } // list filter

            list log-id {
                key "id";
                description "Enter the log-id context";

                leaf id {
                    type int32 {
                        range "1..101";
                    }
                    description "The value of id uniquely identifies an event stream log.";
                }

                leaf oper-state {
                    type types-sros:oper-state;
                    description "Operational state.";
                }

                leaf wrapped {
                    type boolean;
                    description "The sequence-number for this log has wrapped.";
                }

                leaf next-event {
                    type yang:counter64;
                    description
                        "The value of the this object is the count of the number
                         of events that have been forwarded to this logs's destination.";
                }

                container statistics {
                    description "Log-id statistics.";

                    leaf logged-events {
                        type yang:counter64;
                        description
                            "The value of the this object is the count of the number
                             of events that have been forwarded to this logs's destination.";
                    }

                    leaf dropped-events {
                        type yang:counter64;
                        description
                            "The value of the this object is the count of the number
                             of events that have been sent to this logs source(s) and
                             that have not been forwarded to the log destination because
                             they were filtered out by the log filter.";
                    }

                } // container statistics

                list event {
                    key "sequence-number";
                    description
                        "Generated on any event that is generated in the system
                         that is not modeled by a more specific event.";

                    leaf sequence-number {
                        type uint64;
                        description
                            "A sequence number to indicate the ordering of log events in the log-id.
                             If the event is replayed, the sequence number is replayed as well.";
                    }

                    leaf time {
                        type yang:date-and-time;
                        description "Time when the event was generated.";
                    }

                    leaf severity {
                        type types-log:severity-level;
                        description "The severity level of the log event.";
                    }

                    leaf application {
                        type types-log:application;
                        description "The name of the application that reports the log event.";
                    }

                    leaf event-id {
                        type uint32 {
                            range "1..max";
                        }
                        description
                            "The id the event that was generated.
                             Each log event type has a unique identifying number.  This number is
                             unique within a particular software application, such as IP, MPLS,
                             OSPF, etc. but it is not necessarily unique across different software
                             applications.  That is MPLS event #1001 may be different from OSPF
                             event #1001.";
                    }

                    leaf event-name {
                        type types-sros:named-item;
                        description "The name of the log event that was generated.";
                    }

                    leaf vrtr-name {
                        type types-log:vrtr-name;
                        description "The router context name that generated the log event.";
                    }

                    leaf subject {
                        type string {
                            length "0..32";
                        }
                        description
                            "The router context name that generated the log event.
                             The subject is the entity that originated the event, such as the Port ID.";
                    }

                    leaf message {
                        type string {
                            length "1..4100";
                        }
                        description "The log event message.";
                    }

                } // list event

            } // list log-id

            list snmp-trap-group {
                key "log-id";
                description "Enter the snmp-trap-group context";

                leaf log-id {
                    type int32 {
                        range "1..100";
                    }
                    description "SNMP notification group associated with the event log";
                }

                list trap-target {
                    key "name";
                    description "Enter the trap-target context";

                    leaf name {
                        type string {
                            length "1..28";
                        }
                        description "Name for an SNMP notification destination within the SNMP notification group";
                    }

                    leaf replay-start-id {
                        type uint32;
                        description
                            "Indicates the SNMP notification request ID of the first event
                             that could not be generated because there is no route to this
                              notification target address.";
                    }

                    leaf last-replay-time {
                        type yang:date-and-time;
                        description
                            "Indicates the time when missed events were last replayed
                             to this SNMP notification target address.";
                    }

                } // list trap-target

            } // list snmp-trap-group

            list syslog {
                key "syslog-id";
                description "Enter the syslog context";

                leaf syslog-id {
                    type int32 {
                        range "1..10";
                    }
                    description "Unique arbitrary identifier for this SYSLOG collector target";
                }

                leaf below-severity-drops {
                    type yang:counter32;
                    description
                        "Identifies the count of messages not sent to this syslog collector
                         target because the severity level of the message was above the configured level.";
                }

            } // list syslog

            container cli-log-subscriptions {
                description "All CLI sessions in the system with an active cli-log subscription.";

                list cli-log-subscribed-session {
                    key "session-id";
                    description "The CLI session with one or more cli-log subscriptions.";

                    leaf session-id {
                        type uint32;
                        description "The id of the CLI session.";
                    }

                    leaf connection-type {
                        type enumeration {
                            enum "telnet"                       { value 1; }
                            enum "console"                      { value 2; }
                            enum "ssh"                          { value 4; }
                        }
                        description "The type of the connection used for the cli session.";
                    }

                    leaf connection-ip {
                        type types-sros:ip-address;
                        description "The remote IP address of the connection used for the cli session.";
                    }

                    leaf user {
                        type types-sros:named-item;
                        description "Name of the user.";
                    }

                    leaf login-time {
                        type yang:date-and-time;
                        description "The time the user logged in and created the CLI session.";
                    }

                    list subscription {
                        key "id";
                        description "The subscription with the log-id the CLI session is subscribed to in the Base router.";

                        leaf id {
                            type int32 {
                                range "1..101";
                            }
                            description "The value of id uniquely identifies an event stream log.";
                        }

                    } // list subscription

                } // list cli-log-subscribed-session

            } // container cli-log-subscriptions

        } // container log

    } // grouping state-log

}
