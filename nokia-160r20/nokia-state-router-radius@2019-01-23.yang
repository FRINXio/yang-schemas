submodule nokia-state-router-radius {

    yang-version "1.1";

    belongs-to nokia-state { prefix "state"; }

    import ietf-yang-types                { prefix "yang"; }
    import nokia-sros-yang-extensions     { prefix "sros-ext"; }
    import nokia-types-nat                { prefix "types-nat"; }
    import nokia-types-sros               { prefix "types-sros"; }


    sros-ext:sros-major-release "rel16";

    organization "Nokia";

    contact
        "Nokia SR OS Support
         Web: <http://www.nokia.com>";

    description
        "Nokia YANG Data model with operational state for RADIUS on SR OS based routers.

         Copyright 2016 Nokia. All rights reserved. Reproduction of this document
         is authorized on the condition that the foregoing copyright notice is included.

         This nokia-state-router-radius YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-01-23";

    grouping state-router-radius {
        container radius {
            description "Enter the radius context";

            list proxy {
                key "name";
                description "Enter the proxy context";

                leaf name {
                    type types-sros:named-item;
                    description "RADIUS proxy name";
                }

                container cache {
                    description "Enter the cache context";

                    leaf entries {
                        type yang:gauge32;
                        description "Number of entries in the cache of this RADIUS Proxy Server.";
                    }

                    leaf entries-registered {
                        type yang:gauge32;
                        description "Number of RADIUS Proxy Server entries that have been registered by an application";
                    }

                    list entry {
                        key "key";
                        description "Summary of a specific cache entry of a particular RADIUS Proxy Server.";

                        leaf key {
                            type binary {
                                length "1..64";
                            }
                            description "The key of this cache entry.";
                        }

                        leaf age {
                            type types-sros:time-interval;
                            description "The age of this cache entry.";
                        }

                        leaf time-left {
                            type types-sros:time-interval;
                            description "The time left for this cache entry.";
                        }

                        leaf request-length {
                            type uint32;
                            description "The length of the RADIUS Access-Request packet attribute(s) in the cache.";
                        }

                        leaf accept-length {
                            type uint32;
                            description "The length of the RADIUS Access-Accept packet attribute(s) in the cache.";
                        }

                        leaf registered {
                            type boolean;
                            description "Indicates if this cache entry is used by an application.";
                        }

                        leaf nas-address {
                            type types-sros:ipv4-address;
                            description "The NAS IPv4 address.";
                        }

                        leaf nas-ipv6-address {
                            type types-sros:ipv6-address;
                            description "The NAS IPv6 address.";
                        }

                        leaf called-station-id {
                            type binary {
                                length "0..64";
                            }
                            description "The Called-Station-Id in the RADIUS message.";
                        }

                    } // list entry

                } // container cache

                container statistics {
                    description "Received (RX) and Transmitted (TX) packets statistics.";

                    container rx {
                        description "RX statistics.";

                        leaf access-request {
                            type yang:counter32;
                            description "The number of Access-Request packets received by this RADIUS Proxy Server.";
                        }

                        leaf accounting-request {
                            type yang:counter32;
                            description "The number of Accounting-Request packets received by this RADIUS Proxy Server.";
                        }

                        leaf admin-down {
                            type yang:counter32;
                            description
                                "The number of packets received by this RADIUS Proxy Server
                                 that were rejected because it is administratively shut down.";
                        }

                        leaf dropped {
                            type yang:counter32;
                            description "The number of packets received by this RADIUS Proxy Server but rejected.";
                        }

                        leaf dropped-by-python {
                            type yang:counter32;
                            description "The number of packets received by this RADIUS Proxy Server but rejected by Python.";
                        }

                        leaf invalid-accounting-status {
                            type yang:counter32;
                            description
                                "The number of accounting packets received by this RADIUS Proxy Server that
                                 were rejected because they contained an invalid Acct-Status-Type attribute.";
                        }

                        leaf invalid-attribute {
                            type yang:counter32;
                            description
                                "The number of packets received by this RADIUS Proxy Server that were rejected
                                 because one of the attributes was incorrectly encoded.";
                        }

                        leaf invalid-authenticator {
                            type yang:counter32;
                            description
                                "The number of accounting packets received by this RADIUS Proxy Server that
                                 were rejected because they contained an invalid Authenticator field.";
                        }

                        leaf invalid-code {
                            type yang:counter32;
                            description
                                "The number of packets received by this RADIUS Proxy Server
                                 that were rejected because they had an invalid Code field.";
                        }

                        leaf invalid-length {
                            type yang:counter32;
                            description
                                "The number of packets received by this RADIUS Proxy Server
                                 that were rejected because their length was invalid.";
                        }

                        leaf invalid-message-authenticator {
                            type yang:counter32;
                            description
                                "The number of packets received by this RADIUS Proxy Server that were rejected
                                 because they contained an invalid Message-Authenticator attribute.";
                        }

                        leaf invalid-password {
                            type yang:counter32;
                            description
                                "The number of packets received by this RADIUS Proxy Server that were rejected
                                 because the User-Password attribute could not be decoded.";
                        }

                        leaf invalid-user-name {
                            type yang:counter32;
                            description
                                "The number of packets received by this RADIUS Proxy Server that were rejected
                                 because they contained an invalid User-Name attribute.";
                        }

                        leaf aaa-policy-missing {
                            type yang:counter32;
                            description
                                "The number of packets received by this RADIUS Proxy Server that were rejected
                                 because it has no RADIUS server policy configured for that type of packet.";
                        }

                        leaf accounting-status-missing {
                            type yang:counter32;
                            description
                                "The number of accounting packets received by this RADIUS Proxy Server that
                                 were rejected because they contained no Acct-Status-Type attribute.";
                        }

                        leaf load-balance-key-missing {
                            type yang:counter32;
                            description
                                "The number of packets received by this RADIUS Proxy Server that were rejected
                                 because the selected RADIUS server policy's algorithm is set to 'hash-based'
                                 and no load-balance-key is configured.";
                        }

                        leaf out-of-memory {
                            type yang:counter32;
                            description
                                "The number of packets that were rejected by this RADIUS Proxy Server
                                 because there was not enough memory to store them.";
                        }

                        leaf packets {
                            type yang:counter32;
                            description "The number of packets received by this RADIUS Proxy Server.";
                        }

                        leaf retransmit {
                            type yang:counter32;
                            description
                                "The number of packets received by this RADIUS Proxy Server
                                 that were rejected because they are retransmits.";
                        }

                        leaf user-overload {
                            type yang:counter32;
                            description
                                "The number of packets that were rejected by this RADIUS server
                                 because the registered user indicated to be in overload.";
                        }

                    } // container rx

                    container tx {
                        description "TX statistics.";

                        leaf access-accept {
                            type yang:counter32;
                            description "The number of Access-Accept packets transmitted by this RADIUS Proxy Server.";
                        }

                        leaf access-reject {
                            type yang:counter32;
                            description "The number of Access-Reject packets transmitted by this RADIUS Proxy Server.";
                        }

                        leaf access-challenge {
                            type yang:counter32;
                            description "The number of Access-Challenge packets transmitted by this RADIUS Proxy Server.";
                        }

                        leaf accounting-response {
                            type yang:counter32;
                            description "The number of Accounting-Response packets transmitted by this RADIUS Proxy Server.";
                        }

                        leaf client-dropped-authentication {
                            type yang:counter32;
                            description
                                "The number of packets that were dropped by a client registered for
                                 authentication packets.";
                        }

                        leaf dropped {
                            type yang:counter32;
                            description "The number of packets dropped by this RADIUS Proxy Server before transmission.";
                        }

                        leaf dropped-by-python {
                            type yang:counter32;
                            description
                                "The number of packets that were dropped by this RADIUS server
                                 because the packet was rejected by the Python script.";
                        }

                        leaf out-of-memory {
                            type yang:counter32;
                            description
                                "The number of packets that could not be transmitted by this RADIUS Proxy Server
                                 because there was not enough memory.";
                        }

                        leaf radius-server-missing {
                            type yang:counter32;
                            description
                                "The number of packets that were dropped by this RADIUS server because
                                 the RADIUS server policy has no servers configured.";
                        }

                        leaf send-failure {
                            type yang:counter32;
                            description
                                "The number of packets that were dropped by this RADIUS server because the packet
                                 could not get transmitted by one of the servers in the RADIUS server policy.";
                        }

                        leaf server-authenticator-fail {
                            type yang:counter32;
                            description
                                "The number of client packets that were dropped because the RADIUS server replied
                                 with a packet which failed authentication (invalid response Authenticator
                                 or Message-Authenticator attribute).";
                        }

                        leaf server-invalid-attribute {
                            type yang:counter32;
                            description
                                "The number of client packets that were dropped because the RADIUS server
                                 replied with a packet with an invalid attribute.";
                        }

                        leaf server-invalid-code {
                            type yang:counter32;
                            description
                                "The number of client packets that were dropped because the RADIUS server
                                 replied with a packet with an invalid Code field.";
                        }

                        leaf server-timeout {
                            type yang:counter32;
                            description
                                "The number of client packets that were dropped because the RADIUS servers have
                                 timed out.";
                        }

                        leaf user-overload {
                            type yang:counter32;
                            description
                                "The number of packets that were dropped because the registered
                                 user indicated to be in overload.";
                        }

                        container cache {
                            description "Cache statistics.";

                            leaf attribute-too-long {
                                type yang:counter32;
                                description
                                    "The number of packets that could not be cached by this RADIUS Proxy Server
                                     because the total length of the attributes is too long.";
                            }

                            leaf key-too-long {
                                type yang:counter32;
                                description
                                    "The number of packets that could not be cached by this RADIUS Proxy Server
                                     because the key information present in the packet was too long.";
                            }

                            leaf max-entries {
                                type yang:counter32;
                                description
                                    "The number of packets that could not be cached by this RADIUS Proxy Server
                                     because the limit has been reached.";
                            }

                            leaf key-missing {
                                type yang:counter32;
                                description
                                    "The number of packets that could not be cached by this RADIUS Proxy Server
                                     because the key information was not present in the packet.";
                            }

                        } // container cache

                    } // container tx

                    list group-member {
                        key "group-id member-id";
                        description "Per ISA member statistics for a distributed RADIUS Proxy Server.";

                        leaf group-id {
                            type uint32;
                            description "The identifier of the ISA group.";
                        }

                        leaf member-id {
                            type types-nat:bb-group-member;
                            description "The identifier of the ISA Group member.";
                        }

                        container rx {
                            description "RX statistics.";

                            leaf aaa-policy-missing {
                                type yang:counter32;
                                description
                                    "The number of packets received by this RADIUS Proxy Server that were rejected
                                     because it has no ISA RADIUS server policy configured for that type of packet.";
                            }

                            leaf access-request {
                                type yang:counter32;
                                description "The number of Access-Request packets received by this RADIUS Proxy Server.";
                            }

                            leaf accounting-request {
                                type yang:counter32;
                                description "The number of Accounting-Request packets received by this RADIUS Proxy Server.";
                            }

                            leaf accounting-status-missing {
                                type yang:counter32;
                                description
                                    "The number of accounting packets received by this RADIUS Proxy Server that
                                     were rejected because they contained no Acct-Status-Type attribute.";
                            }

                            leaf context-limit-reached {
                                type yang:counter32;
                                description
                                    "The number of packets received by this RADIUS Proxy Server that were rejected
                                     because the limit of client contexts was reached.";
                            }

                            leaf dropped {
                                type yang:counter32;
                                description "The number of packets received by this RADIUS Proxy Server but dropped.";
                            }

                            leaf invalid-accounting-status {
                                type yang:counter32;
                                description
                                    "The number of accounting packets received by this RADIUS Proxy Server that
                                     were rejected because they contained an invalid Acct-Status-Type attribute.";
                            }

                            leaf invalid-attribute {
                                type yang:counter32;
                                description
                                    "The number of packets received by this RADIUS Proxy Server that were rejected
                                     because one of the attributes was incorrectly encoded.";
                            }

                            leaf invalid-authenticator {
                                type yang:counter32;
                                description
                                    "The number of accounting packets received by this RADIUS Proxy Server that
                                     were rejected because they contained an invalid Authenticator field.";
                            }

                            leaf invalid-message-authenticator {
                                type yang:counter32;
                                description
                                    "The number of packets received by this RADIUS Proxy Server that were rejected
                                     because they contained an invalid Message-Authenticator attribute.";
                            }

                            leaf invalid-password {
                                type yang:counter32;
                                description
                                    "The number of packets received by this RADIUS Proxy Server that were rejected
                                     because the User-Password attribute could not be decoded.";
                            }

                            leaf management-overload {
                                type yang:counter32;
                                description
                                    "The number of packets that were rejected by this RADIUS server
                                     because the ISA management core is not able to process any
                                     new RADIUS requests due to overload.";
                            }

                            leaf packets {
                                type yang:counter32;
                                description "The number of packets received by this RADIUS Proxy Server.";
                            }

                            leaf retransmit {
                                type yang:counter32;
                                description
                                    "The number of packets received by this RADIUS Proxy Server
                                     that were rejected because they are retransmitted.";
                            }

                            leaf ue-mac-missing {
                                type yang:counter32;
                                description
                                    "The number of packets received by this RADIUS Proxy Server that were rejected
                                     because the UE MAC address was not present in the packet.";
                            }

                            leaf wrong-purpose {
                                type yang:counter32;
                                description
                                    "The number of packets received by this RADIUS Proxy Server that were rejected
                                     because the value configured is not matching the type of packet.";
                            }

                        } // container rx

                        container tx {
                            description "TX statistics.";

                            leaf access-accept {
                                type yang:counter32;
                                description "The number of Access-Accept packets transmitted by this RADIUS Proxy Server.";
                            }

                            leaf access-reject {
                                type yang:counter32;
                                description "The number of Access-Reject packets transmitted by this RADIUS Proxy Server.";
                            }

                            leaf access-challenge {
                                type yang:counter32;
                                description "The number of Access-Challenge packets transmitted by this RADIUS Proxy Server.";
                            }

                            leaf accounting-response {
                                type yang:counter32;
                                description "The number of Accounting-Response packets transmitted by this RADIUS Proxy Server.";
                            }

                            leaf dropped {
                                type yang:counter32;
                                description "The number of packets dropped by this RADIUS Proxy Server before transmission.";
                            }

                            leaf send-failure {
                                type yang:counter32;
                                description
                                    "The number of packets that were dropped by this RADIUS server because the packet
                                     could not get transmitted to one of the servers in the ISA RADIUS server policy.";
                            }

                            leaf server-authenticator-fail {
                                type yang:counter32;
                                description
                                    "The number of client packets that were dropped because the RADIUS server replied
                                     with a packet with an invalid response Authenticator.";
                            }

                            leaf server-invalid-attribute {
                                type yang:counter32;
                                description
                                    "The number of client packets that were dropped because the RADIUS server
                                     replied with a packet with an invalid attribute.";
                            }

                            leaf server-message-authenticator-fail {
                                type yang:counter32;
                                description
                                    "The number of client packets that were dropped because the RADIUS server replied
                                     with a packet with an invalid Message-Authenticator attribute.";
                            }

                            leaf server-timeout {
                                type yang:counter32;
                                description
                                    "The number of client packets that were dropped because the RADIUS servers have
                                     timed out.";
                            }

                        } // container tx

                    } // list group-member

                } // container statistics

            } // list proxy

        } // container radius

    } // grouping state-router-radius

}
