module nokia-types-isa {

    yang-version "1.1";

    namespace "urn:nokia.com:sros:ns:yang:sr:types-isa";

    prefix "types-isa";

    import ietf-yang-types                { prefix "yang"; }
    import nokia-sros-yang-extensions     { prefix "sros-ext"; }


    sros-ext:sros-major-release "rel16";

    organization "Nokia";

    contact
        "Nokia SR OS Support
         Web: <http://www.nokia.com>";

    description
        "Common card types data types used in the SR OS management system.

         Copyright 2016 Nokia. All rights reserved. Reproduction of this document
         is authorized on the condition that the foregoing copyright notice is included.

         This nokia-types-isa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-07-10";

    typedef slot-mda {
        type string;
        description "An I/O Module (IOM) card slot.";
    }

    typedef wlan-gw-group-id {
        type uint32 {
            range "1..4";
        }
        description "The identification number for a WLAN-GW ISA group";
    }

    typedef wlan-gw-isa-iom-oper-state {
        type enumeration {
            enum "unavailable"                  { value 0; }
            enum "primary"                      { value 1; }
            enum "backup"                       { value 2; }
            enum "busy"                         { value 3; }
        }
        description "Operational state of a WLAN-GW ISA or IOM";
    }

    typedef wlan-gw-watermark-entity {
        type enumeration {
            enum "user-equipment"               { value 1; }
            enum "bridge-domain"                { value 2; }
            enum "radius-proxy-client"          { value 3; }
        }
        description "The entity whose usage is monitored";
    }

    typedef nat-usage-level {
        type yang:gauge32 {
            range "0..100";
        }
        description " an unsigned number that indicates a usage level in percent";
    }

    typedef nat-mda-operational-state {
        type enumeration {
            enum "unavail"                      { value 0; }
            enum "primary"                      { value 1; }
            enum "backup"                       { value 2; }
            enum "busy"                         { value 3; }
        }
        description
            "an enumerated  that indicates the operational state
             of a NAT ISA MDA within a NAT ISA group";
    }

}
