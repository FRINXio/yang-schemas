submodule nokia-state-system-security {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-router             { prefix "types-router"; }
    import nokia-types-services           { prefix "types-services"; }
    import nokia-types-sros               { prefix "types-sros"; }
    import nokia-types-system             { prefix "types-system"; }

    include nokia-state-system-security-aaa;
    include nokia-state-system-security-cpm;
    include nokia-state-system-security-management-access-filter;
    include nokia-state-system-security-pki;
    include nokia-state-system-security-ssh;
    include nokia-state-system-security-tls;
    include nokia-state-system-security-user-parameters;

    sros-ext:sros-major-release "rel16";

    organization "Nokia";

    contact
        "Nokia SR OS Support
         Web: <http://www.nokia.com>";

    description
        "Nokia YANG Data model with operational state for system security parameters. on SR OS based routers.

         Copyright 2016 Nokia. All rights reserved. Reproduction of this document
         is authorized on the condition that the foregoing copyright notice is included.

         This nokia-state-system-security YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-01-18";

    grouping state-system-security {
        container security {
            description "Enter the security context";

            leaf telnet-server-oper-state {
                type types-sros:oper-state;
                description "Indicates the operational status of the telnet server.";
            }

            leaf ftp-server-oper-state {
                type types-sros:oper-state;
                description "Indicates the operational status of the FTP server.";
            }

            leaf telnet6-server-oper-state {
                type types-sros:oper-state;
                description "Indicates the operational status of the IPv6 telnet server.";
            }

            container cpu-protection {
                description "Enter the cpu-protection context";

                container violators {
                    description "Information about where the cpu protection rules are violated";

                    container interfaces {
                        description "Information about interfaces where the cpu protection rules are violated";

                        container overall-rate {
                            description "Interfaces where the protection policy overall rate limit is violated";

                            list interface {
                                key "vrtr-id if-index";
                                description "Interface where the protection policy overall rate limit is violated";

                                leaf vrtr-id {
                                    type int32;
                                    description "The virtual router index.";
                                }

                                leaf if-index {
                                    type int32;
                                    description "The interface index.";
                                }

                                leaf service-name {
                                    type types-services:service-name;
                                    description
                                        "The name of the service containing the interface.
                                         This is only applicable for a service interface.";
                                }

                                leaf interface-type {
                                    type types-router:interface-type;
                                    description "The type of interface.";
                                }

                                leaf interface-name {
                                    type types-sros:interface-name;
                                    description "The name of the interface.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list interface

                        } // container overall-rate

                        container out-of-profile-rate {
                            description "Interfaces where the protection policy out-of-profile rate limit is violated";

                            list interface {
                                key "vrtr-id if-index";
                                description "Interface where the protection policy out-of-profile rate limit is violated";

                                leaf vrtr-id {
                                    type int32;
                                    description "The virtual router index.";
                                }

                                leaf if-index {
                                    type int32;
                                    description "The interface index.";
                                }

                                leaf service-name {
                                    type types-services:service-name;
                                    description
                                        "The name of the service containing the interface.
                                         This is only applicable for a service interface.";
                                }

                                leaf interface-type {
                                    type types-router:interface-type;
                                    description "The type of interface.";
                                }

                                leaf interface-name {
                                    type types-sros:interface-name;
                                    description "The name of the interface.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list interface

                        } // container out-of-profile-rate

                    } // container interfaces

                    container saps {
                        description "Information about SAPs where the cpu protection rules are violated";

                        container overall-rate {
                            description "SAPs where the protection policy overall rate limit is violated";

                            list sap {
                                key "service-id sap-id";
                                description "SAP where the protection policy overall rate limit is violated";

                                leaf service-id {
                                    type types-services:external-service-id;
                                    description "The service index.";
                                }

                                leaf sap-id {
                                    type types-sros:sap;
                                    description "The SAP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list sap

                        } // container overall-rate

                        container out-of-profile-rate {
                            description "SAPs where the protection policy out-of-profile rate limit is violated";

                            list sap {
                                key "service-id sap-id";
                                description "SAP where the protection policy out-of-profile rate limit is violated";

                                leaf service-id {
                                    type types-services:external-service-id;
                                    description "The service index.";
                                }

                                leaf sap-id {
                                    type types-sros:sap;
                                    description "The SAP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list sap

                        } // container out-of-profile-rate

                        container eth-cfm-rate {
                            description "SAPs where the protection policy Ethernet Connectivity Fault Management (CFM) rate limit is violated";

                            list aggregate-flow {
                                key "service-id sap-id level opcode";
                                description "The set of flows on a SAP that violates the protection policy Ethernet CFM aggregate rate limit";

                                leaf service-id {
                                    type types-services:external-service-id;
                                    description "The service index.";
                                }

                                leaf sap-id {
                                    type types-sros:sap;
                                    description "The SAP identifier.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list aggregate-flow

                            list mac-flow {
                                key "service-id sap-id mac-address level opcode";
                                description "Ethernet CFM PDU stream on a SAP that violates the protection policy Ethernet CFM rate limit";

                                leaf service-id {
                                    type types-services:external-service-id;
                                    description "The service index.";
                                }

                                leaf sap-id {
                                    type types-sros:sap;
                                    description "The SAP identifier.";
                                }

                                leaf mac-address {
                                    type yang:mac-address;
                                    description "The source MAC address.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list mac-flow

                        } // container eth-cfm-rate

                    } // container saps

                    container sdps {
                        description "Information about spoke SDPs where the cpu protection rules are violated";

                        container overall-rate {
                            description "Spoke SDPs where the protection policy overall rate limit is violated";

                            list spoke-sdp {
                                key "service-id sdp-bind-id";
                                description "Spoke SDP where the protection policy overall rate limit is violated";

                                leaf service-id {
                                    type types-services:external-service-id;
                                    description "The service index.";
                                }

                                leaf sdp-bind-id {
                                    type types-services:sdp-bind-id;
                                    description "The spoke SDP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list spoke-sdp

                        } // container overall-rate

                        container out-of-profile-rate {
                            description "Spoke SDPs where the protection policy out-of-profile rate limit is violated";

                            list spoke-sdp {
                                key "service-id sdp-bind-id";
                                description "Spoke SDP where the protection policy out-of-profile rate limit is violated";

                                leaf service-id {
                                    type types-services:external-service-id;
                                    description "The service index.";
                                }

                                leaf sdp-bind-id {
                                    type types-services:sdp-bind-id;
                                    description "The spoke SDP identifier.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list spoke-sdp

                        } // container out-of-profile-rate

                        container eth-cfm-rate {
                            description "Spoke SDPs where the protection policy Ethernet Connectivity Fault Management (CFM) rate limit is violated";

                            list aggregate-flow {
                                key "service-id sdp-bind-id level opcode";
                                description "The set of flows on a Spoke SDP that violate the protection policy Ethernet CFM aggregate rate limit";

                                leaf service-id {
                                    type types-services:external-service-id;
                                    description "The service index.";
                                }

                                leaf sdp-bind-id {
                                    type types-services:sdp-bind-id;
                                    description "The spoke SDP identifier.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list aggregate-flow

                            list mac-flow {
                                key "service-id sdp-bind-id mac-address level opcode";
                                description "Ethernet CFM PDU stream on a Spoke SDP that violates the protection policy Ethernet CFM rate limit";

                                leaf service-id {
                                    type types-services:external-service-id;
                                    description "The service index.";
                                }

                                leaf sdp-bind-id {
                                    type types-services:sdp-bind-id;
                                    description "The spoke SDP identifier.";
                                }

                                leaf mac-address {
                                    type yang:mac-address;
                                    description "The source MAC address.";
                                }

                                leaf level {
                                    type types-eth-cfm:mp-level;
                                    description "The Ethernet CFM domain level.";
                                }

                                leaf opcode {
                                    type uint32 {
                                        range "0..255";
                                    }
                                    description "The Ethernet CFM opcode.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list mac-flow

                        } // container eth-cfm-rate

                    } // container sdps

                    container ports {
                        description "Information about ports where the cpu protection rules are violated";

                        list port {
                            key "port-id";
                            description "Ports where the link-specific rate limit or the overall rate limit is violated";

                            leaf port-id {
                                type types-sros:port;
                                description "The identifier that uniquely identifies the port.";
                            }

                            container link-specific-rate {
                                description "Information about violations of the link-specific rate limit on this port";

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // container link-specific-rate

                            container overall-rate {
                                description "Information about violations of the overall rate limit on this port";

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // container overall-rate

                        } // list port

                    } // container ports

                    container mac-sources {
                        description "Information about packet streams that violate the cpu protection policy per-source rules";

                        container sap-sources {
                            description
                                "MAC source packet streams that violate the cpu protection policy per-source rules
                                 on a SAP";

                            list mac-source {
                                key "service-id sap-id mac-address";
                                description "MAC source packet stream that violates the cpu protection policy per-source rules";

                                leaf service-id {
                                    type types-services:external-service-id;
                                    description "The service index.";
                                }

                                leaf sap-id {
                                    type types-sros:sap;
                                    description "The SAP identifier.";
                                }

                                leaf mac-address {
                                    type yang:mac-address;
                                    description "MAC address.";
                                }

                                leaf sap-type {
                                    type types-services:service-type;
                                    description "The type of the service containing the SAP or the spoke SDP.";
                                }

                                leaf service-name {
                                    type types-services:service-name;
                                    description "The name of the service containing the SAP or the spoke SDP.";
                                }

                                leaf interface-type {
                                    type types-router:interface-type;
                                    description "The type of interface.This is only applicable for layer 3 SAPs or spoke SDPs.";
                                }

                                leaf interface-name {
                                    type types-sros:interface-name;
                                    description "The name of the interface.This is only applicable for layer 3 SAPs or spoke SDPs.";
                                }

                                leaf periods {
                                    type yang:counter32;
                                    description
                                        "The number of times the rate limit violation was detected.
                                         the sampling interval length is equal to 1 second.";
                                }

                                leaf first-time {
                                    type yang:date-and-time;
                                    description "Indicates when the violation occurred for the first time.";
                                }

                                leaf last-time {
                                    type yang:date-and-time;
                                    description "Indicates when the violation occurred for the last time.";
                                }

                            } // list mac-source

                        } // container sap-sources

                    } // container mac-sources

                } // container violators

            } // container cpu-protection

            container dot1x {
                description "Enter the dot1x context";

                list radius-policy {
                    key "policy-name";
                    description "Enter the radius-policy context";

                    leaf policy-name {
                        type types-sros:named-item;
                        description "RADIUS server policy to use for 802.1X authentication";
                    }

                    list server {
                        key "server-index";
                        description "Enter the server context";

                        leaf server-index {
                            type uint32 {
                                range "1..5";
                            }
                            description "RADIUS server index";
                        }

                        leaf oper-state {
                            type types-sros:oper-state;
                            description "Indicates the current status of the RADIUS server";
                        }

                    } // list server

                } // list radius-policy

            } // container dot1x

            container keychains {
                description "Enter the keychains context";

                list keychain {
                    key "keychain-name";
                    description "Enter the keychain context";

                    leaf keychain-name {
                        type types-sros:named-item;
                        description "Keychain name";
                    }

                    leaf oper-state {
                        type types-sros:oper-state;
                        description "Indicates the operational state of the keychain.";
                    }

                    leaf expired {
                        type boolean;
                        description "Indicates if the keychain is expired.";
                    }

                } // list keychain

            } // container keychains

            container source-address {
                description "Enter the source-address context";

                list ipv4 {
                    key "application";
                    description "Enter the ipv4 context";

                    leaf application {
                        type enumeration {
                            enum "telnet"                       { value 1; }
                            enum "ftp"                          { value 2; }
                            enum "ssh"                          { value 3; }
                            enum "radius"                       { value 4; }
                            enum "tacplus"                      { value 5; }
                            enum "snmptrap"                     { value 6; }
                            enum "syslog"                       { value 7; }
                            enum "ping"                         { value 8; }
                            enum "traceroute"                   { value 9; }
                            enum "dns"                          { value 10; }
                            enum "sntp"                         { value 11; }
                            enum "ntp"                          { value 12; }
                            enum "cflowd"                       { value 13; }
                            enum "ptp"                          { value 23; }
                            enum "mcreporter"                   { value 24; }
                            enum "sflow"                        { value 27; }
                            enum "icmp-error"                   { value 29; }
                            enum "ldap"                         { value 31; }
                        }
                        description "Source IP address for the application";
                    }

                    leaf oper-status {
                        type types-system:server-oper-status;
                        description "Indicates the operational status of the soure IP entry.";
                    }

                } // list ipv4

                list ipv6 {
                    key "application";
                    description "Enter the ipv6 context";

                    leaf application {
                        type enumeration {
                            enum "telnet"                       { value 14; }
                            enum "ftp"                          { value 15; }
                            enum "radius"                       { value 16; }
                            enum "tacplus"                      { value 17; }
                            enum "snmptrap"                     { value 18; }
                            enum "syslog"                       { value 19; }
                            enum "ping"                         { value 20; }
                            enum "traceroute"                   { value 21; }
                            enum "dns"                          { value 22; }
                            enum "cflowd"                       { value 25; }
                            enum "ntp"                          { value 26; }
                            enum "sflow"                        { value 28; }
                            enum "icmp6-error"                  { value 30; }
                            enum "ldap"                         { value 32; }
                        }
                        description "Source IPv6 address for the application";
                    }

                    leaf oper-status {
                        type types-system:server-oper-status;
                        description "Indicates the operational status of the soure IPv6 entry.";
                    }

                } // list ipv6

            } // container source-address

            uses state-system-security-aaa;
            uses state-system-security-cpm-cpm-filter;
            uses state-system-security-cpm-cpm-queue;
            uses state-system-security-management-access-filter;
            uses state-system-security-pki;
            uses state-system-security-ssh;
            uses state-system-security-tls;
            uses state-system-security-user-parameters-user-params;
        } // container security

    } // grouping state-system-security

}
