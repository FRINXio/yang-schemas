module nokia-types-radius {

    yang-version "1.1";

    namespace "urn:nokia.com:sros:ns:yang:sr:types-radius";

    prefix "types-radius";

    import nokia-sros-yang-extensions     { prefix "sros-ext"; }


    sros-ext:sros-major-release "rel16";

    organization "Nokia";

    contact
        "Nokia SR OS Support
         Web: <http://www.nokia.com>";

    description
        "Common radius data types used in the SR OS management system.

         Copyright 2016 Nokia. All rights reserved. Reproduction of this document
         is authorized on the condition that the foregoing copyright notice is included.

         This nokia-types-radius YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-07-14";

    typedef server-selection-algo {
        type enumeration {
            enum "direct"                       { value 1; }
            enum "round-robin"                  { value 2; }
            enum "hash-based"                   { value 3; }
        }
        default "direct";
        description
            "This type indicates the algorithm used to access the list
             of configured RADIUS servers.";
    }

    typedef radius-attribute-type {
        type uint32 {
            range "1..255";
        }
        description "RADIUS attribute type ";
    }

    typedef radius-vendor-id {
        type union {
            type uint32 {
                range "1..16777215";
            }
            type enumeration {
                enum "nokia"                        { value 6527; }
            }
        }
        description "RADIUS vendor id ";
    }

}
