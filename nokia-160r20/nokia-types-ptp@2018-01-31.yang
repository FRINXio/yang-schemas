module nokia-types-ptp {

    yang-version "1.1";

    namespace "urn:nokia.com:sros:ns:yang:sr:types-ptp";

    prefix "types-ptp";

    import nokia-sros-yang-extensions     { prefix "sros-ext"; }


    sros-ext:sros-major-release "rel16";

    organization "Nokia";

    contact
        "Nokia SR OS Support
         Web: <http://www.nokia.com>";

    description
        "Common PTP data types used in the SR OS management system.

         Copyright 2016 Nokia. All rights reserved. Reproduction of this document
         is authorized on the condition that the foregoing copyright notice is included.

         This nokia-types-ptp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-01-31";

    typedef clock-type {
        type enumeration {
            enum "ordinary-slave"               { value 1; }
            enum "ordinary-master"              { value 2; }
            enum "boundary"                     { value 3; }
        }
        description
            "The type of clock of the network element:
             ordinarySlave  (1) - The system is always a slave clock in the
                                  master-slave hierarchy. The system derives its
                                  timing from one or more master clocks in the
                                  network.
             ordinaryMaster (2) - The system is a grandmaster clock in the
                                  master-slave hierarchy.  The system provides
                                  timing to multiple slave clocks in the
                                  network.
             boundary       (3) - The system is a boundary clock, which may be
                                  anywhere in the master-slave clock hierarchy.
                                  It can obtain timing from a master clock, and
                                  provide timing to multiple slave clocks.";
    }

    typedef domain {
        type uint32 {
            range "0..255";
        }
        description
            "The Precision Time Protocol (PTP) domain.

             The value 0 specifies the default domain for IEEE1588-2008.
             The value 4 specifies the default domain for ITU-T G.8265.1
             specification.
             The value 24 specifies the default domain for ITU-T G.8275.1
             specification.";
    }

    typedef priority {
        type uint32 {
            range "0..255";
        }
        description
            "The Precision Time Protocol (PTP) priority used both for the value to
             advertise in the Announce messages and for the local clock value in
             data set comparisons.

             It is used by the Best Master Clock Algorithm to determine which clock
             should provide timing for the network.

             The priority is rated highest (0) to lowest (255).";
    }

    typedef profile {
        type enumeration {
            enum "g8265dot1-2010"               { value 1; }
            enum "ieee1588-2008"                { value 2; }
            enum "g8275dot1-2014"               { value 3; }
        }
        description
            "The Precision Time Protocol (PTP) profile specifies the standard to
             which PTP conforms.
                  g8265dot1-2010 - conforms to the PTP profile specified in the
                                   ITU-T G.8265.1 specification
                  ieee1588-2008  - conforms to the default PTP profile specified in
                                   the IEEE 1588-2008 standard
                  g8275dot1-2014 - conforms to the PTP profile specified in the
                                   ITU-T G.8275.1 specification.";
    }

    typedef log-interval {
        type int32 {
            range "-128..127";
        }
        description
            "The interval between PTP packets, or equivalently a packet rate.
             Is is the logarithm to the base 2 of the interval in seconds.

             For example, -7 specifies a rate of 128 packets per second, and
             +4 specifies a packet rate of 1 packet every 16 seconds.";
    }

}
