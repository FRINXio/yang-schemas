submodule nokia-state-svc-ies-sub-if {

    yang-version "1.1";

    belongs-to nokia-state { prefix "state"; }

    import ietf-yang-types                { prefix "yang"; }
    import nokia-sros-yang-extensions     { prefix "sros-ext"; }
    import nokia-types-services           { prefix "types-services"; }
    import nokia-types-sros               { prefix "types-sros"; }

    include nokia-state-svc-ies-grp-if-wlangw;
    include nokia-state-svc-ies-sub-if-wlangw;

    sros-ext:sros-major-release "rel16";

    organization "Nokia";

    contact
        "Nokia SR OS Support
         Web: <http://www.nokia.com>";

    description
        "Nokia YANG Data model with operational state for ies service subscriber interfaces on SR OS based routers.

         Copyright 2016 Nokia. All rights reserved. Reproduction of this document
         is authorized on the condition that the foregoing copyright notice is included.

         This nokia-state-svc-ies-sub-if YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-06-07";

    grouping state-svc-ies-sub-if-subscriber-interface {
        list subscriber-interface {
            key "interface-name";
            description "Enter the subscriber-interface context";

            leaf interface-name {
                type types-sros:interface-name;
                description "Interface name";
            }

            leaf if-index {
                type int32;
                description "The interface index.";
            }

            leaf system-if-index {
                type int32;
                description "The interface system index.";
            }

            container ipv4 {
                description "Enter the ipv4 context";

                leaf oper-state {
                    type types-sros:oper-state;
                    description "The current IPv4 operational status of this router interface.";
                }

                leaf down-reason {
                    type bits {
                        bit admin-disabled                 { position 0; }
                        bit service-admin-disabled         { position 1; }
                        bit port-down                      { position 2; }
                        bit address-or-parent-not-ready    { position 3; }
                        bit associated-object-not-ready    { position 4; }
                        bit rvpls-down                     { position 5; }
                        bit operational-group-down         { position 6; }
                        bit admin-destroy                  { position 7; }
                        bit no-address                     { position 8; }
                        bit no-info                        { position 9; }
                        bit hold-down-timer-running        { position 10; }
                        bit protocol-down                  { position 11; }
                        bit invalid-port-configuration     { position 12; }
                        bit unknown                        { position 13; }
                        bit no-route-distinguisher         { position 14; }
                        bit wlan-gateway-redundancy-standby { position 15; }
                        bit wlan-gateway-group-degraded    { position 16; }
                        bit ip-control-tunnel-down         { position 17; }
                        bit pdn-address-mismatch           { position 18; }
                    }
                    description
                        "Indicates the reason for why the interface is operationally down.
                                         
                         Values:
                             admin-disabled                  - Administratively disabled.
                             service-admin-disabled          - Assiocated service is administratively disabled.
                             port-down                       - Associated SAP/port is operationally down.
                             address-or-parent-not-ready     - Associated address or parent interface is not ready.
                             associated-object-not-ready     - Associated object is not ready.
                             rvpls-down                      - Associated R-VPLS service is operationally down.
                             operational-group-down          - Associated operational group is operationally down.
                             admin-destroy                   - The interface is being destroyed.
                             no-address                      - There is no address configured.
                             no-info                         - The interface info is not present.
                             hold-down-timer-running         - The hold down timer is running.
                             protocol-down                   - The protocols are operationally down.
                             invalid-port-configuration      - Invalid port configuration.
                             unknown                         - The interface is operationally down due to some unknown reason.
                             no-route-distinguisher          - No route-distinguisher configured in the VRF.
                             wlan-gateway-redundancy-standby - The interface is in standby state for WLAN-GW redundancy.
                             wlan-gateway-group-degraded     - The interface associated WLAN-GW group is in a degraded state.
                             ip-control-tunnel-down          - The IP tunnel associated to a control-tunnel interface is operationally down.
                             pdn-address-mismatch            - The IP address learned from the packet data network does not match the configured primary IP address.";
                }

                container statistics {
                    description "Interface IPv4 statistics.";

                    leaf out-packets {
                        type yang:counter64;
                        description "The number of packets transmitted by this interface.";
                    }

                    leaf out-octets {
                        type yang:counter64;
                        description "The number of octets transmitted by this interface.";
                    }

                    leaf out-discard-packets {
                        type yang:counter64;
                        description "The number of transmit packets discarded.";
                    }

                    leaf out-discard-octets {
                        type yang:counter64;
                        description "The number of transmit octets discarded.";
                    }

                    leaf in-packets {
                        type yang:counter64;
                        description "The number of packets received.";
                    }

                    leaf in-octets {
                        type yang:counter64;
                        description "The number of octets received.";
                    }

                    leaf urpf-check-fail-packets {
                        type yang:counter64;
                        description "The number of packets that fail uRPF check on this interface.";
                    }

                    leaf urpf-check-fail-octets {
                        type yang:counter64;
                        description "The number of octets in the packets that fail uRPF check.";
                    }

                    leaf out-discard-dbcast-packets {
                        type yang:counter64;
                        description "The number of directed-broadcast packets dropped.";
                    }

                    leaf out-discard-dbcast-octets {
                        type yang:counter64;
                        description "The number of directed-broadcast octets dropped.";
                    }

                } // container statistics

                list address {
                    key "ipv4-address";
                    description "Enter the address context";

                    leaf ipv4-address {
                        type types-sros:ipv4-unicast-address;
                        description "IP address  or IP subnet applied to interface";
                    }

                    leaf oper-address {
                        type types-sros:ip-address;
                        description "Indicates the operational address of this entry.";
                    }

                    leaf creation-origin {
                        type types-sros:creation-origin;
                        description "Indicates the mechanism used to create this entry.";
                    }

                } // list address

                container dhcp {
                    description "Enter the dhcp context";

                    container lease-populate {
                        description "Enter the lease-populate context";

                        leaf current-lease-states {
                            type uint32 {
                                range "0..511999";
                            }
                            description "The number of DHCP lease states currently allocated on this interface.";
                        }

                    } // container lease-populate

                    container statistics {
                        description "Packet statistics";

                        container client-packets {
                            description "Client packet statistics";

                            leaf snooped {
                                type yang:counter32;
                                description "The number of DHCP client packets that have been snooped on this SAP.";
                            }

                            leaf forwarded {
                                type yang:counter32;
                                description "The number  of  DHCP  client  packets  that have been forwarded on this SAP.";
                            }

                            leaf dropped {
                                type yang:counter32;
                                description "The number  of  DHCP  client  packets  that have been dropped on this SAP.";
                            }

                            container proxied {
                                description "Proxied packet statistics";

                                leaf radius {
                                    type yang:counter32;
                                    description
                                        "The number of DHCP client packets that have been proxied on this SAP
                                         based on data received from a RADIUS server.";
                                }

                                leaf lease-split {
                                    type yang:counter32;
                                    description
                                        "The number of DHCP client packets that have been proxied on this SAP
                                         based on lease state.";
                                }

                            } // container proxied

                        } // container client-packets

                        container server-packets {
                            description "Server packet statistics";

                            leaf snooped {
                                type yang:counter32;
                                description "The number of DHCP server packets that have been snooped on this SAP.";
                            }

                            leaf forwarded {
                                type yang:counter32;
                                description "The number  of  DHCP  server  packets  that have been forwarded on this SAP.";
                            }

                            leaf dropped {
                                type yang:counter32;
                                description "The number  of  DHCP  server  packets  that have been dropped on this SAP.";
                            }

                        } // container server-packets

                        container spoofed {
                            description "Spoofed packet statistics";

                            leaf force-renews {
                                type yang:counter32;
                                description "The number of DHCP FORCERENEW messages spoofed on this SAP to the DHCP clients.";
                            }

                            leaf releases {
                                type yang:counter32;
                                description "The number of DHCP RELEASE messages spoofed on this SAP to the DHCP server.";
                            }

                        } // container spoofed

                    } // container statistics

                } // container dhcp

            } // container ipv4

            container ipv6 {
                description "Enter the ipv6 context";

                leaf oper-state {
                    type types-sros:oper-state;
                    description "The current IPv6 operational status of this router interface.";
                }

                leaf down-reason {
                    type bits {
                        bit admin-disabled                 { position 0; }
                        bit service-admin-disabled         { position 1; }
                        bit port-down                      { position 2; }
                        bit address-or-parent-not-ready    { position 3; }
                        bit associated-object-not-ready    { position 4; }
                        bit rvpls-down                     { position 5; }
                        bit operational-group-down         { position 6; }
                        bit admin-destroy                  { position 7; }
                        bit no-address                     { position 8; }
                        bit no-info                        { position 9; }
                        bit hold-down-timer-running        { position 10; }
                        bit protocol-down                  { position 11; }
                        bit invalid-port-configuration     { position 12; }
                        bit unknown                        { position 13; }
                        bit no-route-distinguisher         { position 14; }
                        bit wlan-gateway-redundancy-standby { position 15; }
                        bit wlan-gateway-group-degraded    { position 16; }
                        bit ip-control-tunnel-down         { position 17; }
                        bit pdn-address-mismatch           { position 18; }
                    }
                    description
                        "Indicates the reason for why the interface is operationally down.
                                         
                         Values:
                             admin-disabled                  - Administratively disabled.
                             service-admin-disabled          - Assiocated service is administratively disabled.
                             port-down                       - Associated SAP/port is operationally down.
                             address-or-parent-not-ready     - Associated address or parent interface is not ready.
                             associated-object-not-ready     - Associated object is not ready.
                             rvpls-down                      - Associated R-VPLS service is operationally down.
                             operational-group-down          - Associated operational group is operationally down.
                             admin-destroy                   - The interface is being destroyed.
                             no-address                      - There is no address configured.
                             no-info                         - The interface info is not present.
                             hold-down-timer-running         - The hold down timer is running.
                             protocol-down                   - The protocols are operationally down.
                             invalid-port-configuration      - Invalid port configuration.
                             unknown                         - The interface is operationally down due to some unknown reason.
                             no-route-distinguisher          - No route-distinguisher configured in the VRF.
                             wlan-gateway-redundancy-standby - The interface is in standby state for WLAN-GW redundancy.
                             wlan-gateway-group-degraded     - The interface associated WLAN-GW group is in a degraded state.
                             ip-control-tunnel-down          - The IP tunnel associated to a control-tunnel interface is operationally down.
                             pdn-address-mismatch            - The IP address learned from the packet data network does not match the configured primary IP address.";
                }

                container statistics {
                    description "Interface IPv6 statistics.";

                    leaf out-packets {
                        type yang:counter64;
                        description "The number of packets transmitted by this interface.";
                    }

                    leaf out-octets {
                        type yang:counter64;
                        description "The number of octets transmitted by this interface.";
                    }

                    leaf out-discard-packets {
                        type yang:counter64;
                        description "The number of transmit packets discarded.";
                    }

                    leaf out-discard-octets {
                        type yang:counter64;
                        description "The number of transmit octets discarded.";
                    }

                    leaf in-packets {
                        type yang:counter64;
                        description "The number of packets received.";
                    }

                    leaf in-octets {
                        type yang:counter64;
                        description "The number of octets received.";
                    }

                    leaf urpf-check-fail-packets {
                        type yang:counter64;
                        description "The number of packets that fail uRPF check on this interface.";
                    }

                    leaf urpf-check-fail-octets {
                        type yang:counter64;
                        description "The number of octets in the packets that fail uRPF check.";
                    }

                    container hosts {
                        description "Ipv6-hosts state information.";

                        leaf ipoe-dhcp6 {
                            type yang:gauge32;
                            description "The number of IPoE DHCPv6 hosts.";
                        }

                        leaf ipoe-slaac {
                            type yang:gauge32;
                            description "The number of IPoE SLAAC hosts.";
                        }

                        leaf ppp-dhcp6 {
                            type yang:gauge32;
                            description "The number of PPP DHCPv6 hosts.";
                        }

                        leaf ppp-slaac {
                            type yang:gauge32;
                            description "The number of PPP SLAAC hosts.";
                        }

                        leaf static-enabled {
                            type yang:gauge32;
                            description "The number of IPv6 static IPoE hosts that are enabled.";
                        }

                    } // container hosts

                } // container statistics

                list address {
                    key "ipv6-address";
                    description "Enter the address context";

                    leaf ipv6-address {
                        type types-sros:ipv6-address;
                        description "IPv6 address for a router interface";
                    }

                    leaf address-state {
                        type types-sros:address-state;
                        description "Indicates the address state of the IPv6 address of the interface.";
                    }

                    leaf oper-address {
                        type types-sros:ip-address;
                        description "Indicates the operational address of this entry.";
                    }

                    leaf creation-origin {
                        type types-sros:creation-origin;
                        description "Indicates the mechanism used to create this entry.";
                    }

                } // list address

                list prefix {
                    key "ipv6-prefix";
                    description "Enter the prefix context";

                    leaf ipv6-prefix {
                        type types-sros:ipv6-prefix;
                        description "IPv6 address for a router interface";
                    }

                    leaf address-state {
                        type types-sros:address-state;
                        description "Indicates the address state of the IPv6 address of the interface.";
                    }

                    leaf oper-address {
                        type types-sros:ip-address;
                        description "Indicates the operational address of this entry.";
                    }

                    leaf creation-origin {
                        type types-sros:creation-origin;
                        description "Indicates the mechanism used to create this entry.";
                    }

                } // list prefix

                container dhcp6 {
                    description "Enter the dhcp6 context";

                    container proxy-server {
                        description "Enter the proxy-server context";

                        container server-id {
                            description "Enter the server-id context";

                            leaf duid-en-number {
                                type uint32;
                                description "The vendor's registered Private Enterprise Number maintained by IANA.";
                            }

                        } // container server-id

                    } // container proxy-server

                } // container dhcp6

            } // container ipv6

            container hold-time {
                description "Enter the hold-time context";

                container ipv4 {
                    description "Enter the ipv4 context";

                    leaf hold-timer {
                        type uint32;
                        units "seconds";
                        description
                            "The hold-timer indicates the time left before
                             the interface comes up or goes down, depending on the ongoing
                             transition state of the interface.";
                    }

                } // container ipv4

                container ipv6 {
                    description "Enter the ipv6 context";

                    leaf hold-timer {
                        type uint32;
                        units "seconds";
                        description
                            "The hold-timer indicates the time left before
                             the interface comes up or goes down, depending on the ongoing
                             transition state of the interface.";
                    }

                } // container ipv6

            } // container hold-time

            list group-interface {
                key "group-interface-name";
                description "Enter the group-interface context";

                leaf group-interface-name {
                    type types-sros:interface-name;
                    description "Interface name";
                }

                leaf if-index {
                    type int32;
                    description "The interface index.";
                }

                leaf system-if-index {
                    type int32;
                    description "The interface system index.";
                }

                container ipv4 {
                    description "Enter the ipv4 context";

                    leaf oper-state {
                        type types-sros:oper-state;
                        description "The current IPv4 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.";
                    }

                    container icmp {
                        description "Enter the icmp context";

                        container statistics {
                            description "Interface ICMPv4 statistics.";

                            leaf icmp-in-msgs {
                                type yang:counter32;
                                description
                                    "Total Number of ICMPv4 messages received by this interface.
                                                     
                                     This includes all those counted by icmp-in-errors. Note that this
                                     interface is the interface to which the ICMPv4 messages were
                                     addressed which may not be necessarily the input interface
                                     for the messages.";
                            }

                            leaf icmp-in-errors {
                                type yang:counter32;
                                description
                                    "Number of ICMPv4 errored messages received by this interface.
                                                     
                                     This implies ICMPv4 messages determined as having specific
                                     ICMPv4 errors (bad ICMPv4 checksums, bad length, etc.).";
                            }

                            leaf icmp-in-dest-unreachables {
                                type yang:counter32;
                                description "Number of ICMPv4 destination unreachable messages received by this interface.";
                            }

                            leaf icmp-in-redirects {
                                type yang:counter32;
                                description "Number of ICMPv4 redirect messages received by this interface.";
                            }

                            leaf icmp-in-echos {
                                type yang:counter32;
                                description "Number of ICMPv4 echo (request) messages received by this interface.";
                            }

                            leaf icmp-in-echo-replies {
                                type yang:counter32;
                                description "Number of ICMPv4 echo reply messages received by this interface.";
                            }

                            leaf icmp-in-time-exceeds {
                                type yang:counter32;
                                description "Number of ICMPv4 time exceeded messages received by this interface.";
                            }

                            leaf icmp-in-src-quenches {
                                type yang:counter32;
                                description "Number of ICMPv4 source quench messages received by this interface.";
                            }

                            leaf icmp-in-timestamps {
                                type yang:counter32;
                                description "Number of ICMPv4 timestamp (request) messages received by this interface.";
                            }

                            leaf icmp-in-timestamp-replies {
                                type yang:counter32;
                                description "Number of ICMPv4 timestamp reply messages received by this interface.";
                            }

                            leaf icmp-in-address-masks {
                                type yang:counter32;
                                description "Number of ICMPv4 address mask request messages received by this interface.";
                            }

                            leaf icmp-in-address-mask-replies {
                                type yang:counter32;
                                description "Number of ICMPv4 address mask reply messages received by this interface.";
                            }

                            leaf icmp-in-parm-problems {
                                type yang:counter32;
                                description "Number of ICMPv4 parameter problem messages received by this interface.";
                            }

                            leaf icmp-out-msgs {
                                type yang:counter32;
                                description
                                    "Total number of ICMPv4 messages this interface attempted to send.
                                                     
                                     This includes all those counted by icmp-out-errors.";
                            }

                            leaf icmp-out-errors {
                                type yang:counter32;
                                description
                                    "Number of ICMPv4 messages this interface could not be send due to problems
                                     discovered within ICMPv4 such as lack of buffers.
                                                     
                                     This value should not include errors discovered outside the ICMPv4 layer such as
                                     the inability of VRtr IPv4 to route the resultant datagram. In some implementations
                                     there may be no types of error which contribute to this counter's value.";
                            }

                            leaf icmp-out-dest-unreachables {
                                type yang:counter32;
                                description "Number of ICMPv4 destination unreachable messages sent by this interface.";
                            }

                            leaf icmp-out-redirects {
                                type yang:counter32;
                                description "Number of ICMPv4 redirect messages sent by this interface.";
                            }

                            leaf icmp-out-echos {
                                type yang:counter32;
                                description "Number of ICMPv4 echo request messages sent by this interface.";
                            }

                            leaf icmp-out-echo-replies {
                                type yang:counter32;
                                description "Number of ICMPv4 echo reply messages sent by this interface.";
                            }

                            leaf icmp-out-time-exceeds {
                                type yang:counter32;
                                description "Number of ICMPv4 time exceeded messages sent by this interface.";
                            }

                            leaf icmp-out-src-quenches {
                                type yang:counter32;
                                description "Number of ICMPv4 source quench messages sent by this interface.";
                            }

                            leaf icmp-out-timestamps {
                                type yang:counter32;
                                description "Number of ICMPv4 timestamp (request) messages sent by this interface.";
                            }

                            leaf icmp-out-timestamp-replies {
                                type yang:counter32;
                                description "Number of ICMPv4 timestamp reply messages sent by this interface.";
                            }

                            leaf icmp-out-address-masks {
                                type yang:counter32;
                                description "Number of ICMPv4 address mask request messages sent by this interface.";
                            }

                            leaf icmp-out-address-mask-replies {
                                type yang:counter32;
                                description "Number of ICMPv4 address mask reply messages sent by this interface.";
                            }

                            leaf icmp-out-parm-problems {
                                type yang:counter32;
                                description "Number of ICMPv4 parameter problem messages sent by this interface.";
                            }

                            leaf icmp-out-discards {
                                type yang:counter32;
                                description "Number of discarded ICMPv4 messages on this interface.";
                            }

                        } // container statistics

                    } // container icmp

                    container statistics {
                        description "Interface IPv4 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        leaf out-discard-dbcast-packets {
                            type yang:counter64;
                            description "The number of directed-broadcast packets dropped.";
                        }

                        leaf out-discard-dbcast-octets {
                            type yang:counter64;
                            description "The number of directed-broadcast octets dropped.";
                        }

                    } // container statistics

                    container arp-host {
                        description "ARP host parameters.";

                        container statistics {

                            leaf hosts {
                                type uint32;
                                description "The number of ARP hosts on this interface.";
                            }

                        } // container statistics

                    } // container arp-host

                    container neighbor-discovery {
                        description "Enter the neighbor-discovery context";

                        list neighbor {
                            key "ipv4-address";
                            description "IP-to-MAC address mapping state parameters on the interface.";

                            leaf ipv4-address {
                                type types-sros:ipv4-address;
                                description "IPv4 address corresponding to the media-dependent physical address";
                            }

                            leaf oper-state {
                                type types-sros:oper-state;
                                description "Indicates if the ARP entry is being used actively in the ARP table.";
                            }

                            leaf port {
                                type types-sros:port;
                                description "The ID of the port on which this entry was learned.";
                            }

                            leaf encap {
                                type types-sros:encap-val;
                                description
                                    "The encap value of the SAP this entry was learned on.

                                     If this entry was learned on a network port or null-encap SAP,
                                     the value of this object will be zero.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                    container dhcp {
                        description "Enter the dhcp context";

                        container lease-populate {
                            description "Enter the lease-populate context";

                            leaf current-lease-states {
                                type uint32 {
                                    range "0..511999";
                                }
                                description "The number of DHCP lease states currently allocated on this interface.";
                            }

                        } // container lease-populate

                        container statistics {
                            description "Packet statistics";

                            container client-packets {
                                description "Client packet statistics";

                                leaf snooped {
                                    type yang:counter32;
                                    description "The number of DHCP client packets that have been snooped on this SAP.";
                                }

                                leaf forwarded {
                                    type yang:counter32;
                                    description "The number  of  DHCP  client  packets  that have been forwarded on this SAP.";
                                }

                                leaf dropped {
                                    type yang:counter32;
                                    description "The number  of  DHCP  client  packets  that have been dropped on this SAP.";
                                }

                                container proxied {
                                    description "Proxied packet statistics";

                                    leaf radius {
                                        type yang:counter32;
                                        description
                                            "The number of DHCP client packets that have been proxied on this SAP
                                             based on data received from a RADIUS server.";
                                    }

                                    leaf lease-split {
                                        type yang:counter32;
                                        description
                                            "The number of DHCP client packets that have been proxied on this SAP
                                             based on lease state.";
                                    }

                                } // container proxied

                            } // container client-packets

                            container server-packets {
                                description "Server packet statistics";

                                leaf snooped {
                                    type yang:counter32;
                                    description "The number of DHCP server packets that have been snooped on this SAP.";
                                }

                                leaf forwarded {
                                    type yang:counter32;
                                    description "The number  of  DHCP  server  packets  that have been forwarded on this SAP.";
                                }

                                leaf dropped {
                                    type yang:counter32;
                                    description "The number  of  DHCP  server  packets  that have been dropped on this SAP.";
                                }

                            } // container server-packets

                            container spoofed {
                                description "Spoofed packet statistics";

                                leaf force-renews {
                                    type yang:counter32;
                                    description "The number of DHCP FORCERENEW messages spoofed on this SAP to the DHCP clients.";
                                }

                                leaf releases {
                                    type yang:counter32;
                                    description "The number of DHCP RELEASE messages spoofed on this SAP to the DHCP server.";
                                }

                            } // container spoofed

                        } // container statistics

                    } // container dhcp

                } // container ipv4

                container ipv6 {
                    description "Enter the ipv6 context";

                    leaf oper-state {
                        type types-sros:oper-state;
                        description "The current IPv6 operational status of this router interface.";
                    }

                    leaf down-reason {
                        type bits {
                            bit admin-disabled                 { position 0; }
                            bit service-admin-disabled         { position 1; }
                            bit port-down                      { position 2; }
                            bit address-or-parent-not-ready    { position 3; }
                            bit associated-object-not-ready    { position 4; }
                            bit rvpls-down                     { position 5; }
                            bit operational-group-down         { position 6; }
                            bit admin-destroy                  { position 7; }
                            bit no-address                     { position 8; }
                            bit no-info                        { position 9; }
                            bit hold-down-timer-running        { position 10; }
                            bit protocol-down                  { position 11; }
                            bit invalid-port-configuration     { position 12; }
                            bit unknown                        { position 13; }
                            bit no-route-distinguisher         { position 14; }
                            bit wlan-gateway-redundancy-standby { position 15; }
                            bit wlan-gateway-group-degraded    { position 16; }
                            bit ip-control-tunnel-down         { position 17; }
                            bit pdn-address-mismatch           { position 18; }
                        }
                        description
                            "Indicates the reason for why the interface is operationally down.
                                             
                             Values:
                                 admin-disabled                  - Administratively disabled.
                                 service-admin-disabled          - Assiocated service is administratively disabled.
                                 port-down                       - Associated SAP/port is operationally down.
                                 address-or-parent-not-ready     - Associated address or parent interface is not ready.
                                 associated-object-not-ready     - Associated object is not ready.
                                 rvpls-down                      - Associated R-VPLS service is operationally down.
                                 operational-group-down          - Associated operational group is operationally down.
                                 admin-destroy                   - The interface is being destroyed.
                                 no-address                      - There is no address configured.
                                 no-info                         - The interface info is not present.
                                 hold-down-timer-running         - The hold down timer is running.
                                 protocol-down                   - The protocols are operationally down.
                                 invalid-port-configuration      - Invalid port configuration.
                                 unknown                         - The interface is operationally down due to some unknown reason.
                                 no-route-distinguisher          - No route-distinguisher configured in the VRF.
                                 wlan-gateway-redundancy-standby - The interface is in standby state for WLAN-GW redundancy.
                                 wlan-gateway-group-degraded     - The interface associated WLAN-GW group is in a degraded state.
                                 ip-control-tunnel-down          - The IP tunnel associated to a control-tunnel interface is operationally down.
                                 pdn-address-mismatch            - The IP address learned from the packet data network does not match the configured primary IP address.";
                    }

                    container statistics {
                        description "Interface IPv6 statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                        container hosts {
                            description "Ipv6-hosts state information.";

                            leaf ipoe-dhcp6 {
                                type yang:gauge32;
                                description "The number of IPoE DHCPv6 hosts.";
                            }

                            leaf ipoe-slaac {
                                type yang:gauge32;
                                description "The number of IPoE SLAAC hosts.";
                            }

                            leaf ppp-dhcp6 {
                                type yang:gauge32;
                                description "The number of PPP DHCPv6 hosts.";
                            }

                            leaf ppp-slaac {
                                type yang:gauge32;
                                description "The number of PPP SLAAC hosts.";
                            }

                            leaf static-enabled {
                                type yang:gauge32;
                                description "The number of IPv6 static IPoE hosts that are enabled.";
                            }

                        } // container hosts

                    } // container statistics

                    container dhcp6 {
                        description "Enter the dhcp6 context";

                        container proxy-server {
                            description "Enter the proxy-server context";

                            container server-id {
                                description "Enter the server-id context";

                                leaf duid-en-number {
                                    type uint32;
                                    description "The vendor's registered Private Enterprise Number maintained by IANA.";
                                }

                            } // container server-id

                        } // container proxy-server

                    } // container dhcp6

                    container neighbor-discovery {
                        description "Enter the neighbor-discovery context";

                        list neighbor {
                            key "ipv6-address";
                            description "IPv6-to-MAC address mapping state parameters on the interface.";

                            leaf ipv6-address {
                                type types-sros:ipv6-address;
                                description "IPv6 address corresponding to the media-dependent physical address";
                            }

                            leaf state {
                                type enumeration {
                                    enum "incomplete"                   { value 0; }
                                    enum "reachable"                    { value 1; }
                                    enum "stale"                        { value 2; }
                                    enum "delay"                        { value 3; }
                                    enum "probe"                        { value 4; }
                                }
                                description
                                    "The Neighbor Unreachability Detection state for the interface
                                     when the address mapping is used.";
                            }

                            leaf is-router {
                                type boolean;
                                description "Indicates whether this entry is a router.";
                            }

                            leaf secure-nd {
                                type enumeration {
                                    enum "not-applicable"               { value 0; }
                                    enum "secure"                       { value 1; }
                                    enum "unsecure"                     { value 2; }
                                }
                                description
                                    "Indicates whether the physical address is received
                                     via Secured Neighbor Discovery messages.";
                            }

                            leaf mtu {
                                type uint32;
                                description "The MTU of the link attached to this entry.";
                            }

                            leaf mac-address {
                                type yang:mac-address;
                                description "The media-dependent physical address.";
                            }

                            leaf type {
                                type enumeration {
                                    enum "other"                        { value 0; }
                                    enum "static"                       { value 1; }
                                    enum "dynamic"                      { value 2; }
                                    enum "managed"                      { value 100; }
                                    enum "evpn"                         { value 101; }
                                }
                                description "The type of mapping.";
                            }

                            leaf timer {
                                type uint32 {
                                    range "0..65535";
                                }
                                units "seconds";
                                description
                                    "Indicates how much longer an ARP entry remains in the ARP cache.

                                     When timer has a value of zero, the entry is cleared from the cache.";
                            }

                        } // list neighbor

                    } // container neighbor-discovery

                } // container ipv6

                list srrp {
                    key "srrp-id";
                    description "Enter the srrp context";

                    leaf srrp-id {
                        type uint32 {
                            range "1..4294967295";
                        }
                        description "SRRP instance ID";
                    }

                    container bfd-liveness {
                        description "Enter the bfd-liveness context";

                        leaf src-ip {
                            type types-sros:ip-address;
                            description
                                "The value indicates the source
                                 IP address on the interface running BFD.";
                        }

                        leaf session-state {
                            type enumeration {
                                enum "unknown"                      { value 1; }
                                enum "connected"                    { value 2; }
                                enum "broken"                       { value 3; }
                                enum "peer-detects-down"            { value 4; }
                                enum "not-configured"               { value 5; }
                                enum "no-resources"                 { value 6; }
                            }
                            description
                                "The value indicates the operational
                                 state of the BFD session the VRRP is relying
                                 upon for its fast triggering mechanism.";
                        }

                    } // container bfd-liveness

                } // list srrp

                container bonding-parameters {
                    description "Enter the bonding-parameters context";

                    leaf oper-state {
                        type types-sros:oper-state;
                        description "Operational state of ESM bonding.";
                    }

                } // container bonding-parameters

                container gtp-parameters {
                    description "Enter the gtp-parameters context";

                    leaf oper-state {
                        type types-sros:oper-state;
                        description "Operational state of this GTP Access.";
                    }

                } // container gtp-parameters

                list sap {
                    key "sap-id";
                    description "Enter the sap context";

                    leaf sap-id {
                        type types-sros:sap;
                        description "SAP identifier";
                    }

                    leaf oper-state {
                        type enumeration {
                            enum "up"                           { value 1; }
                            enum "down"                         { value 2; }
                        }
                        description "Operating state of this SAP";
                    }

                    leaf mirror-state {
                        type enumeration {
                            enum "ingress"                      { value 1; }
                            enum "egress"                       { value 2; }
                            enum "ingress-and-egress"           { value 3; }
                            enum "disabled"                     { value 4; }
                        }
                        description "Indicates whether traffic mirroring has been enabled on this SAP";
                    }

                    leaf oper-flags {
                        type types-services:l3-sap-oper-flags;
                        description "Conditions that affect the operating status of this SAP.";
                    }

                    leaf oper-dist-cpu-prot-policy {
                        type types-sros:named-item-or-empty;
                        description "Operational Distributed CPU Protection Policy.";
                    }

                    container statistics {
                        description "Statistics information";

                        container authentication {
                            description "Authentication statistics information";

                            leaf discarded-packets {
                                type yang:counter32;
                                description
                                    "The number of DHCP packets discarded
                                     as result of authentication.";
                            }

                            leaf success-packets {
                                type yang:counter32;
                                description "The number of DHCP packets successfully authenticated.";
                            }

                        } // container authentication

                        container ipv4-hosts {
                            description "Ipv4-hosts state information";

                            leaf lease-allocations {
                                type yang:gauge32;
                                description
                                    "The number of DHCP lease states currently
                                     allocated on this SAP.";
                            }

                        } // container ipv4-hosts

                        container ipv6-hosts {
                            description "Ipv6-hosts state information";

                            leaf ipoe-dhcp6 {
                                type yang:gauge32;
                                description "The number of IPoE DHCPv6 hosts for this SAP.";
                            }

                            leaf ppp-dhcp6 {
                                type yang:gauge32;
                                description "The number of PPP DHCPv6 hosts for this SAP.";
                            }

                            leaf ppp-slaac {
                                type yang:gauge32;
                                description "The number of PPP SLAAC hosts for this SAP.";
                            }

                            leaf ipoe-slaac {
                                type yang:gauge32;
                                description "The number of IPoE SLAAC hosts for this SAP.";
                            }

                            leaf static-enabled {
                                type yang:gauge32;
                                description
                                    "The number of IPv6 static IPoE hosts for this SAP
                                     where the value of admin-status is equal to 'enable'.";
                            }

                        } // container ipv6-hosts

                    } // container statistics

                    container ingress {
                        description "Enter the ingress context";

                        container qos {
                            description "Enter the qos context";

                            container sap-ingress {
                                description "Enter the sap-ingress context";

                                container forwarding-engine {
                                    description "Forwarding engine information";

                                    container statistics {
                                        description "Statistics information";

                                        leaf dropped-packets {
                                            type yang:counter64;
                                            description
                                                "The number of packets dropped by the
                                                 ingress packet processor due to: SAP state,
                                                 ingress MAC, IP or IPv6 filter, same segment
                                                 discard, bad checksum, etc.";
                                        }

                                        leaf dropped-octets {
                                            type yang:counter64;
                                            description
                                                "The number of octets dropped by the
                                                 ingress packet processor due to: SAP state,
                                                 ingress MAC, IP or IPv6 filter, same segment
                                                 discard, bad checksum, etc.";
                                        }

                                        leaf received-valid-packets {
                                            type yang:counter64;
                                            description
                                                "The value of received-valid indicates
                                                 number of received valid packets, as determined by the SAP
                                                 ingress QoS policy, offered by the packet processor to the traffic manager.";
                                        }

                                        leaf received-valid-octets {
                                            type yang:counter64;
                                            description
                                                "The value of received-valid indicates
                                                 number of received valid octets, as determined by the SAP
                                                 ingress QoS policy, offered by the packet processor to the traffic manager.";
                                        }

                                        leaf high-priority-offered-packets {
                                            type yang:counter64;
                                            description
                                                "The number of high priority packets,
                                                 as determined by the SAP ingress QoS
                                                 policy, offered by the packet processor to the
                                                 traffic manager.";
                                        }

                                        leaf high-priority-offered-octets {
                                            type yang:counter64;
                                            description
                                                "The number of high priority octets,
                                                 as determined by the SAP ingress QoS
                                                 policy, offered by the packet processor to the
                                                 traffic manager.";
                                        }

                                        leaf low-priority-offered-packets {
                                            type yang:counter64;
                                            description
                                                "The number of low priority packets,
                                                 as determined by the SAP ingress QoS
                                                 policy, offered by the packet processor to the
                                                 traffic manager.";
                                        }

                                        leaf low-priority-offered-octets {
                                            type yang:counter64;
                                            description
                                                "The number of low priority octets,
                                                 as determined by the SAP ingress QoS
                                                 policy, offered by the packet processor to the
                                                 traffic manager.";
                                        }

                                        leaf uncolor-offered-packets {
                                            type yang:counter64;
                                            description
                                                "The number of uncolored packets,
                                                 as determined by the SAP ingress QoS
                                                 policy, offered by the packet processor to the
                                                 traffic manager.";
                                        }

                                        leaf uncolor-offered-octets {
                                            type yang:counter64;
                                            description
                                                "The number of uncolored octets,
                                                 as determined by the SAP ingress QoS
                                                 policy, offered by the packet processor to the
                                                 traffic manager.";
                                        }

                                        leaf managed-offered-packets {
                                            type yang:counter64;
                                            description
                                                "The value of managed-offered indicates
                                                 number of managed multicast packets, as determined by the SAP
                                                 ingress QoS policy, offered by the packet processor to the traffic manager.";
                                        }

                                        leaf managed-offered-octets {
                                            type yang:counter64;
                                            description
                                                "The value of managed-offered indicates
                                                 number of managed multicast octets, as determined by the SAP
                                                 ingress QoS policy, offered by the packet processor to the traffic manager.";
                                        }

                                        leaf aggregate-offered-packets {
                                            type yang:counter64;
                                            description
                                                "The value of aggregate-offered indicates aggregate
                                                 number of hi, lo priority and uncolour packets,
                                                 as determined by the SAP ingress QoS policy,
                                                 offered by the packet processor to the traffic manager.";
                                        }

                                        leaf aggregate-offered-octets {
                                            type yang:counter64;
                                            description
                                                "The value of managed-offered indicates aggregate
                                                 number of hi, lo priority and uncolour octets,
                                                 as determined by the SAP ingress QoS policy,
                                                 offered by the packet processor to the traffic manager.";
                                        }

                                        leaf last-cleared-time {
                                            type yang:date-and-time;
                                            description "Time when the counters in this table were last cleared.";
                                        }

                                    } // container statistics

                                } // container forwarding-engine

                                container traffic-manager {
                                    description "Traffic manager information";

                                    container statistics {
                                        description "Statistics information";

                                        leaf cpm-packets {
                                            type yang:counter64;
                                            description
                                                "The value of cpm-packets indicates
                                                 ingress traffic in terms of packets destined to CPM
                                                 associated with this SAP.";
                                        }

                                        leaf cpm-octets {
                                            type yang:counter64;
                                            description
                                                "The value of cpm indicates
                                                 ingress traffic in terms of bytes destined to CPM
                                                 associated with this SAP.";
                                        }

                                        leaf high-priority-dropped-packets {
                                            type yang:counter64;
                                            description
                                                "The number of high priority packets,
                                                 as determined by the SAP ingress QoS
                                                 policy, dropped by the traffic manager due to:
                                                 MBS exceeded, buffer pool limit
                                                 exceeded, etc.";
                                        }

                                        leaf high-priority-dropped-octets {
                                            type yang:counter64;
                                            description
                                                "The number of high priority octets,
                                                 as determined by the SAP ingress QoS
                                                 policy, dropped by the traffic manager due to:
                                                 MBS exceeded, buffer pool limit
                                                 exceeded, etc.";
                                        }

                                        leaf low-priority-dropped-packets {
                                            type yang:counter64;
                                            description
                                                "The number of low priority packets,
                                                 as determined by the SAP ingress QoS
                                                 policy, dropped by the traffic manager due to:
                                                 MBS exceeded, buffer pool limit
                                                 exceeded, etc.";
                                        }

                                        leaf low-priority-dropped-octets {
                                            type yang:counter64;
                                            description
                                                "The number of low priority octets,
                                                 as determined by the SAP ingress QoS
                                                 policy, dropped by the traffic manager due to:
                                                 MBS exceeded, buffer pool limit
                                                 exceeded, etc.";
                                        }

                                        leaf in-profile-forwarded-packets {
                                            type yang:counter64;
                                            description
                                                "The number of in-profile packets
                                                 (rate below CIR) forwarded by the
                                                 ingress traffic manager.";
                                        }

                                        leaf in-profile-forwarded-octets {
                                            type yang:counter64;
                                            description
                                                "The number of in-profile octets
                                                 (rate below CIR) forwarded by the
                                                 ingress traffic manager.";
                                        }

                                        leaf out-profile-forwarded-packets {
                                            type yang:counter64;
                                            description
                                                "The number of out-of-profile packets
                                                 (rate above CIR) forwarded by the
                                                 ingress traffic manager.";
                                        }

                                        leaf out-profile-forwarded-octets {
                                            type yang:counter64;
                                            description
                                                "The number of out-of-profile octets
                                                 (rate above CIR) forwarded by the
                                                 ingress traffic manager.";
                                        }

                                        leaf aggregate-forwarded-packets {
                                            type yang:counter64;
                                            description
                                                "The aggregate number of in and out-of profile
                                                  packets forwarded by the ingress traffic manager.";
                                        }

                                        leaf aggregate-forwarded-octets {
                                            type yang:counter64;
                                            description
                                                "The aggregate number of in and out-of-profile
                                                 octets forwarded by the ingress traffic manager.";
                                        }

                                        leaf aggregate-dropped-packets {
                                            type yang:counter64;
                                            description
                                                "The aggregate number of in and out-of profile
                                                 packets, dropped by the traffic manager due to:
                                                 MBS exceeded, buffer pool limit
                                                 exceeded, etc.";
                                        }

                                        leaf aggregate-dropped-octets {
                                            type yang:counter64;
                                            description
                                                "The aggregate number of in and out-of profile
                                                 octets, dropped by the traffic manager due to:
                                                 MBS exceeded, buffer pool limit
                                                 exceeded, etc.";
                                        }

                                        leaf last-cleared-time {
                                            type yang:date-and-time;
                                            description "Time when the counters in this table were last cleared.";
                                        }

                                    } // container statistics

                                } // container traffic-manager

                            } // container sap-ingress

                        } // container qos

                    } // container ingress

                    container egress {
                        description "Enter the egress context";

                        container qos {
                            description "Enter the qos context";

                            container sap-egress {
                                description "Enter the sap-egress context";

                                container traffic-manager {
                                    description "Traffic manager information";

                                    container statistics {
                                        description "Statistics information";

                                        leaf in-inplus-profile-dropped-packets {
                                            type yang:counter64;
                                            description
                                                "The number of in-profile packets
                                                 discarded by the egress traffic manager due
                                                 to: MBS exceeded, buffer pool limit
                                                 exceeded, etc.";
                                        }

                                        leaf in-inplus-profile-dropped-octets {
                                            type yang:counter64;
                                            description
                                                "The number of in-profile octets
                                                 discarded by the egress traffic manager due
                                                 to: MBS exceeded, buffer pool limit
                                                 exceeded, etc.";
                                        }

                                        leaf out-exceed-profile-dropped-packets {
                                            type yang:counter64;
                                            description
                                                "The number of out-of-profile packets
                                                 discarded by the egress traffic manager due
                                                 to: MBS exceeded, buffer pool limit
                                                 exceeded, etc.";
                                        }

                                        leaf out-exceed-profile-dropped-octets {
                                            type yang:counter64;
                                            description
                                                "The number of out-of-profile packets
                                                 discarded by the egress traffic manager due
                                                 to: MBS exceeded, buffer pool limit
                                                 exceeded, etc.";
                                        }

                                        leaf in-inplus-profile-forwarded-packets {
                                            type yang:counter64;
                                            description
                                                "The number of in-profile packets
                                                 (rate below CIR) forwarded by the
                                                 egress traffic manager.";
                                        }

                                        leaf in-inplus-profile-forwarded-octets {
                                            type yang:counter64;
                                            description
                                                "The number of in-profile octets
                                                 (rate below CIR) forwarded by the
                                                 egress traffic manager.";
                                        }

                                        leaf out-exceed-profile-forwarded-packets {
                                            type yang:counter64;
                                            description
                                                "The number of out-of-profile packets
                                                 (rate above CIR) forwarded by the
                                                 egress traffic manager.";
                                        }

                                        leaf out-exceed-profile-forwarded-octets {
                                            type yang:counter64;
                                            description
                                                "The number of out-of-profile octets
                                                 (rate above CIR) forwarded by the
                                                 egress traffic manager.";
                                        }

                                        leaf aggregate-forwarded-packets {
                                            type yang:counter64;
                                            description
                                                "The aggregate number of in and out-of profile
                                                 packets forwarded by the egress traffic manager.";
                                        }

                                        leaf aggregate-forwarded-octets {
                                            type yang:counter64;
                                            description
                                                "The aggregate number of in and out-of profile
                                                 octets forwarded by the egress traffic manager.";
                                        }

                                        leaf aggregate-dropped-packets {
                                            type yang:counter64;
                                            description
                                                "The aggregate number of in and out-of profile
                                                 packets discarded by the egress traffic manager due
                                                 to: MBS exceeded, buffer pool limit
                                                 exceeded, etc.";
                                        }

                                        leaf aggregate-dropped-octets {
                                            type yang:counter64;
                                            description
                                                "The aggregate number of in and out-of profile
                                                 octets discarded by the egress traffic manager due
                                                 to: MBS exceeded, buffer pool limit
                                                 exceeded, etc.";
                                        }

                                        leaf last-cleared-time {
                                            type yang:date-and-time;
                                            description "Time when the counters in this table were last cleared.";
                                        }

                                    } // container statistics

                                } // container traffic-manager

                            } // container sap-egress

                        } // container qos

                    } // container egress

                    container lag {
                        description "Lag information.";

                        leaf active-port {
                            type types-sros:port;
                            description
                                "Port on the lag associated with this SAP, that is used when
                                 lag-per-link-hash is enabled on the lag or when lag-link-map-profile
                                 is configured on this SAP.";
                        }

                        container per-link-hash-oper {
                            description "Lag per-link-hash information.";

                            leaf class {
                                type int32;
                                description "Operational value for class associated with this SAP.";
                            }

                            leaf weight {
                                type int32;
                                description "Operational value used for weight associated with this SAP.";
                            }

                            leaf is-overriden {
                                type boolean;
                                description
                                    "Whether administrative values, subscriber management determined
                                     operational weight and class are used for this SAP.";
                            }

                        } // container per-link-hash-oper

                    } // container lag

                    container static-host {
                        description "Enter the static-host context";

                        list ipv4 {
                            key "ip mac";
                            description "Enter the ipv4 context";

                            leaf ip {
                                type types-sros:ipv4-unicast-address;
                                description "IP address used by the static host.";
                            }

                            leaf mac {
                                type types-sros:mac-unicast-address;
                                description "MAC address of the static host.";
                            }

                            leaf dynamic-mac {
                                type yang:mac-address;
                                description "The dynamically learned MAC address for this host.";
                            }

                            leaf retail-service {
                                type types-services:service-name;
                                description
                                    "The service name of the retailer service
                                     to which this static host belongs.";
                            }

                            leaf retail-interface {
                                type types-sros:named-item;
                                description
                                    "The interface name of the retailer service interface to which
                                     this static host belongs.";
                            }

                            leaf forwarding-state {
                                type types-sros:oper-state;
                                description "Forwarding state of this static host.";
                            }

                            leaf oper-rip-policy {
                                type types-sros:named-item;
                                description "RIP policy which is used to set up the RIP listener for this static host.";
                            }

                            leaf esm-rip-status {
                                type enumeration {
                                    enum "not-applicable"               { value 0; }
                                    enum "active"                       { value 1; }
                                    enum "inactive"                     { value 2; }
                                    enum "no-esm"                       { value 3; }
                                    enum "wrong-anti-spoof"             { value 4; }
                                    enum "parent-interface-down"        { value 5; }
                                    enum "host-inactive"                { value 6; }
                                    enum "l2-aware-not-supported"       { value 7; }
                                    enum "gtp-not-supported"            { value 8; }
                                    enum "mc-standby"                   { value 9; }
                                    enum "rip-disabled"                 { value 10; }
                                }
                                description "Indicates the status of the RIP listener.";
                            }

                            container shcv {
                                description "Enter the shcv context";

                                leaf oper-state {
                                    type enumeration {
                                        enum "disabled"                     { value 1; }
                                        enum "down"                         { value 2; }
                                        enum "up"                           { value 3; }
                                    }
                                    description
                                        "The state of the subscriber host connectivity
                                         check for this static host.";
                                }

                                leaf checks {
                                    type yang:gauge32;
                                    description "The number of connectivity checks for this static host.";
                                }

                                leaf replies {
                                    type yang:gauge32;
                                    description "The number of host replies for this static host.";
                                }

                                leaf reply-time {
                                    type yang:timestamp;
                                    description
                                        "The timestamp of the last successful connectivity
                                         check for this static host.";
                                }

                            } // container shcv

                            list managed-route {
                                key "prefix";
                                description "Enter the managed-route context";

                                leaf prefix {
                                    type types-sros:ipv4-unicast-prefix;
                                    description "Managed route prefix.";
                                }

                                leaf status {
                                    type enumeration {
                                        enum "installed"                    { value 0; }
                                        enum "not-installed"                { value 1; }
                                        enum "wrong-anti-spoof"             { value 2; }
                                        enum "out-of-memory"                { value 3; }
                                        enum "shadowed"                     { value 4; }
                                        enum "route-table-full"             { value 5; }
                                        enum "parent-interface-down"        { value 6; }
                                        enum "host-inactive"                { value 7; }
                                        enum "esm-required"                 { value 8; }
                                        enum "l2-aware-not-supported"       { value 9; }
                                        enum "next-hop-limit-exceeded"      { value 10; }
                                        enum "not-applicable"               { value 11; }
                                        enum "no-next-hop"                  { value 12; }
                                        enum "gtp-not-supported"            { value 13; }
                                    }
                                    description "The state of this managed route.";
                                }

                            } // list managed-route

                        } // list ipv4

                        list ipv6 {
                            key "prefix mac";
                            description "Enter the ipv6 context";

                            leaf prefix {
                                type types-sros:ipv6-unicast-prefix;
                                description "IPv6 prefix";
                            }

                            leaf mac {
                                type types-sros:mac-unicast-address;
                                description "MAC address";
                            }

                            leaf dynamic-mac {
                                type yang:mac-address;
                                description "The dynamically learned MAC address for this host.";
                            }

                            leaf retail-service {
                                type types-services:service-name;
                                description
                                    "The service name of the retailer service
                                     to which this static host belongs.";
                            }

                            leaf retail-interface {
                                type types-sros:named-item;
                                description
                                    "The interface name of the retailer service interface to which
                                     this static host belongs.";
                            }

                            leaf forwarding-state {
                                type types-sros:oper-state;
                                description "Forwarding state of this static host.";
                            }

                            container shcv {
                                description "Enter the shcv context";

                                leaf oper-state {
                                    type enumeration {
                                        enum "disabled"                     { value 1; }
                                        enum "down"                         { value 2; }
                                        enum "up"                           { value 3; }
                                    }
                                    description
                                        "The state of the subscriber host connectivity
                                         check for this static host.";
                                }

                                leaf checks {
                                    type yang:gauge32;
                                    description "The number of connectivity checks for this static host.";
                                }

                                leaf replies {
                                    type yang:gauge32;
                                    description "The number of host replies for this static host.";
                                }

                                leaf reply-time {
                                    type yang:timestamp;
                                    description
                                        "The timestamp of the last successful connectivity
                                         check for this static host.";
                                }

                            } // container shcv

                            list managed-route {
                                key "ipv6-prefix";
                                description "Enter the managed-route context";

                                leaf ipv6-prefix {
                                    type types-sros:ipv6-unicast-prefix;
                                    description "Managed route prefix.";
                                }

                                leaf status {
                                    type enumeration {
                                        enum "installed"                    { value 0; }
                                        enum "not-installed"                { value 1; }
                                        enum "wrong-anti-spoof"             { value 2; }
                                        enum "out-of-memory"                { value 3; }
                                        enum "shadowed"                     { value 4; }
                                        enum "route-table-full"             { value 5; }
                                        enum "parent-interface-down"        { value 6; }
                                        enum "host-inactive"                { value 7; }
                                        enum "esm-required"                 { value 8; }
                                        enum "l2-aware-not-supported"       { value 9; }
                                        enum "next-hop-limit-exceeded"      { value 10; }
                                        enum "not-applicable"               { value 11; }
                                        enum "no-next-hop"                  { value 12; }
                                        enum "gtp-not-supported"            { value 13; }
                                    }
                                    description "The state of this managed route.";
                                }

                            } // list managed-route

                        } // list ipv6

                    } // container static-host

                    container igmp-host-tracking {
                        description "Enter the igmp-host-tracking context";

                        leaf group-count {
                            type int32;
                            description "The number of multicast groups which have been learned on this interface.";
                        }

                        list host-statistics {
                            key "host-address";
                            description "Statistics associated with this multicast stream";

                            leaf host-address {
                                type types-sros:ipv4-address;
                                description "The IP address of this host.";
                            }

                            leaf v2-reports {
                                type yang:counter32;
                                description "V2 Reports.";
                            }

                            leaf leaves {
                                type yang:counter32;
                                description "V2 Leaves.";
                            }

                            leaf v3-reports {
                                type yang:counter32;
                                description "V3 Reports.";
                            }

                            leaf drops {
                                type yang:counter32;
                                description "Total number of dropped packets.";
                            }

                            leaf group-joins {
                                type yang:counter32;
                                description "Total number of joins.";
                            }

                            leaf group-leaves {
                                type yang:counter32;
                                description "Total number of leaves.";
                            }

                            leaf group-expiries {
                                type yang:counter32;
                                description "Total number of group expiries.";
                            }

                            leaf import-policy-drops {
                                type yang:counter32;
                                description
                                    "Number of times we matched the host IP address or
                                     group or source addresses specified in the import
                                     policy.";
                            }

                            leaf maximum-number-groups-drops {
                                type yang:counter32;
                                description
                                    "Number of times a join is dropped because we reached
                                     the maximum number of groups.";
                            }

                            leaf maximum-number-sources-drops {
                                type yang:counter32;
                                description
                                    "Number of times a join is dropped because we reached
                                     the maximum number of sources per group.";
                            }

                            leaf maximum-number-group-sources-drops {
                                type yang:counter32;
                                description
                                    "Number of times a join is dropped because we reached
                                     the maximum number group-source combinations.";
                            }

                        } // list host-statistics

                        list host-group-sources {
                            key "host-address group-address source-address";
                            description
                                "Information about a particular host associated with this
                                 multicast stream";

                            leaf host-address {
                                type types-sros:ipv4-address;
                                description "The IP address of this host.";
                            }

                            leaf group-address {
                                type types-sros:ipv4-multicast-address;
                                description "Group address of multicast channel";
                            }

                            leaf source-address {
                                type types-sros:ipv4-address;
                                description "Source address of multicast channel.";
                            }

                            leaf bandwidth {
                                type uint32;
                                units "kilobps";
                                description
                                    "The bandwidth allocated to this host for this multicast
                                     stream.";
                            }

                            leaf uptime {
                                type uint32;
                                units "seconds";
                                description "The time elapsed since this entry was created.";
                            }

                            leaf expiry-time {
                                type uint32;
                                units "seconds";
                                description "The time remaining before this entry is aged out.";
                            }

                            leaf subscriber-id {
                                type types-sros:named-item;
                                description "The subscriber identification of this subscriber host.";
                            }

                        } // list host-group-sources

                    } // container igmp-host-tracking

                    container pppoe {
                        description "PPPoE state.";

                        container statistics {
                            description "PPPoE statistics.";

                            container rx {
                                description "RX statistics.";

                                leaf padi {
                                    type yang:counter32;
                                    description "Number of PADI (PPPoE Active Discovery Initiation) packets.";
                                }

                                leaf padr {
                                    type yang:counter32;
                                    description "Number of PADR (PPPoE Active Discovery Request) packets.";
                                }

                                leaf padt {
                                    type yang:counter32;
                                    description "Number of PADT (PPPoE Active Discovery Terminate) packets.";
                                }

                                leaf session {
                                    type yang:counter32;
                                    description "Number of PPP session stage packets.";
                                }

                                leaf invalid-version {
                                    type yang:counter32;
                                    description "Number of PPPoE packets with an invalid version field.";
                                }

                                leaf invalid-type {
                                    type yang:counter32;
                                    description "Number of PPPoE packets with an invalid type field.";
                                }

                                leaf invalid-code {
                                    type yang:counter32;
                                    description "Number of PPPoE packets with an invalid code field.";
                                }

                                leaf invalid-session {
                                    type yang:counter32;
                                    description "Number of PPPoE packets with an invalid session-id field.";
                                }

                                leaf invalid-len {
                                    type yang:counter32;
                                    description "Number of PPPoE packets with an invalid length field.";
                                }

                                leaf invalid-tags {
                                    type yang:counter32;
                                    description "Number of PPPoE Active Discovery packets with invalid tags.";
                                }

                                leaf invalid-ac-cookie {
                                    type yang:counter32;
                                    description "Number of PPPoE Active Discovery packets with an invalid AC-Cookie tag.";
                                }

                                leaf invalid-mac {
                                    type yang:counter32;
                                    description "Number of PPPoE packets with an invalid MAC address.";
                                }

                                leaf dropped {
                                    type yang:counter32;
                                    description "Number of dropped PPPoE packets.";
                                }

                            } // container rx

                            container tx {
                                description "TX statistics.";

                                leaf pado {
                                    type yang:counter32;
                                    description "Number of PADO (PPPoE Active Discovery Offer) packets.";
                                }

                                leaf pads {
                                    type yang:counter32;
                                    description "Number of PADS (PPPoE Active Discovery Session) packets.";
                                }

                                leaf padt {
                                    type yang:counter32;
                                    description "Number of PADT (PPPoE Active Discovery Terminate) packets.";
                                }

                                leaf session {
                                    type yang:counter32;
                                    description "Number of PPP session stage packets.";
                                }

                            } // container tx

                        } // container statistics

                    } // container pppoe

                    container msap {
                        description "Managed SAPs.";

                        leaf capture-sap-id {
                            type types-sros:sap;
                            description "SAP identifier of the capture sap that created this MSAP";
                        }

                        leaf capture-service {
                            type types-services:service-name;
                            description "Service identifier of the capture sap that created this MSAP";
                        }

                        leaf msap-policy {
                            type types-sros:named-item;
                            description "The msap-policy used to create this MSAP";
                        }

                        leaf idle {
                            type boolean;
                            description "A managed SAP is considered idle when no hosts are associated with it.";
                        }

                        leaf sticky {
                            type boolean;
                            description "A sticky managed SAP will not be removed automatically.";
                        }

                    } // container msap

                    container data-trigger {
                        description "Per SAP information on data-triggered hosts and mac-learning.";

                        container statistics {
                            description "Data-trigger packet statistics.";

                            leaf rx-total {
                                type yang:counter32;
                                description "The total number of data triggers received on this SAP";
                            }

                            leaf rx-dynamic-business-service {
                                type yang:counter32;
                                description "The number of data triggers received on a dynamic business service SAP";
                            }

                            leaf rx-ipv4 {
                                type yang:counter32;
                                description "The number of IPv4 data triggers received on this SAP";
                            }

                            leaf rx-ipv6 {
                                type yang:counter32;
                                description "The number of IPv6 data triggers received on this SAP";
                            }

                            leaf accepted-dynamic-business-service {
                                type yang:counter32;
                                description
                                    "The number of data triggers accepted and passed on for further procerssing
                                     on a dynamic business service SAP.";
                            }

                            leaf accepted-ipv4 {
                                type yang:counter32;
                                description
                                    "The number of IPv4 data triggers accepted and passed on for
                                     further procerssing on this SAP.";
                            }

                            leaf accepted-ipv6 {
                                type yang:counter32;
                                description
                                    "The number of IPv6 data triggers accepted and passed on for further
                                     procerssing on this SAP.";
                            }

                            container dropped {

                                leaf invalid-mac {
                                    type yang:counter32;
                                    description "The number of packets dropped because of invalid source or destination MAC address on this SAP";
                                }

                                leaf invalid-ipv6-header {
                                    type yang:counter32;
                                    description "The number of packets dropped because of an invalid IPv6 header on this SAP";
                                }

                                leaf invalid-ipv6-source {
                                    type yang:counter32;
                                    description "The number of packets dropped because of an invalid IPv6 source address on this SAP";
                                }

                                leaf non-existing-ipv6-host {
                                    type yang:counter32;
                                    description "The number of packets dropped because the ipv6 host is unknown in the system";
                                }

                                leaf invalid-ipv4-header {
                                    type yang:counter32;
                                    description "The number of packets dropped because of an invalid IPv4 header on this SAP";
                                }

                                leaf invalid-ipv4-source {
                                    type yang:counter32;
                                    description "The number of packets dropped because of an invalid IPv4 source address on this SAP";
                                }

                                leaf non-existing-ipv4-host {
                                    type yang:counter32;
                                    description "The number of packets dropped because the ipv4 host is unknown in the system";
                                }

                                leaf out-of-memory {
                                    type yang:counter32;
                                    description "The number of packets dropped because the system runs out of processing memory";
                                }

                                leaf unsupported-protocol {
                                    type yang:counter32;
                                    description "The number of packets dropped because the protocol is not supported";
                                }

                            } // container dropped

                        } // container statistics

                    } // container data-trigger

                    container arp-host {
                        description "Hosts created by ARP triggers";

                        container statistics {

                            leaf last-cleared-time {
                                type yang:date-and-time;
                                description "The last time that these stats were cleared";
                            }

                            leaf hosts {
                                type yang:gauge32;
                                description "The actual number of ARP hosts on this SAP";
                            }

                            leaf triggers-received {
                                type yang:counter32;
                                description "The number of ARP triggers received on this SAP";
                            }

                            leaf error-triggers-dropped {
                                type yang:counter32;
                                description "ARP triggers that are dropped due to various error conditions";
                            }

                            leaf overload-triggers-dropped {
                                type yang:counter32;
                                description
                                    "ARP triggers that are dropped because of too many outstanding
                                     requests";
                            }

                            leaf forced-verifications {
                                type yang:counter32;
                                description "The number of times a host connectivity verification was forced";
                            }

                            leaf hosts-created {
                                type yang:counter32;
                                description "The number of times an ARP host was created on this SAP";
                            }

                            leaf hosts-deleted {
                                type yang:counter32;
                                description "The number of times an ARP host was deleted on this SAP";
                            }

                            leaf hosts-updated {
                                type yang:counter32;
                                description "The number of times an ARP host was updated on this SAP";
                            }

                            leaf authentication-requests {
                                type yang:counter32;
                                description
                                    "The number of times an authentication request was initiated
                                     by the system for an ARP host on this SAP";
                            }

                        } // container statistics

                    } // container arp-host

                    list locked-out-host {
                        key "id";
                        description "A locked out host";

                        leaf id {
                            type uint32;
                            description "Id of the locked out host";
                        }

                        leaf mac-address {
                            type yang:mac-address;
                            description "Mac-address of the locked out host";
                        }

                        leaf circuit-id {
                            type binary {
                                length "1..256";
                            }
                            description "Circuit-id of the locked out host";
                        }

                        leaf remote-id {
                            type binary {
                                length "1..256";
                            }
                            description "Remote-id of the locked out host";
                        }

                        leaf elapsed-reset-time {
                            type uint32;
                            units "seconds";
                            description "Elapsed reset time";
                        }

                        leaf elapsed-lock-time {
                            type uint32;
                            units "seconds";
                            description "Elapsed lock time";
                        }

                        leaf current-lock-timeout {
                            type uint32;
                            units "seconds";
                            description "The timeout for the current lock interval";
                        }

                        leaf next-lock-timeout {
                            type uint32;
                            units "seconds";
                            description "The timeout for the next lock interval";
                        }

                        leaf lockout-count {
                            type uint32;
                            description "Number of lockouts";
                        }

                        leaf lockout-state {
                            type enumeration {
                                enum "graceful"                     { value 1; description "The host is allowed to authenticate and the reset timer
                                is running. Another authentication failure for this host
                                while in this state while change the state to active.
                                If the reset timer expires, the lock out for this host
                                is removed."; }
                                enum "active"                       { value 2; description "The host is not allowed to authenticate and the lock-out
                                timer is running. When the timer expires, the state is
                                changed to graceful."; }
                            }
                            description "Lockout state for this host";
                        }

                    } // list locked-out-host

                } // list sap

                container statistics {
                    description "Statistics information about ies group interface.";

                    container ip {
                        description "Interface IP statistics.";

                        leaf out-packets {
                            type yang:counter64;
                            description "The number of packets transmitted by this interface.";
                        }

                        leaf out-octets {
                            type yang:counter64;
                            description "The number of octets transmitted by this interface.";
                        }

                        leaf out-discard-packets {
                            type yang:counter64;
                            description "The number of transmit packets discarded.";
                        }

                        leaf out-discard-octets {
                            type yang:counter64;
                            description "The number of transmit octets discarded.";
                        }

                        leaf in-packets {
                            type yang:counter64;
                            description "The number of packets received.";
                        }

                        leaf in-octets {
                            type yang:counter64;
                            description "The number of octets received.";
                        }

                        leaf urpf-check-fail-packets {
                            type yang:counter64;
                            description "The number of packets that fail uRPF check on this interface.";
                        }

                        leaf urpf-check-fail-octets {
                            type yang:counter64;
                            description "The number of octets in the packets that fail uRPF check.";
                        }

                    } // container ip

                    list mac {
                        key "mac-address";
                        description "Mac-accounting statistics";

                        leaf mac-address {
                            type yang:mac-address;
                            description "Mac-address";
                        }

                        leaf out-packets {
                            type yang:counter64;
                            description "The number of packets sent to the mac address";
                        }

                        leaf out-octets {
                            type yang:counter64;
                            description "The number of bytes sent to the mac address";
                        }

                        leaf in-packets {
                            type yang:counter64;
                            description "The number of packets received from the mac address";
                        }

                        leaf in-octets {
                            type yang:counter64;
                            description "The number of bytes received from the mac address";
                        }

                    } // list mac

                } // container statistics

                uses state-svc-ies-grp-if-wlangw-wlan-gw;
            } // list group-interface

            container statistics {
                description "Statistics information about ies subscriber interface.";

                container ip {
                    description "Interface IP statistics.";

                    leaf out-packets {
                        type yang:counter64;
                        description "The number of packets transmitted by this interface.";
                    }

                    leaf out-octets {
                        type yang:counter64;
                        description "The number of octets transmitted by this interface.";
                    }

                    leaf out-discard-packets {
                        type yang:counter64;
                        description "The number of transmit packets discarded.";
                    }

                    leaf out-discard-octets {
                        type yang:counter64;
                        description "The number of transmit octets discarded.";
                    }

                    leaf in-packets {
                        type yang:counter64;
                        description "The number of packets received.";
                    }

                    leaf in-octets {
                        type yang:counter64;
                        description "The number of octets received.";
                    }

                    leaf urpf-check-fail-packets {
                        type yang:counter64;
                        description "The number of packets that fail uRPF check on this interface.";
                    }

                    leaf urpf-check-fail-octets {
                        type yang:counter64;
                        description "The number of octets in the packets that fail uRPF check.";
                    }

                } // container ip

                list mac {
                    key "mac-address";
                    description "Mac-accounting statistics";

                    leaf mac-address {
                        type yang:mac-address;
                        description "Mac-address";
                    }

                    leaf out-packets {
                        type yang:counter64;
                        description "The number of packets sent to the mac address";
                    }

                    leaf out-octets {
                        type yang:counter64;
                        description "The number of bytes sent to the mac address";
                    }

                    leaf in-packets {
                        type yang:counter64;
                        description "The number of packets received from the mac address";
                    }

                    leaf in-octets {
                        type yang:counter64;
                        description "The number of bytes received from the mac address";
                    }

                } // list mac

            } // container statistics

            uses state-svc-ies-sub-if-wlangw-wlan-gw;
        } // list subscriber-interface

    } // grouping state-svc-ies-sub-if-subscriber-interface

}
