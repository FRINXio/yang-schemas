module nokia-types-li {

    yang-version "1.1";

    namespace "urn:nokia.com:sros:ns:yang:sr:types-li-filter";

    prefix "types-li-filter";

    import nokia-sros-yang-extensions     { prefix "sros-ext"; }


    sros-ext:sros-major-release "rel16";

    organization "Nokia";

    contact
        "Nokia SR OS Support
         Web: <http://www.nokia.com>";

    description
        "Common li-filter data types used in the SR OS management system.

         Copyright 2016 Nokia. All rights reserved. Reproduction of this document
         is authorized on the condition that the foregoing copyright notice is included.

         This nokia-types-li YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2017-03-03";

    typedef li-filter-name {
        type string {
            length "1..32";
        }
        description "The name of a li filter.";
    }

    typedef filter-type {
        type enumeration {
            enum "ipv4"                         { value 1; }
            enum "mac"                          { value 2; }
            enum "ipv6"                         { value 4; }
        }
        description
            "The type of the system filter policy to be selected as
             the active system filter policy";
    }

    typedef operator {
        type enumeration {
            enum "none"                         { value 0; }
            enum "eq"                           { value 1; }
            enum "range"                        { value 2; }
            enum "lt"                           { value 3; }
            enum "gt"                           { value 4; }
        }
        description "Comparison operator.";
    }

    typedef port-number {
        type int32 {
            range "0|1..65535";
        }
        description "The port number.";
    }

}
