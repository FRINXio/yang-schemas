module nokia-types-filter {

    yang-version "1.1";

    namespace "urn:nokia.com:sros:ns:yang:sr:types-filter";

    prefix "types-filter";

    import ietf-yang-types                { prefix "yang"; }
    import nokia-sros-yang-extensions     { prefix "sros-ext"; }
    import nokia-types-sros               { prefix "types-sros"; }


    sros-ext:sros-major-release "rel16";

    organization "Nokia";

    contact
        "Nokia SR OS Support
         Web: <http://www.nokia.com>";

    description
        "Common filter data types used in the SR OS management system.

         Copyright 2016 Nokia. All rights reserved. Reproduction of this document
         is authorized on the condition that the foregoing copyright notice is included.

         This nokia-types-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-12-03";

    typedef filter-log-id {
        type uint32 {
            range "101..199";
        }
    }

    typedef filter-log-summary-criterion {
        type enumeration {
            enum "src-addr"                     { value 0; }
            enum "dst-addr"                     { value 1; }
        }
        description
            "Indicates the field on which log summarization will be done.
             - when set to srcAddr, received log packets are summarized
               based on the src ip/mac-addr
             - when set to dstAddr, received log packets are summarized
               based on the dst ip/mac-addr";
    }

    typedef filter-id {
        type uint32 {
            range "1..65535";
        }
        description "The identification number of a filter.";
    }

    typedef filter-name {
        type string {
            length "1..64";
        }
        description
            "Named item used for naming filters.
             Filter name must not start with a digit.";
    }

    typedef embed-offset {
        type uint32 {
            range "0..2097151";
        }
        description
            "Insertion offset of entries of an embedded filter into an embedding
             filter. An entry at position x in the embedded filter is inserted
             at position x + offset in the embedding filter.";
    }

    typedef oid {
        type yang:object-identifier-128 {
            length "1..2048";
            pattern "((0(\\.([1-9]|[1-3][0-9])))|(0(\\.[1-3]?[0-9]))(\\.(0|([1-9]\\d*)))+|((1(\\.[1-3]?[0-9]))|(2\\.(0|([1-9]\\d*))))(\\.(0|([1-9]\\d*)))*)";
            pattern "\\d*(\\.\\d*){1,127}";
            pattern "(([0-1](\\.[1-3]?[0-9]))|(2\\.(0|([1-9]\\d*))))(\\.(0|([1-9]\\d*)))*";
        }
        description "This type represents object-identifier-128 excluding OID zeroDotZero.";
    }

    typedef entry-id {
        type uint32 {
            range "1..2097151";
        }
        description
            "Uniquely identifies an entry in a policy or filter table.
             To facilitate insertion of entries in the tables, we recommend
             assigning entry IDs by 10s:  10, 20, 30, etc.";
    }

    typedef entry-block-size {
        type entry-id {
            range "1..65535";
        }
        description "Defines size of block used for filter entries insertion.";
    }

    typedef limited-entry-id {
        type entry-id {
            range "1..65535";
        }
        description
            "Uniquely identifies an entry in a policy or filter table.
             To facilitate insertion of entries in the tables, we recommend
             assigning entry IDs by 10s:  10, 20, 30, etc.";
    }

    typedef mac-frame-type {
        type enumeration {
            enum "802dot3"                      { value 0; }
            enum "802dot2-llc"                  { value 1; }
            enum "802dot2-snap"                 { value 2; }
            enum "ethernet-ii"                  { value 3; }
        }
        description "The frame type in a MAC address filter.";
    }

    typedef filter-default-action {
        type enumeration {
            enum "drop"                         { value 1; }
            enum "accept"                       { value 2; }
        }
        description
            "The default action of a filter.
             - drop        (1): packets matching the filter entry are dropped.
             - accept      (2): packets matching the filter entry are accepted.";
    }

    typedef filter-scope {
        type enumeration {
            enum "exclusive"                    { value 1; }
            enum "template"                     { value 2; }
            enum "embedded"                     { value 3; }
            enum "system"                       { value 4; }
        }
        description "The scope of a filter.";
    }

    typedef filter-downloaded-action {
        type enumeration {
            enum "none"                         { value 1; }
            enum "primary"                      { value 2; }
            enum "secondary"                    { value 3; }
            enum "forward"                      { value 4; }
            enum "drop"                         { value 5; }
            enum "not-applicable"               { value 6; }
        }
        description
            "Filter action downloaded to IOM:
             - none          (1): No filter entry action is downloaded to IOM.
                                  Entry is inactive or filter is not applied.
             - primary       (2): Primary filter entry action is downloaded to IOM.
             - secondary     (3): Secondary filter entry action is downloaded to
                                  IOM.
             - forward       (4): Neither primary nor secondary action is downloaded
                                  to IOM. Action forward is downloaded to IOM.
             - drop          (5): Neither primary nor secondary action is downloaded
                                  to IOM. Action drop is downloaded to IOM.
             - not-applicable (6): Field is not supported for configured action.";
    }

    typedef filter-pbr-down-action-ovr {
        type enumeration {
            enum "drop"                         { value 1; }
            enum "forward"                      { value 2; }
            enum "filter-default-action"        { value 3; }
        }
        description
            "The textual convention TFilterPbrDownActionOvr specifies an override of
             default PBR down action:
             - none                  (0): default PBR down action is applied to
                                          packets matching the filter entry.
                                          Default PBR down action is either drop
                                          or forward based on PBR action type.
             - drop                  (1): packets matching the filter entry are
                                          dropped.
             - forward               (2): packets matching the filter entry are
                                          forwarded.
             - filter-default-action (3): packets matching the filter entry are
                                          handled according to filter default action
                                          configured using tIPFilterDefaultAction
                                          for IP filter, tIPv6FilterDefaultAction
                                          for IPv6 filter and
                                          tMacFilterDefaultAction for MAC filter.";
    }

    typedef isa-filter-default-action {
        type enumeration {
            enum "drop"                         { value 1; description "Packets matching the filter entry are dropped"; }
            enum "forward"                      { value 2; description "Packets matching the filter entry are forwarded"; }
        }
        default "drop";
        description "The default action of an ISA filter";
    }

    typedef nat-type {
        type enumeration {
            enum "dslite"                       { value 3; }
            enum "nat64"                        { value 4; }
        }
        description "Specifies the NAT type.";
    }

    typedef rate-limit {
        type union {
            type uint32 {
                range "0..2000000000";
            }
            type enumeration {
                enum "max"                          { value -1; }
            }
        }
        description
            "A limiting rate in kilobits per second for traffic matching
             the filter entry. The value -1 means max rate.";
    }

    typedef ttl-or-hop-limit-value {
        type int32 {
            range "0..255";
        }
    }

    typedef ttl-or-hop-limit-lt-value {
        type ttl-or-hop-limit-value {
            range "1..max";
        }
    }

    typedef ttl-or-hop-limit-gt-value {
        type ttl-or-hop-limit-value {
            range "min..254";
        }
    }

    typedef pkt-len-or-payload-len-value {
        type int32 {
            range "0..65535";
        }
    }

    typedef pkt-len-or-payload-len-lt-value {
        type pkt-len-or-payload-len-value {
            range "1..max";
        }
    }

    typedef pkt-len-or-payload-len-gt-value {
        type pkt-len-or-payload-len-value {
            range "min..65534";
        }
    }

    typedef embed-oper-state {
        type enumeration {
            enum "failed-no-resources"          { value -1; }
            enum "inactive"                     { value 0; }
            enum "active"                       { value 1; }
        }
        description "embed-oper-state specifies operational states of filter embedding.";
    }

    typedef pbr-target-status {
        type enumeration {
            enum "unknown"                      { value 0; }
            enum "does-not-exist"               { value 1; }
            enum "up"                           { value 2; }
            enum "down"                         { value 3; }
            enum "router-specific"              { value 4; }
        }
        description
            "Status of PBR target :
             - unknown           (0): Status of PBR target is not tracked
             - does-not-exist    (1): The system does not know the PBR target.
             - up                (2): PBR target is known by the system and can be
                                      used for forwarding the traffic.
             - down              (3): PBR target is known by the system but can't be
                                      used for forwarding the traffic.
             - router-specific   (4): PBR target status depends on service where filter
                                      is applied.";
    }

    typedef filter-egress-pbr {
        type enumeration {
            enum "true"                         { value 1; }
            enum "true-with-l4lb"               { value 2; }
        }
        description
            "true          - 1: egress policy based routing is allowed and default
                              load-balancing based on hash of source/destination
                              address of the packet is applied
             true-with-l4lb - 2: egress policy based routing is allowed and
                              l4-load-balancing is applied (if available include
                              TCP/UDP port in hash.";
    }

    typedef ipv4-match-icmp-codes {
        type int32 {
            range "0..255";
        }
        description "IP icmp code numbers.";
    }

    typedef ipv6-match-icmp-codes {
        type int32 {
            range "0..255";
        }
        description "IPv6 icmp code numbers.";
    }

    typedef ipv4-match-icmp-types {
        type int32 {
            range "0..255";
        }
        description "IP icmp type numbers.";
    }

    typedef ipv6-match-icmp-types {
        type int32 {
            range "0..255";
        }
        description "IPv6 icmp type numbers.";
    }

    typedef filter-match-ip-option {
        type types-sros:ip-option;
    }

    typedef redirect-policy-test-last-action {
        type enumeration {
            enum "enabled"                      { value 1; }
            enum "disabled"                     { value 2; }
            enum "none"                         { value 3; }
        }
        description
            "This typedef is used to indicate the last impact of a test
             assigned to a destination of a redirect policy on an operational state
             of the destination.

             Value 'enabled' indicates the operational state of the destination
             has been set to 'inService'.

             Value 'disabled' indicates the operational state of the destination
             has been set to 'outOfService'.

             Value 'none' indicates the operational state of the destination
             has not been changed yet.";
    }

    typedef filter-sticky-dest {
        type union {
            type int32 {
                range "0..65535";
            }
            type enumeration {
                enum "no-hold-time-up"              { value 0; }
            }
        }
        units "seconds";
        description
            "This typedef is used to enable feature of destination stickiness
             and to specify the time how long will system wait until
             it sets and fixes the current best destination as active destination.

             After the value of active destination is fixed it will remain unchanged until the
             active destination becomes unreachable. When the value of
             sticky-dest is -1 the property of destination stickiness is
             turned off. That means that active destination is always the best one.
             The countdown starts when there was no destination reachable and any
             destination becomes reachable.";
    }

    typedef filter-gre-tunnel-gre-key {
        type union {
            type enumeration {
                enum "if-index"                     { value -2; }
            }
            type uint32;
        }
        description "This typedef is used to set gre-key value for gre-tunnel-template.";
    }

    typedef maf-action {
        type enumeration {
            enum "ignore-match"                 { value 0; }
            enum "accept"                       { value 1; }
            enum "drop"                         { value 2; }
            enum "reject"                       { value 3; }
        }
        description
            "Action to take be taken as a result of matching the configured
             criteria in a Management Access Filter.
             none   (0) - no action specified, follow default behavior.
             permit (1) - packets matching the configured criteria are
                          permitted.
             deny   (2) - packets matching the configured criteria are
                          denied and an ICMP host unreachable message
                          is issued.
             denyHostUnreachable (3) - packets matching the configured criteria
                                       are denied and no ICMP host unreachable
                                       message is issued.";
    }

    typedef maf-mac-action {
        type enumeration {
            enum "ignore-match"                 { value 0; }
            enum "accept"                       { value 1; }
            enum "drop"                         { value 2; }
        }
        description
            "Action to take be taken as a result of matching the configured
             criteria in a Management Access Filter.
             none   (0) - no action specified, follow default behavior.
             permit (1) - packets matching the configured criteria are
                          permitted.
             deny   (2) - packets matching the configured criteria are
                          denied and an ICMP host unreachable message
                          is issued.";
    }

    typedef filter-match-flow-label {
        type int32 {
            range "0..1048575";
        }
        description "This typedef is used to specify flow label match criterion used in filters.";
    }

    typedef filter-binding-operator {
        type enumeration {
            enum "and"                          { value 0; }
            enum "or"                           { value 1; }
        }
        description
            "This typedef is used to specify the logical operator to use for combining destinations'
             tests results to form the operational state of the whole binding.";
    }

}
