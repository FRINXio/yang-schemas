submodule Cisco-IOS-XR-ip-tcp-oper-sub2 {

  belongs-to Cisco-IOS-XR-ip-tcp-oper {
    prefix Cisco-IOS-XR-ip-tcp-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-tcp package operational data.

     Copyright (c) 2013-2017 by Cisco Systems, Inc.
     All rights reserved.";

  revision "2018-02-14" {
    description
      "PCB_ID argument is passed in string format.";
  }

  revision "2017-05-01" {
    description
      "Fixing backward compatibility error in module.";
  }

  revision "2016-02-26" {
    description
      "Descriptions updated.";
  }

  revision "2015-11-09" {
    description
      "IOS XR 6.0 revision.";
  }


  grouping IP-TCP {
    description "TCP Traffic Information";
    leaf tcp-input-packets {
      type uint32;
      description "TCP packets received";
    }
    leaf tcp-checksum-error-packets {
      type uint32;
      description "TCP packets with checksum errors";
    }
    leaf tcp-dropped-packets {
      type uint32;
      description "TCP packets dropped (no port)";
    }
    leaf tcp-output-packets {
      type uint32;
      description "TCP packets transmitted";
    }
    leaf tcp-retransmitted-packets {
      type uint32;
      description "TCP packets retransmitted";
    }
  }
}
