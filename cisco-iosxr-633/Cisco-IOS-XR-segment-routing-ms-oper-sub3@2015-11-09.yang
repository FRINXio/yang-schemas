submodule Cisco-IOS-XR-segment-routing-ms-oper-sub3 {

  belongs-to Cisco-IOS-XR-segment-routing-ms-oper {
    prefix Cisco-IOS-XR-segment-routing-ms-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR segment-routing-ms package operational data.

     Copyright (c) 2013-2017 by Cisco Systems, Inc.
     All rights reserved.";

  revision "2015-11-09" {
    description
      "IOS XR 6.0 revision.";
  }

  typedef Srms-mi-flag-e-b {
    type enumeration {
      enum false {
        value 0;
        description "False";
      }
      enum true {
        value 1;
        description "True";
      }
    }
    description "Srms mi flag e b";
  }
  typedef In6-addr-t-b {
    type inet:ipv6-address;
    description "In6 addr t b";
  }
  typedef Srms-mi-af-e-b {
    type enumeration {
      enum none {
        value 0;
        description "None";
      }
      enum ipv4 {
        value 1;
        description "IPv4";
      }
      enum ipv6 {
        value 2;
        description "IPv6";
      }
    }
    description "Srms mi af e b";
  }
  typedef Srms-mi-src-e-b {
    type enumeration {
      enum none {
        value 0;
        description "None";
      }
      enum local {
        value 1;
        description "Local";
      }
      enum remote {
        value 2;
        description "Remote";
      }
    }
    description "Srms mi src e b";
  }

  grouping ADDR {
    description "ADDR";
    leaf af {
      type Srms-mi-af-e-b;
      description "AF";
    }
    leaf ipv4 {
      when "../af = 'ipv4'" {
        description "../AF = 'IPv4'";
      }
      type inet:ipv4-address;
      description "IPv4";
    }
    leaf ipv6 {
      when "../af = 'ipv6'" {
        description "../AF = 'IPv6'";
      }
      type In6-addr-t-b;
      description "IPv6";
    }
  }

  grouping SRMS-MI-T-B {
    description "SRMS show bag";

    container addr {
      description "addr";
      uses ADDR;
    }
    leaf src {
      type Srms-mi-src-e-b;
      description "src";
    }
    leaf router {
      type string {
        length "0..30";
      }
      description "Router ID";
    }
    leaf area {
      type string {
        length "0..30";
      }
      description "Area (OSPF) or Level (ISIS)";
    }
    leaf prefix-xr {
      type uint8;
      description "Prefix length";
    }
    leaf sid-start {
      type uint32;
      description "Starting SID";
    }
    leaf sid-count {
      type uint32;
      description "SID range";
    }
    leaf last-prefix {
      type string {
        length "0..50";
      }
      description "Last IP Prefix";
    }
    leaf last-sid-index {
      type uint32;
      description "Last SID Index";
    }
    leaf flag-attached {
      type Srms-mi-flag-e-b;
      description "Attached flag";
    }
  }
}
