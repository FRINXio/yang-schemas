module Cisco-IOS-XR-ipv4-dhcpd-subscriber-cfg {

  /*** NAMESPACE / PREFIX DEFINITION ***/

  namespace "http://cisco.com/ns/yang"+
    "/Cisco-IOS-XR-ipv4-dhcpd-subscriber-cfg";


  prefix "ipv4-dhcpd-subscriber-cfg";

  /*** LINKAGE (IMPORTS / INCLUDES) ***/

  import ietf-inet-types { prefix "inet"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-dhcpd-subscriber package configuration.

     This YANG module augments the
       Cisco-IOS-XR-subscriber-infra-tmplmgr-cfg
     module with configuration data.

     Copyright (c) 2013-2017 by Cisco Systems, Inc.
     All rights reserved.";

  revision "2015-11-09" {
    description
      "IOS XR 6.0 revision.";
  }


  augment "/a1:dynamic-template/a1:ip-subscribers/a1:ip-subscriber" {

    container dhcpd {
      description "Interface dhcpv4 configuration data";
      leaf class {
        type string;
        description "The class to be used for proxy/server profile";
      }
      leaf default-gateway {
        type inet:ipv4-address-no-zone;
        description "The Default Gateway IP address";
      }
      leaf session-limit {
        type int32;
        description "The pool to be used for Prefix Delegation";
      }
      leaf dhcpv4-option {
        type string;
        description
          "Cisco VSA to configure any dhcp4 option per
          subscriber";
      }
    }
    description
      "This augment extends the configuration data of
      'Cisco-IOS-XR-subscriber-infra-tmplmgr-cfg'";
  }
}
