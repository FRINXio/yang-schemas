module Cisco-IOS-XR-ppp-ma-lcp-cfg {

  /*** NAMESPACE / PREFIX DEFINITION ***/

  namespace "http://cisco.com/ns/yang/Cisco-IOS-XR-ppp-ma-lcp-cfg";


  prefix "ppp-ma-lcp-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ppp-ma-lcp package configuration.

     This YANG module augments the
       Cisco-IOS-XR-ifmgr-cfg
     module with configuration data.

     Copyright (c) 2013-2017 by Cisco Systems, Inc.
     All rights reserved.";

  revision "2015-11-09" {
    description
      "IOS XR 6.0 revision.";
  }

  typedef Ppp-authentication-method {
    type enumeration {
      enum pap {
        value 1;
        description "PAP";
      }
      enum chap {
        value 2;
        description "CHAP";
      }
      enum ms-chap {
        value 3;
        description "MS CHAP";
      }
    }
    description "Ppp authentication method";
  }

  augment "/a1:interface-configurations/a1:interface-configuration" {

    container ppp {
      description "Interface PPP configuration data";

      container mcmp {
        description "PPP Multiclass Multilink parameters";

        container local {
          description
            "This specifies the MCMP options for the local
            host";
          leaf initial {
            type uint32 {
              range "1..16";
            }
            default "2";
            description "Local Initial #classes";
          }
          leaf maximum {
            type uint32 {
              range "1..16";
            }
            default "4";
            description "Local Maximum #classes";
          }
        }
        leaf enable {
          type empty;
          description
            "This specifies that MCMP is enabled on this
            interface";
        }
        leaf remote {
          type uint32 {
            range "1..16";
          }
          default "2";
          description
            "This specifies the MCMP options for the peer";
        }
      }

      container lcp {
        description "PPP LCP configuration data";

        container multilink {
          description "Multilink configuration";

          container minimum-active {
            description
              "Minimum criteria for the linestate of a
              Multilink PPPinterface to be brought up";
            leaf links {
              type uint32 {
                range "1..65535";
              }
              default "1";
              description
                "Number of active links needed to bring up an
                MP interface";
            }
          }
        }

        container pap {
          description
            "Password Authentication Protocol (PAP)
            configuration data";

          container send-user-info {
            description
              "This specifies the outbound PAP username and
              password";
            leaf username {
              type string;
              description "Outbound PAP username";
            }
            leaf password {
              type xr:Proprietary-password;
              description "Outbound PAP password";
            }
          }
          leaf refuse {
            type empty;
            description
              "This specifies whether to refuse to
              authenticate using PAP";
          }
        }

        container loop-back {
          description "Loopback configuration";
          leaf ignore {
            type empty;
            description "Allow magic numbers to be equal";
          }
        }

        container ms-chap {
          description
            "Microsoft Challenge Handshake Authentication
            Protocol (MS-CHAP) configuration data";
          leaf password {
            type xr:Proprietary-password;
            description
              "This specifies the default MS-CHAP password";
          }
          leaf host-name {
            type string;
            description "This specifies the MS-CHAP hostname";
          }
          leaf refuse {
            type empty;
            description
              "This specifies whether to refuse to
              authenticate using MS-CHAP";
          }
        }

        container authentication {
          description "PPP authentication parameters";

          container method {
            description
              "This specifies the PPP link authentication
              method";
            leaf name {
              type string;
              description
                "Use an authentication list with this name";
            }
            leaf-list method {
              type Ppp-authentication-method;
              max-elements "3";
              description
                "Select between one and three authentication
                methods in order of preference";
            }
          }
          leaf max-authentication-failures {
            type uint32 {
              range "0..10";
            }
            description
              "This specifies whether to allow multiple
              authentication failures and, if so, how many";
          }
          leaf timeout {
            type uint32 {
              range "3..30";
            }
            default "10";
            description
              "Maximum time to wait for an authentication
              response";
          }
        }

        container chap {
          description
            "Challenge Handshake Authentication Protocol
            (CHAP) configuration data";
          leaf password {
            type xr:Proprietary-password;
            description "This specifies the default CHAP password";
          }
          leaf host-name {
            type string;
            description "This specifies the CHAP hostname";
          }
          leaf refuse {
            type empty;
            description
              "This specifies whether to refuse to
              authenticate using CHAP";
          }
        }
        leaf service-type {
          type int32;
          description
            "This specifies whether to allow multiple
            authentication failures and, if so, how many";
        }
      }
    }
    description
      "This augment extends the configuration data of
      'Cisco-IOS-XR-ifmgr-cfg'";
  }
}
