module Cisco-IOS-XR-ip-sbfd-oper {

  /*** NAMESPACE / PREFIX DEFINITION ***/

  namespace "http://cisco.com/ns/yang/Cisco-IOS-XR-ip-sbfd-oper";


  prefix "ip-sbfd-oper";

  /*** LINKAGE (IMPORTS / INCLUDES) ***/

  import ietf-inet-types { prefix "inet"; }

  import Cisco-IOS-XR-types { prefix "xr"; }

  include Cisco-IOS-XR-ip-sbfd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-sbfd package operational data.

     This module contains definitions
     for the following management objects:
       sbfd: Seamless BFD (S-BFD) operational data

     Copyright (c) 2013-2017 by Cisco Systems, Inc.
     All rights reserved.";

  revision "2015-11-09" {
    description
      "IOS XR 6.0 revision.";
  }


  container sbfd {
    config false;
    description "Seamless BFD (S-BFD) operational data";

    container target-identifier {
      description "Target-identifier information";

      container remote-vrfs {
        description "SBFD remote discriminator data";

        list remote-vrf {
          key "vrf-name";
          description "Table of remote discriminator data per VRF";
          leaf vrf-name {
            type xr:Cisco-ios-xr-string;
            description "VRF name";
          }

          list remote-discriminator {
            description "SBFD remote discriminator ";
            leaf vrf-name {
              type xr:Cisco-ios-xr-string;
              description "VRF Name ";
            }
            leaf remote-discriminator {
              type int32;
              description "Remote Discriminator";
            }
            leaf address {
              type inet:ip-address-no-zone;
              description "Address";
            }
            uses BFD-MGMT-TGT-IDENTIFIER-REMOTE;
          }
        }
      }

      container local-vrfs {
        description "SBFD local discriminator  data";

        list local-vrf {
          key "vrf-name";
          description "Table of local discriminator data per VRF";
          leaf vrf-name {
            type xr:Cisco-ios-xr-string;
            description "VRF name";
          }

          list local-discriminator {
            description "SBFD local discriminator ";
            leaf local-discriminator {
              type int32;
              description "Local discriminator";
            }
            leaf vrf-name {
              type xr:Cisco-ios-xr-string;
              description "VRF Name ";
            }
            uses BFD-MGMT-TGT-IDENTIFIER-LOCAL;
          }
        }
      }
    }
  }
}
