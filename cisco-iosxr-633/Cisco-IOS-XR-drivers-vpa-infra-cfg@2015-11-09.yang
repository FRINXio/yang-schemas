module Cisco-IOS-XR-drivers-vpa-infra-cfg {

  /*** NAMESPACE / PREFIX DEFINITION ***/

  namespace "http://cisco.com/ns/yang"+
    "/Cisco-IOS-XR-drivers-vpa-infra-cfg";


  prefix "drivers-vpa-infra-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR drivers-vpa-infra package configuration.

     This module contains definitions
     for the following management objects:
       hardware-module: Configure subslot h/w module

     Copyright (c) 2013-2017 by Cisco Systems, Inc.
     All rights reserved.";

  revision "2015-11-09" {
    description
      "IOS XR 6.0 revision.";
  }

  typedef Hw-module-spa-physical-mode {
    type enumeration {
      enum cem {
        value 1;
        description "CEM mode type";
      }
    }
    description "Hw module spa physical mode";
  }
  typedef Hw-module-spa-physical-interface {
    type enumeration {
      enum t3 {
        value 1;
        description "T3 interface type(default)";
      }
      enum e3 {
        value 2;
        description "E3 interface type";
      }
      enum t1 {
        value 3;
        description "T1 interface type";
      }
      enum e1 {
        value 4;
        description "E1 interface type";
      }
      enum sonet {
        value 5;
        description "Sonet interface type";
      }
      enum sdh {
        value 6;
        description "SDH interface type";
      }
    }
    description "Hw module spa physical interface";
  }
  typedef Hw-module-shutdown-power-mode {
    type enumeration {
      enum unpowered {
        value 1;
        description "Keep the showdown module unpowered";
      }
      enum powered {
        value 2;
        description "Keep the showdown module powered (default)";
      }
    }
    description "Hw module shutdown power mode";
  }

  container hardware-module {
    description "Configure subslot h/w module";

    container logging {
      description "Logging configuration";
    }

    container nodes {
      description " subslot h/w module";

      list node {
        key "node-name";
        description "The identifier for a SPA node";
        leaf card-type {
          type Hw-module-spa-physical-interface;
          description "Configure the SPA physical interface type";
        }
        leaf mode {
          type Hw-module-spa-physical-mode;
          description "Configure the SPA mode";
        }
        leaf shutdown {
          type Hw-module-shutdown-power-mode;
          description "Shutdown a subslot h/w module";
        }
        leaf node-name {
          type xr:Node-id;
          description "A SPA node";
        }
      }
    }
  }
}
