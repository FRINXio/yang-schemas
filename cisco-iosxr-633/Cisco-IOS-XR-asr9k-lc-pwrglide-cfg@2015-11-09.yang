module Cisco-IOS-XR-asr9k-lc-pwrglide-cfg {

  /*** NAMESPACE / PREFIX DEFINITION ***/

  namespace "http://cisco.com/ns/yang"+
    "/Cisco-IOS-XR-asr9k-lc-pwrglide-cfg";


  prefix "asr9k-lc-pwrglide-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-lc-pwrglide package configuration.

     This module contains definitions
     for the following management objects:
       hardware-module-port-mode: HW module port-mode config

     Copyright (c) 2013-2017 by Cisco Systems, Inc.
     All rights reserved.";

  revision "2015-11-09" {
    description
      "IOS XR 6.0 revision.";
  }


  container hardware-module-port-mode {
    description "HW module port-mode config";

    list config-mode {
      key "id1";
      description "Active or Pre configuration";
      leaf id1 {
        type xr:Cisco-ios-xr-string;
        description "act- or pre-config";
      }

      list node {
        key "id2";
        description "A node";

        container port-mode {
          description "Linecard port-mode";
          leaf if-port-mode {
            type string;
            description "Linecard interface port-mode";
          }
        }
        leaf id2 {
          type xr:Cisco-ios-xr-string;
          description "Fully qualified line card specification";
        }
      }
    }
  }
}
