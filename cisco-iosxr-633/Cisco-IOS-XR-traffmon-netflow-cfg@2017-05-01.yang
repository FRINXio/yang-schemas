module Cisco-IOS-XR-traffmon-netflow-cfg {

  /*** NAMESPACE / PREFIX DEFINITION ***/

  namespace "http://cisco.com/ns/yang"+
    "/Cisco-IOS-XR-traffmon-netflow-cfg";


  prefix "traffmon-netflow-cfg";

  /*** LINKAGE (IMPORTS / INCLUDES) ***/

  import ietf-inet-types { prefix "inet"; }

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR traffmon-netflow package configuration.

     This module contains definitions
     for the following management objects:
       net-flow: NetFlow Configuration

     This YANG module augments the
       Cisco-IOS-XR-ifmgr-cfg
     module with configuration data.

     Copyright (c) 2013-2017 by Cisco Systems, Inc.
     All rights reserved.";

  revision "2017-05-01" {
    description
      "Fixing backward compatibility error in module.";
  }

  revision "2015-11-09" {
    description
      "IOS XR 6.0 revision.";
  }

  typedef Nf-export-timeout {
    type uint32 {
      range "0..604800";
    }
    description "Nf export timeout";
  }
  typedef Nf-active-cache-aging-timeout {
    type uint32 {
      range "1..604800";
    }
    description "Nf active cache aging timeout";
  }
  typedef Nf-inactive-cache-aging-timeout {
    type uint32 {
      range "0..604800";
    }
    description "Nf inactive cache aging timeout";
  }
  typedef Nf-sample-interval {
    type uint32 {
      range "1..65535";
    }
    description "Nf sample interval";
  }
  typedef Nf-sample-number {
    type uint32;
    description "Nf sample number";
  }
  typedef Nf-template-timeout {
    type uint32 {
      range "1..604800";
    }
    description "Nf template timeout";
  }
  typedef Nf-map-name {
    type xr:Cisco-ios-xr-string {
      length "1..32";
    }
    description "Nf map name";
  }
  typedef Nf-cache-aging-mode {
    type enumeration {
      enum normal {
        value 0;
        description "Normal, caches age";
      }
      enum permanent {
        value 1;
        description "Permanent, caches never age";
      }
      enum immediate {
        value 2;
        description "Immediate, caches age immediately";
      }
    }
    description "Nf cache aging mode";
  }
  typedef Nf-cache-entry {
    type uint32 {
      range "4096..1000000";
    }
    description "Nf cache entry";
  }
  typedef Nf-update-cache-aging-timeout {
    type uint32 {
      range "1..604800";
    }
    description "Nf update cache aging timeout";
  }
  typedef Nf-sampling-mode {
    type enumeration {
      enum random {
        value 2;
        description "Random sampling";
      }
    }
    description "Nf sampling mode";
  }
  typedef Nf-export-version {
    type uint32 {
      range "9..10";
    }
    description "Nf export version";
  }
  typedef Nf-cache-timeout-rate-limit {
    type uint32 {
      range "1..1000000";
    }
    description "Nf cache timeout rate limit";
  }

  grouping FLOW-MONITOR-NAME {
    description "Common node of ingress, egress";

    list flow-monitor-name {
      key "monitor-map-name";
      description "Specify a sampler for a flow monitor";
      leaf monitor-map-name {
        type xr:Cisco-ios-xr-string;
        description "Flow monitor map name";
      }
      leaf sampler-map-name {
        type string;
        mandatory true;
        description "Sampler map name";
      }
    }
  }

  grouping FLOW-MONITOR-MAP {
    description
      "Common node of mpls, ipv4, ipv6,
      data-link-frame-section";

    container flow-monitor-map {
      description "Configure a flow monitor map";

      container ingress {
        description "Configure ingress monitoring direction";
        uses FLOW-MONITOR-NAME;
      }

      container egress {
        description "Configure egress monitoring direction";
        uses FLOW-MONITOR-NAME;
      }
    }
  }

  grouping NETFLOW-CFG-FLOW-MONITOR-MAP {
    description
      "Common node of mpls, ipv4, ipv6,
      data-link-frame-sectionCommon node of
      flow-monitor-map-table,
      flow-monitor-map-performance-table";

    list flow-monitor-map {
      key "monitor-map-name";
      description "Monitor map name";

      container option {
        description "Specify an option for the flow cache";
        leaf filtered {
          type empty;
          description "Specify whether data should be filtered";
        }
        leaf out-bundle-member {
          type empty;
          description
            "Specify whether to export physical ifh for
            bundle interface";
        }
        leaf out-phys-int {
          type empty;
          description
            "Specify whether it exports the physical output
            interface";
        }
        leaf bgp-attr {
          type empty;
          description
            "Specify if BGP Attributes AS_PATH STD_COMM
            should be exported";
        }
      }

      container exporters {
        description
          "Configure exporters to be used by the
          monitor-map";

        list exporter {
          key "exporter-name";
          description
            "Configure exporter to be used by the
            monitor-map";
          leaf exporter-name {
            type Nf-map-name;
            description "Exporter name";
          }
        }
      }

      container record {
        presence "Indicates a record node is configured.";
        description "Specify a flow record format";
        leaf record-name {
          type Nf-map-name;
          mandatory true;
          description
            "Flow record format (Either 'ipv4-raw'
            ,'ipv4-peer-as', 'ipv6', 'mpls', 'mpls-ipv4',
            'mpls-ipv6', 'mpls-ipv4-ipv6', 'ipv6-peer-as')";
        }
        leaf label {
          type uint32 {
            range "1..6";
          }
          description "Enter label value for MPLS record type";
        }
      }
      leaf cache-update-aging-timeout {
        type Nf-update-cache-aging-timeout;
        units "second";
        default "1800";
        description "Specify the update flow cache aging timeout";
      }
      leaf cache-entries {
        type Nf-cache-entry;
        default "65535";
        description
          "Specify the number of entries in the flow cache";
      }
      leaf cache-inactive-aging-timeout {
        type Nf-inactive-cache-aging-timeout;
        units "second";
        default "15";
        description "Specify the inactive flow cache aging timeout";
      }
      leaf cache-active-aging-timeout {
        type Nf-active-cache-aging-timeout;
        units "second";
        default "1800";
        description "Specify the active flow cache aging timeout";
      }
      leaf cache-timeout-rate-limit {
        type Nf-cache-timeout-rate-limit;
        default "2000";
        description
          "Specify the maximum number of entries to age
          each second";
      }
      leaf cache-aging-mode {
        type Nf-cache-aging-mode;
        default "normal";
        description "Specify the flow cache aging mode";
      }
      leaf monitor-map-name {
        type Nf-map-name;
        description "Monitor map name";
      }
    }
  }

  container net-flow {
    description "NetFlow Configuration";

    container flow-exporter-maps {
      description "Configure a flow exporter map";

      list flow-exporter-map {
        key "exporter-map-name";
        description "Exporter map name";

        container udp {
          description "Use UDP as transport protocol";
          leaf destination-port {
            type uint32 {
              range "1024..65535";
            }
            description "Configure Destination UDP port";
          }
        }

        container destination {
          description "Configure export destination (collector)";
          leaf ip-address {
            type inet:ipv4-address-no-zone;
            description "Destination IPv4 address";
          }
          leaf ipv6-address {
            type string;
            description "IPV6 address of the tunnel destination";
          }
          leaf vrf-name {
            type string;
            description "VRF name";
          }
        }

        container version {
          description "Specify export version parameters";

          container options {
            description "Specify options for exporting templates";
            leaf interface-table-export-timeout {
              type Nf-export-timeout;
              units "second";
              description
                "Specify timeout for exporting interface
                table";
            }
            leaf sampler-table-export-timeout {
              type Nf-export-timeout;
              units "second";
              description
                "Specify timeout for exporting sampler table";
            }
            leaf vrf-table-export-timeout {
              type Nf-export-timeout;
              units "second";
              description "Specify timeout for exporting vrf table";
            }
          }
          leaf version-type {
            type Nf-export-version;
            description "Export version number";
          }
          leaf options-template-timeout {
            type Nf-template-timeout;
            units "second";
            default "1800";
            description "Option template configuration options";
          }
          leaf common-template-timeout {
            type Nf-template-timeout;
            units "second";
            default "1800";
            description "Specify custom timeout for the template";
          }
          leaf data-template-timeout {
            type Nf-template-timeout;
            units "second";
            default "1800";
            description "Data template configuration options";
          }
        }
        leaf source-interface {
          type xr:Interface-name;
          description "Configure source interface for collector";
        }
        leaf dscp {
          type uint32 {
            range "0..63";
          }
          description "Specify DSCP value for export packets";
        }
        leaf packet-length {
          type uint32 {
            range "512..1468";
          }
          description
            "Configure Maximum Value for Export Packet size";
        }
        leaf exporter-map-name {
          type Nf-map-name;
          description "Exporter map name";
        }
      }
    }

    container flow-sampler-maps {
      description "Flow sampler map configuration";

      list flow-sampler-map {
        key "sampler-map-name";
        description "Sampler map name";

        container sampling-modes {
          description "Configure packet sampling mode";

          list sampling-mode {
            key "mode";
            description "Configure sampling mode";
            leaf mode {
              type Nf-sampling-mode;
              description "Sampling mode";
            }
            leaf sample-number {
              type Nf-sample-number;
              mandatory true;
              description
                "Number of packets to be sampled in the
                sampling interval";
            }
            leaf interval {
              type Nf-sample-interval;
              mandatory true;
              description "Sampling interval in units of packets";
            }
          }
        }
        leaf sampler-map-name {
          type Nf-map-name;
          description "Sampler map name";
        }
      }
    }

    container flow-monitor-map-table {
      description "Flow monitor map configuration";
      uses NETFLOW-CFG-FLOW-MONITOR-MAP;
    }

    container flow-monitor-map-performance-table {
      description
        "Configure a performance traffic flow monitor map";
      uses NETFLOW-CFG-FLOW-MONITOR-MAP;
    }
  }

  augment "/a1:interface-configurations/a1:interface-configuration" {

    container net-flow {
      description "Interface netflow configuration";

      container data-link-frame-section {
        description "Configure datalinkframesection netflow";
        uses FLOW-MONITOR-MAP;
      }

      container mpls {
        description "Configure MPLS netflow";
        uses FLOW-MONITOR-MAP;
      }

      container ipv6 {
        description "Configure IPv6 netflow";
        uses FLOW-MONITOR-MAP;
      }

      container ipv4 {
        description "Configure IPv4 netflow";
        uses FLOW-MONITOR-MAP;
      }
    }
    description
      "This augment extends the configuration data of
      'Cisco-IOS-XR-ifmgr-cfg'";
  }
}
