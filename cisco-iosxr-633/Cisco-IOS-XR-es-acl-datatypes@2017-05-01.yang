module Cisco-IOS-XR-es-acl-datatypes {

  /*** NAMESPACE / PREFIX DEFINITION ***/

  namespace "http://cisco.com/ns/yang/Cisco-IOS-XR-es-acl-datatypes";


  prefix "es-acl-datatypes";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2017 by Cisco Systems, Inc.
     All rights reserved.";

  revision "2017-05-01" {
    description
      "Fixing backward compatibility error in module.";
  }

  revision "2015-11-09" {
    description
      "IOS XR 6.0 revision.";
  }

  typedef Es-acl-name {
    type xr:Cisco-ios-xr-string {
      length "1..65";
    }
    description "Es acl name";
  }
  typedef Acl-usage-app-id-enum {
    type enumeration {
      enum pfilter {
        value 1;
        description "General Usage Statistics";
      }
      enum bgp {
        value 2;
        description "Usage staistics related to BGP Traffic";
      }
      enum ospf {
        value 3;
        description "Usage staistics related to OSPF Traffic";
      }
    }
    description "Acl usage app id enum";
  }
  typedef Acl-sequence-number-range {
    type uint32 {
      range "1..2147483646";
    }
    description "Acl sequence number range";
  }
}
