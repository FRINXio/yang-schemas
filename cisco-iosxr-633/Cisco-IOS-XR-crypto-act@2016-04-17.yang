module Cisco-IOS-XR-crypto-act {

    namespace "http://cisco.com/ns/yang/Cisco-IOS-XR-crypto-act";
    
    prefix "crypto-act";
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR action package configuration.

     Copyright (c) 2016-2018 by Cisco Systems, Inc.
     All rights reserved.";
    
    revision "2016-04-17" {
        description
            "IOS XR 6.1.1 revision.";
    }

    grouping KEY-MODULUS {
        leaf key-label {
            description "RSA keypair label";
            type string;
        }
        leaf key-modulus {
            description "Key modulus in the range of 512 to 4096 for your "
                + "General Purpose Keypair. Choosing a key modulus greater "
                + "than 512 may take a few minutes";
            type int32 {
                range "512..4096";
            }
            mandatory true;
        }
    }

    rpc key-generate-rsa-general-keys {
        description "Generate a general purpose RSA key pair for signing and encryption";
        input {
            uses KEY-MODULUS;
        }
    }

    rpc key-generate-rsa-usage-keys {
        description "Generate seperate RSA key pairs for signing and encryption";
        input {
            uses KEY-MODULUS;
        }
    }

    rpc key-generate-rsa {
        description "Generate seperate RSA key pairs for signing and encryption";
        input {
            uses KEY-MODULUS;
        }
    }

    rpc key-generate-dsa {
        description "Generate DSA keys";
        input {
            leaf key-modulus {
                description "Key modulus size can be 512, 768 or 1024 bits.";
                type int32 {
                    range "512|768|1024";
                }
                mandatory true;
            }
        }
    }

    rpc key-zeroize-rsa {
        description "Remove RSA keys";
        input {
            leaf key-label {
                description "RSA key label";
                type string;
            }
        }
    }

    rpc key-zeroize-dsa {
        description "Remove DSA keys";
    }

    rpc key-zeroize-authentication-rsa {
        description "Remove RSA authentication key";
    }

    rpc key-import-authentication-rsa {
        description "Remove RSA authentication key";
        input {
            leaf path {
                description "Path to RSA pubkey file";
                type string;
                mandatory true;
            }
        }
    }

    rpc ca-authenticate {
        description "Get the certification authority certificate";
        input {
            leaf server-name {
                description "CA Server Name";
                type string;
                mandatory true;
            }
        }
    }

    rpc ca-enroll {
        description "Request a certificate from a CA";
        input {
            leaf server-name {
                description "CA Server Name";
                type string;
                mandatory true;
            }
        }
    }

    rpc ca-import-certificate {
        description "Import a certificate from a s/tftp server or the terminal";
        input {
            leaf server-name {
                description "CA Server Name";
                type string;
                mandatory true;
            }
        }
    }

    rpc ca-cancel-enroll {
        description "Cancel enrollment from a CA";
        input {
            leaf server-name {
                description "CA Server Name";
                type string;
                mandatory true;
            }
        }
    }

    rpc ca-crl-request {
        description "Actions on certificate revocation lists";
        input {
            leaf uri {
                description "CRL Distribution Point in URI format";
                type string;
                mandatory true;
            }
        }
        output {
            leaf certificate {
                type string;
                description "Certificate returned";
                mandatory true;
            }
        }
    }

    rpc ca-trustpool-import-url {
        description "Manual import trustpool certificates from URL";
        input {
            leaf url {
                description "in URL format";
                type string;
            }
        }
    }

    rpc ca-trustpool-import-url-clean {
        description "Remove downloaded certificates in trustpool";
        input {
            leaf url {
                description "in URL format";
                type string;
            }
        }
    }
}
