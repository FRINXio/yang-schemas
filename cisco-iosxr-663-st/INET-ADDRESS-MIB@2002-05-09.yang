module INET-ADDRESS-MIB {
  namespace "http://tail-f.com/ns/mibs/INET-ADDRESS-MIB/200205090000Z";
  prefix INET_ADDRESS_MIB;
  import tailf-common {
    prefix tailf;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2002-05-09 {
    description
      "";
  }


  typedef InetAddressType {
    type enumeration {
      enum "unknown" {
        value 0;
      }
      enum "ipv4" {
        value 1;
      }
      enum "ipv6" {
        value 2;
      }
      enum "ipv4z" {
        value 3;
      }
      enum "ipv6z" {
        value 4;
      }
      enum "dns" {
        value 16;
      }
    }
  }

  typedef InetAddress {
    type tailf:hex-list {
    }
  }

  typedef InetAddressIPv4 {
    type tailf:hex-list {
    }
  }

  typedef InetAddressIPv6 {
    type tailf:hex-list {
    }
  }

  typedef InetAddressIPv4z {
    type tailf:hex-list {
    }
  }

  typedef InetAddressIPv6z {
    type tailf:hex-list {
    }
  }

  typedef InetAddressDNS {
    type string {
      length "1 .. 255";
    }
  }

  typedef InetAddressPrefixLength {
    type uint32 {
      range "0 .. 4294967295";
    }
  }

  typedef InetPortNumber {
    type uint32 {
      range "0 .. 65535";
    }
  }

  typedef InetAutonomousSystemNumber {
    type uint32 {
      range "0 .. 4294967295";
    }
  }

  typedef InetScopeType {
    type enumeration {
      enum "interfaceLocal" {
        value 1;
      }
      enum "linkLocal" {
        value 2;
      }
      enum "subnetLocal" {
        value 3;
      }
      enum "adminLocal" {
        value 4;
      }
      enum "siteLocal" {
        value 5;
      }
      enum "organizationLocal" {
        value 8;
      }
      enum "global" {
        value 14;
      }
    }
  }

  typedef InetZoneIndex {
    type uint32 {
      range "0 .. 4294967295";
    }
  }

  typedef InetVersion {
    type enumeration {
      enum "unknown" {
        value 0;
      }
      enum "ipv4" {
        value 1;
      }
      enum "ipv6" {
        value 2;
      }
    }
  }
}
