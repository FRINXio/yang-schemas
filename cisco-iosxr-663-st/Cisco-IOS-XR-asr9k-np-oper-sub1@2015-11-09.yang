submodule Cisco-IOS-XR-asr9k-np-oper-sub1 {

  belongs-to Cisco-IOS-XR-asr9k-np-oper {
    prefix Cisco-IOS-XR-asr9k-np-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-np package operational data.

     Copyright (c) 2013-2018 by Cisco Systems, Inc.
     All rights reserved.";

  revision "2015-11-09" {
    description
      "IOS XR 6.0 revision.";
  }


  grouping PRM-EFD {
    description "EFD cos to priority mapping";
    leaf hp-list-is-supported {
      type uint32;
      description "high-priority-list CLI is supported";
    }
    leaf-list vlan-cos-mapping {
      type uint32;
      max-elements "8";
      description "Array of VLAN COS Mapping";
    }
    leaf-list mplscos-mapping {
      type uint32;
      max-elements "8";
      description "Array of MPLS COS Mapping";
    }
    leaf-list ipcos-mapping {
      type uint32;
      max-elements "8";
      description "Array of IP COS Mapping";
    }
  }

  grouping PRM-NP-FAST-DROP-A {
    description "NP fast drop";
    leaf interface-name {
      type string;
      description "Interface name";
    }
    leaf counter-value {
      type uint64;
      description "The Value of the counter";
    }
  }

  grouping PRM-NP-FAST-DROP {
    description "Array of NP Fast Drop Counters";

    list np-fast-drop {
      description "Array of NP Fast Drop Counters";
      uses PRM-NP-FAST-DROP-A;
    }
  }

  grouping PRM-NP-COUNTERS-A {
    description "NP Counters";
    leaf counter-index {
      type uint32;
      description "Counter Index";
    }
    leaf counter-value {
      type uint64;
      description "The accurate value of the counter";
    }
    leaf rate {
      type uint32;
      units "packet/s";
      description "Rate in Packets Per Second";
    }
    leaf counter-type {
      type string;
      description
        "Counter TypeDROP: Drop counterPUNT: Punt
        counterFWD:  Forward or generic counterUNKNOWN:
        Counter type unknown";
    }
    leaf counter-name {
      type string;
      description "Counter name";
    }
  }

  grouping PRM-NP-COUNTERS {
    description "Array of NP Counters";

    list np-counter {
      description "Array of NP Counters";
      uses PRM-NP-COUNTERS-A;
    }
  }

  grouping PRM-NP-PROFILE {
    description "np profile info";
    leaf scale {
      type string;
      description "Scale";
    }
  }

  grouping PRM-NP-L2RM-HW-RSC-TCAM-PAR {
    description "NP L2RM TCAM Par info";
    leaf tcam-par {
      type uint32;
      description "tcam par";
    }
    leaf total {
      type uint32;
      description "total";
    }
    leaf free {
      type uint32;
      description "free";
    }
  }

  grouping PRM-NP-L2RM-HW-RSC-HASH-BLK {
    description "NP L2RM Hash Block info";
    leaf hash-blk {
      type uint32;
      description "hash block";
    }
    leaf total {
      type uint32;
      description "total";
    }
    leaf free {
      type uint32;
      description "free";
    }
  }

  grouping PRM-NP-L2RM-HW-RSC-A {
    description "NP L2RM hw_rsc detail";

    list hash-block {
      description "Hash Block hw blk";
      uses PRM-NP-L2RM-HW-RSC-HASH-BLK;
    }

    list tcam-partition {
      description "TCAM partition per hw blk";
      uses PRM-NP-L2RM-HW-RSC-TCAM-PAR;
    }
  }

  grouping PRM-NP-L2RM-HW-RSC {
    description "NP L2RM  hw_rsc";

    container hw-resource {
      description "resources per hw blk";
      uses PRM-NP-L2RM-HW-RSC-A;
    }
    leaf ppt-alloc {
      type uint64;
      description "ppt allocated";
    }
    leaf ppt-write {
      type uint64;
      description "ppt write";
    }
    leaf ppt-free {
      type uint64;
      description "ppt free";
    }
  }

  grouping TCAM-VMR-ENTRY {
    description "Application VMR entry";
    leaf num-vmr-ids {
      type uint32;
      description "Vmr IDs";
    }
    leaf num-active-entries {
      type uint32;
      description "The number of active vmr entries";
    }
    leaf num-allocated-entries {
      type uint32;
      description "The number of active vmr entries";
    }
  }

  grouping ACL-COMM-REGION {
    description "acl common region";
    leaf free-entries {
      type uint32;
      description "Free entries in the table";
    }
    leaf allocated-entries {
      type uint32;
      description "The number of active vmr entries";
    }
  }

  grouping TCAM-ODS-TABLE {
    description "tcam ods table";

    container acl-common {
      description "ACL common region";
      uses ACL-COMM-REGION;
    }

    container app-id-ifib {
      description "App IFIB entry";
      uses TCAM-VMR-ENTRY;
    }

    container app-id-qos {
      description "App qos entry";
      uses TCAM-VMR-ENTRY;
    }

    container app-id-acl {
      description "App acl entry";
      uses TCAM-VMR-ENTRY;
    }

    container app-id-afmon {
      description "App afmon entry";
      uses TCAM-VMR-ENTRY;
    }

    container app-id-li {
      description "App LI entry";
      uses TCAM-VMR-ENTRY;
    }

    container app-id-pbr {
      description "App PBR entry";
      uses TCAM-VMR-ENTRY;
    }

    container app-id-edpl {
      description "App EDPL entry";
      uses TCAM-VMR-ENTRY;
    }
    leaf free-entries {
      type uint32;
      description "Free entries in the table";
    }
    leaf reserved-entries {
      type uint32;
      description "The number of active vmr entries";
    }
  }

  grouping TCAM-L2-TABLE-A {
    description "tcam l2 table";
    leaf partition-id {
      type uint32;
      description "PartitionID";
    }
    leaf priority {
      type uint32;
      description "Priority";
    }
    leaf valid-entries {
      type uint32;
      description "Valid entries";
    }
    leaf free-entries {
      type uint32;
      description "Free entries";
    }
  }

  grouping TCAM-SHOW-SUM {
    description "tcam summary";

    container tcam-lt-ods2 {
      description "TCAM ODS2 partition summary";
      uses TCAM-ODS-TABLE;
    }

    container tcam-lt-ods8 {
      description "TCAM ODS8 partition summary";
      uses TCAM-ODS-TABLE;
    }

    list tcam-lt-l2 {
      description "Array of TCAM L2 partition summaries";
      uses TCAM-L2-TABLE-A;
    }
  }

  grouping TCAM-VMR-ENTRY-INT {
    description "Application VMR entry internal";
    leaf num-vmr-ids {
      type uint32;
      description "Vmr IDs";
    }
    leaf total-used-entries {
      type uint32;
      description "number of used vmr entries";
    }
    leaf total-allocated-entries {
      type uint32;
      description "The number of active vmr entries";
    }
  }

  grouping TCAM-ODS-TABLE-INT {
    description "tcam ods table internal";

    container app-id-ifib {
      description "App IFIB entry";
      uses TCAM-VMR-ENTRY-INT;
    }

    container app-id-qos {
      description "App qos entry";
      uses TCAM-VMR-ENTRY-INT;
    }

    container app-id-acl {
      description "App acl entry";
      uses TCAM-VMR-ENTRY-INT;
    }

    container app-id-afmon {
      description "App afmon entry";
      uses TCAM-VMR-ENTRY-INT;
    }

    container app-id-li {
      description "App LI entry";
      uses TCAM-VMR-ENTRY-INT;
    }

    container app-id-pbr {
      description "App PBR entry";
      uses TCAM-VMR-ENTRY-INT;
    }

    container application-edpl-entry {
      description "App EDPL entry";
      uses TCAM-VMR-ENTRY-INT;
    }
    leaf max-entries {
      type uint32;
      description "Max entries";
    }
    leaf free-entries {
      type uint32;
      description "Free entries";
    }
  }

  grouping TCAM-L2-TABLE-INT-A {
    description "tcam l2 table internal";
    leaf partition-id {
      type uint32;
      description "PartitionID";
    }
    leaf valid-entries {
      type uint32;
      description "Valid entries";
    }
    leaf free-entries {
      type uint32;
      description "Free entries";
    }
  }

  grouping TCAM-SHOW-SUM-INT {
    description "tcam summary internal";

    container tcam-lt-ods2 {
      description "TCAM LT ODS 2 summary";
      uses TCAM-ODS-TABLE-INT;
    }

    container tcam-lt-ods8 {
      description "TCAM LT_ODS 8 summary";
      uses TCAM-ODS-TABLE-INT;
    }

    list tcam-lt-l2 {
      description "Array of TCAM LT L2 partition summaries";
      uses TCAM-L2-TABLE-INT-A;
    }
  }

  grouping TCAM-INFO-SHOW-SUM {
    description "tcam summary info";

    container internal-tcam-info {
      description "Internal tcam summary info";
      uses TCAM-SHOW-SUM-INT;
    }

    container tcam-info {
      description "External tcam summary info";
      uses TCAM-SHOW-SUM;
    }
  }

  grouping PRM-NP-LOAD {
    description "np load info";
    leaf utilization {
      type uint32;
      units "percentage";
      description "Percent load on the NP engines";
    }
    leaf packet-per-second-rate {
      type uint32;
      description "Packet rate load on NP engines";
    }
  }

  grouping PRM-NP-CHN-LOAD-A {
    description "NP Channel load counters";
    leaf flow-ctr-counter {
      type uint32;
      description "Flow control counters";
    }
    leaf avg-rfd-usage {
      type uint32;
      description "Average RFD Usage";
    }
    leaf peak-rfd-usage {
      type uint32;
      description "Peak RFD Usage";
    }
    leaf avg-guar-rfd-usage {
      type uint32;
      description "Average of guaranteed RFD usage";
    }
    leaf peak-guar-rfd-usage {
      type uint32;
      description "Peak of guaranteed RFD usage";
    }
    leaf interface-name {
      type string;
      description "Inerface Name";
    }
  }

  grouping PRM-NP-CHN-LOAD {
    description "Array of NP Channel load counters";

    list np-chn-load {
      description "Array of NP Channel load counters";
      uses PRM-NP-CHN-LOAD-A;
    }
  }

  grouping TCAM-VMR-ENTRY-ID {
    description "Feature VMR entry";
    leaf vmr-id {
      type uint32;
      description "Vmr ID";
    }
    leaf used-entries {
      type uint32;
      description "The number of used vmr entries";
    }
    leaf allocated-entries {
      type uint32;
      description "The number of active vmr entries";
    }
  }

  grouping TCAM-FEATURE-ENTRY {
    description "tcam feature info";
    leaf feature-id {
      type string;
      description "Feature ID";
    }
    leaf num-vmr-ids {
      type uint32;
      description "Number of VRM IDs";
    }
    leaf total-used-entries {
      type uint32;
      description "Number of used VMR entries";
    }
    leaf total-allocated-entries {
      type uint32;
      description "Total Allocated entries";
    }

    list vmr-entry {
      description "VMR entries";
      uses TCAM-VMR-ENTRY-ID;
    }
  }

  grouping TCAM-REGION-TABLE-INT {
    description "tcam table internal region";
    leaf region-name {
      type string;
      description "Region Name";
    }
    leaf max-entries {
      type uint32;
      description "Max entries";
    }
    leaf free-entries {
      type uint32;
      description "Free entries";
    }

    list feature {
      description "Feature";
      uses TCAM-FEATURE-ENTRY;
    }
  }

  grouping TCAM-SHOW-SUM-INT-REGION {
    description "tcam summary internal region";

    list tcam-region {
      description "TCAM Regions";
      uses TCAM-REGION-TABLE-INT;
    }
  }

  grouping TCAM-INFO-SHOW-SUM-REGION {
    description "tcam info summary region";

    container internal-tcam-info {
      description "Internal tcam summary info";
      uses TCAM-SHOW-SUM-INT-REGION;
    }
  }

  grouping PRM-NP-UIDB-A {
    description "NP uidb";
    leaf interface-name {
      type string;
      description "Interface name";
    }
    leaf interface-handle {
      type uint32;
      description "Interface handle";
    }
    leaf index {
      type uint16;
      description "UIDB Index";
    }
    leaf interface-type {
      type string;
      description "Interface type";
    }
  }

  grouping PRM-NP-UIDB {
    description "Array of NP UIDB Index";

    list uidb-index {
      description "Array of NP UIDB Index";
      uses PRM-NP-UIDB-A;
    }
  }
}
