/*
 * Generated by confdc --mib2yang
 * Source: ENTITY-STATE-MIB.mib
 * 
 * Copyright (c) 2015-2017 by Cisco Systems, Inc.
 * All rights reserved.
 */
module Cisco-IOS-XR-sysadmin-entity-state-mib {
  namespace "http://www.cisco.com/ns/yang/Cisco-IOS-XR-sysadmin-entity-state-mib";
  tailf:id  "http://tail-f.com/ns/mibs/ENTITY-STATE-MIB/200511220000Z";
  prefix ENTITY_STATE_MIB;
  tailf:snmp-mib-module-name "ENTITY-STATE-MIB";

  import ietf-yang-types {
    prefix yang;
  }
  import tailf-common {
    prefix tailf;
  }
  import Cisco-IOS-XR-sysadmin-entity-state-tc-mib {
    prefix ENTITY-STATE-TC-MIB;
  }
  import Cisco-IOS-XR-sysadmin-entity-mib {
    prefix ENTITY-MIB;
  }

  organization    "Cisco Systems Inc.";

  contact         "Cisco Systems, Inc.
                   Customer Service

                   Postal: 170 West Tasman Drive
                   San Jose, CA 95134

                   Tel: +1 800 553-NETS

                   E-mail: cs-yang@cisco.com";

  description     "This module contains a collection of YANG
                   definitions for Cisco IOS-XR SysAdmin configuration.

                   Copyright(c) 2015-2017 by Cisco Systems, Inc.
                   All rights reserved.";

  revision 2017-04-12 {
    description
      "Changed namespace and module name";
  }

  revision 2005-11-22 {
    description
      "";
  }

  container ENTITY-STATE-MIB {
    container entStateTable {
      config false;
      tailf:callpoint cp_snmp_entStateTable;
      list entStateEntry {
        key "entPhysicalIndex";
        tailf:sort-order "snmp";
        config false;
        tailf:snmp-oid "1.3.6.1.2.1.131.1.1";
        leaf entPhysicalIndex {
          type ENTITY-MIB:PhysicalIndex;
          tailf:snmp-oid "1.3.6.1.2.1.47.1.1.1.1.1";
        }
        leaf entStateLastChanged {
          type yang:date-and-time;
          tailf:snmp-oid "1.3.6.1.2.1.131.1.1.1.1";
          config false;
        }
        leaf entStateAdmin {
          type ENTITY-STATE-TC-MIB:EntityAdminState;
          tailf:snmp-oid "1.3.6.1.2.1.131.1.1.1.2";
          config false;
        }
        leaf entStateOper {
          type ENTITY-STATE-TC-MIB:EntityOperState;
          tailf:snmp-oid "1.3.6.1.2.1.131.1.1.1.3";
          config false;
        }
        leaf entStateUsage {
          type ENTITY-STATE-TC-MIB:EntityUsageState;
          tailf:snmp-oid "1.3.6.1.2.1.131.1.1.1.4";
          config false;
        }
        leaf entStateAlarm {
          type ENTITY-STATE-TC-MIB:EntityAlarmStatus;
          tailf:snmp-oid "1.3.6.1.2.1.131.1.1.1.5";
          config false;
        }
        leaf entStateStandby {
          type ENTITY-STATE-TC-MIB:EntityStandbyStatus;
          tailf:snmp-oid "1.3.6.1.2.1.131.1.1.1.6";
          config false;
        }
      }
    }
  }
}
