submodule Cisco-IOS-XR-ipv6-traceroute-act {

    belongs-to Cisco-IOS-XR-traceroute-act {
        prefix "traceroute-act";
    }

    include "Cisco-IOS-XR-ipv4-traceroute-act";

    organization "Cisco Systems, Inc.";
    
    contact
    "Cisco Systems, Inc.
     Customer Service

     Postal: 170 West Tasman Drive
     San Jose, CA 95134

     Tel: +1 800 553-NETS

     E-mail: cs-yang@cisco.com";

    description 
    "This module contains a collection of YANG definitions
     for Cisco IOS-XR IPv6 traceroute action package configuration.

     Copyright (c) 2016 by Cisco Systems, Inc.
     All rights reserved.";
    
    revision "2016-09-17" {
        description
            "IOS XR 6.2.1 revision.";
    }

   grouping IPV6-SPECIFIC-OPTIONS {

       leaf priority {
           description "Priority of hte packet";
           type uint16 {
                   range "0..15";
           }
       }

       leaf outgoing-interface {
           description "Outgoing interface, needed in case of traceroute to link local address";
           type string;
       }
 
   }

   grouping IPV6-TRACEROUTE-INPUT {

       uses TRACEROUTE-OPTIONS;

       uses IPV6-SPECIFIC-OPTIONS;
   }
}
