module Cisco-IOS-XR-fib-common-oper {

  /*** NAMESPACE / PREFIX DEFINITION ***/

  namespace "http://cisco.com/ns/yang/Cisco-IOS-XR-fib-common-oper";


  prefix "fib-common-oper";

  /*** LINKAGE (IMPORTS / INCLUDES) ***/

  import ietf-inet-types { prefix "inet"; }

  import Cisco-IOS-XR-types { prefix "xr"; }

  include Cisco-IOS-XR-fib-common-oper-sub7 {
    revision-date 2017-09-07;
  }

  include Cisco-IOS-XR-fib-common-oper-sub6 {
    revision-date 2017-09-07;
  }

  include Cisco-IOS-XR-fib-common-oper-sub5 {
    revision-date 2017-09-07;
  }

  include Cisco-IOS-XR-fib-common-oper-sub4 {
    revision-date 2017-09-07;
  }

  include Cisco-IOS-XR-fib-common-oper-sub3 {
    revision-date 2017-09-07;
  }

  include Cisco-IOS-XR-fib-common-oper-sub2 {
    revision-date 2017-09-07;
  }

  include Cisco-IOS-XR-fib-common-oper-sub1 {
    revision-date 2017-09-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fib-common package operational data.

     This module contains definitions
     for the following management objects:
       fib-statistics: cef interface drops operational data
       fib: fib
       oc-aft-l3: oc aft l3
       mpls-forwarding: mpls forwarding

     Copyright (c) 2013-2018 by Cisco Systems, Inc.
     All rights reserved.";

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }

  typedef Fib-route-source {
    type enumeration {
      enum lsd {
        value 5;
        description "LSD";
      }
      enum rib {
        value 7;
        description "RIB";
      }
      enum mrib {
        value 13;
        description "MRIB";
      }
    }
    description "Fib route source";
  }
  typedef Fib-protocol {
    type enumeration {
      enum ipv4 {
        value 0;
        description "ipv4 protocol";
      }
      enum ipv6 {
        value 1;
        description "ipv6 protocol";
      }
      enum mpls {
        value 2;
        description "MPLS protocol";
      }
    }
    description "Fib protocol";
  }
  typedef Fibipv6-flow-label {
    type uint32 {
      range "0..1048575";
    }
    description "Fibipv6 flow label";
  }
  typedef Fibafi-proto {
    type enumeration {
      enum ipv4 {
        value 0;
        description "ipv4 protocol";
      }
      enum ipv4-mpls {
        value 1;
        description "ipv4 mpls protocol";
      }
      enum ipv6 {
        value 2;
        description "ipv6 protocol";
      }
      enum ipv6-mpls {
        value 3;
        description "ipv6 mpls protocol";
      }
    }
    description "Fibafi proto";
  }
  typedef Fib-label {
    type uint32 {
      range "16..1048575";
    }
    description "Fib label";
  }
  typedef Fibllc-entry {
    type enumeration {
      enum xc {
        value 1;
        description "LabelXconnect";
      }
      enum pfx {
        value 2;
        description "IPPrefix";
      }
    }
    description "Fibllc entry";
  }
  typedef Fibnh-info-repl {
    type enumeration {
      enum fib-nh-repl-none {
        value 0;
        description "None Replicated NHINFO";
      }
      enum fib-nh-repl-rsvpte {
        value 1;
        description "Replicated NHINFO for TE Accounting";
      }
      enum fib-nh-repl-sr-mpls {
        value 2;
        description "Replicated NHINFO for SR MPLS Accounting";
      }
      enum fib-nh-repl-bm {
        value 3;
        description "Replicated NHINFO for Bundle member";
      }
    }
    description "Fibnh info repl";
  }
  typedef Fibfrr {
    type enumeration {
      enum fib-te-frr-node {
        value 0;
        description "TE FRR";
      }
      enum fib-te-frr-intf {
        value 1;
        description "TE Interface FRR";
      }
      enum fib-te-frr-protected-nh {
        value 2;
        description "TE Protected FRR";
      }
      enum fib-te-frr-backup-nh {
        value 3;
        description "TE Backup FRR";
      }
      enum fib-per-link-frr-protected-nh {
        value 4;
        description "Per Link Protected FRR";
      }
      enum fib-per-link-frr-backup-nh {
        value 5;
        description "Per Link Backup FRR";
      }
      enum fib-prefix-frr-protected-nh {
        value 6;
        description "Per Prefix Protected FRR";
      }
      enum fib-prefix-frr-backup-nh {
        value 7;
        description "Per Prefix Backup FRR";
      }
      enum fib-pic-frr-protected-nh {
        value 8;
        description "BGP PIC Protected FRR";
      }
      enum fib-pic-frr-backup-nh {
        value 9;
        description "BGP PIC Backup FRR";
      }
    }
    description "Fibfrr";
  }
  typedef Fib-link {
    type enumeration {
      enum link-ipv4 {
        value 0;
        description "IPv4 link protocol";
      }
      enum link-ipv6 {
        value 1;
        description "IPv6 link protocol";
      }
      enum link-mpls {
        value 2;
        description "MPLS link protocol";
      }
    }
    description "Fib link";
  }
  typedef Mpls-label {
    type uint32 {
      range "16..1048575";
    }
    description "Mpls label";
  }
  typedef Mplseos {
    type enumeration {
      enum eos0 {
        value 0;
        description "EOS Disable";
      }
      enum eos1 {
        value 1;
        description "EOS Enable";
      }
    }
    description "Mplseos";
  }

  grouping STATE {
    description "Common node of prefix, label";

    container state {
      description "Operational data";
      uses FIB-OC-AFT-PREFIX-STATE;
    }
  }

  grouping INFORMATION {
    description "Common node of vrf, forwarding";

    list information {
      description "MPLS forwarding information";
      leaf label-value {
        type Mpls-label;
        description "Local label value";
      }
      leaf eos {
        type Mplseos;
        description "End of stack flag";
      }
      uses MPLS-SH-LEAF;
    }
  }

  grouping PREFIX-TABLE {
    description "Common node of ipv6-unicast, ipv4-unicast";

    container prefixes {
      description "Table of IP prefixes";

      list prefix {
        key "prefix";
        description "Prefix data";
        leaf prefix {
          type string;
          description "Prefix";
        }
        uses NEXT-HOP-TABLE;
        uses STATE;
      }
    }
  }

  grouping NEXT-HOP-TABLE {
    description "Common node of prefix, label";

    container next-hops {
      description
        "A next-hop associated with the forwarding
        instance";

      list next-hop {
        key "index";
        description
          "A next-hop associated with the forwarding
          instance";
        leaf index {
          type uint32;
          description
            "A unique index identifying the next-hop entry
            for the AFT entry";
        }
        uses FIB-OC-AFT-PATH;
      }
    }
  }

  container fib-statistics {
    config false;
    description "cef interface drops operational data";

    container nodes {
      description "List of nodes";

      list node {
        key "node-name";
        description "Specific node operational data";

        container drops {
          description "Specific node drops";
          uses FIB-STATISTICS-BAG-DROPS;
        }
        leaf node-name {
          type xr:Node-id;
          description "Node name";
        }
      }
    }
  }

  container fib {
    config false;
    description "fib";

    container nodes {
      description "Table of nodes";

      list node {
        key "node-name";
        description "Operational data for a specific Node";

        container global {
          description "FIB Global info";

          container fib-cofo {
            description "Collapsed Forwarding";

            container fib-cofo-idb {
              description "Collapsed Forwarding IDB Table";

              container fib-cofo-idb-table-entries {
                description
                  "Collapsed Forwarding Idb Table Entries";

                list fib-cofo-idb-table-entry {
                  description
                    "Collapsed Forwarding Idb Table Entries";
                  leaf sdr-id {
                    type uint32;
                    description "SDR ID value";
                  }
                  leaf if-index {
                    type uint32;
                    description "Interface Index";
                  }
                  uses FIB-SH-COFO-IDB-TBL-ENTRY-INFO;
                }
              }
            }

            container fib-cofo-table-id {
              description "Collapsed Forwarding Table Id Table";

              container fib-cofo-table-id-entries {
                description "Collapsed Forwarding Table Id Entries";

                list fib-cofo-table-id-entry {
                  description
                    "Collapsed Forwarding Idb Table Entries";
                  leaf sdr-id {
                    type uint32;
                    description "SDR ID value";
                  }
                  leaf protocol {
                    type Fib-protocol;
                    description "Protocol";
                  }
                  leaf rd {
                    type xr:Cisco-ios-xr-string;
                    description "Route Distinguisher";
                  }
                  leaf table-id {
                    type uint32;
                    description "Table Id";
                  }
                  uses FIB-SH-COFO-TBL-ID-ENTRY-INFO;
                }
              }

              container fib-cofo-table-id-summary {
                description "Collapsed Forwarding Table Id Entries";
                uses FIB-SH-COFO-TBL-ID-DB-SUM;
              }
            }
          }

          container summary {
            description "Global Summary";

            container total {
              description "Display total counters and common info";
              uses FIB-GLOBAL-SUMMARY-TOTAL;
            }

            container protos {
              description "Proto Table";

              list proto {
                key "protocol-name";
                description "Proto Table entry";
                leaf protocol-name {
                  type Fibafi-proto;
                  description "Protocol Name";
                }
                uses FIB-GLOBAL-SUMMARY-PROTO;
              }
            }
          }

          container object-history {
            description "Object History";

            container obj-history-protos {
              description "Proto Table";

              list obj-history-proto {
                key "protocol-name";
                description "Protocol Table entry";
                leaf protocol-name {
                  type Fibafi-proto;
                  description "Protocol Name";
                }
                uses FIB-GLOBAL-SUMMARY-OBJ-HISTORY-PROTO;
              }
            }
          }
        }

        container protocols {
          description "Protocol table";

          list protocol {
            key "protocol-name";
            description "Protocol table entry";

            container issu-state {
              description "CEF ISSU State";
              uses FIB-ISSU-STATE;
            }

            container resource {
              description "Resource information";

              container resource-detail-info {
                description "Detailed info";
                uses FIB-SH-RSRC-AVAIL-STATE;
              }

              container resource-hardware-ingress-info {
                description
                  "Detailed info with ingress hardware info";
                uses FIB-SH-RSRC-AVAIL-STATE;
              }

              container resource-hardware-egress-info {
                description
                  "Detailed info with egress hardware info";
                uses FIB-SH-RSRC-AVAIL-STATE;
              }

              container resource-summary-info {
                description "Summary info";
                uses FIB-SH-RSRC-AVAIL-STATE;
              }
            }

            container fib-summaries {
              description "Summary for FIB tables";

              list fib-summary {
                description "Summary for the requested fib table";
                leaf vrf-name {
                  type xr:Cisco-ios-xr-string;
                  description "VRF Name";
                }
                leaf table-id {
                  type xr:Hex-integer;
                  description "FIB table id";
                }
                uses FIB-SH-SUM;
              }
            }

            container external-summary-all {
              description "Summary for all external clients";
              uses FIB-SH-TBL-EXT-SUM-ALL;
            }

            container frr-log {
              description "Table of Fast Reroute activation logs";

              container frr-interfaces {
                description "FRR Interface Table";

                list frr-interface {
                  key "frr-interface-name";
                  description "Specify FRR Interface Name";

                  container logs {
                    description "FRR log table";

                    list log {
                      key "log-index";
                      description
                        "Specify index into frr log table";
                      leaf log-index {
                        type uint32;
                        description "FRR Log Index";
                      }
                      uses FIB-SH-FRR-LOG;
                    }
                  }
                  leaf frr-interface-name {
                    type xr:Interface-name;
                    description "Interface Name";
                  }
                }
              }
            }

            container vrfs {
              description "VRF table";

              list vrf {
                key "vrf-name";
                description "VRF table entry";

                container ip-prefix-details {
                  description "IP FIB prefix detail table";

                  list ip-prefix-detail {
                    description "IP FIB prefix detail table entry";
                    leaf prefix {
                      type inet:ip-address-no-zone;
                      description "Destination IP address";
                    }
                    leaf prefix-length {
                      type xr:Ipv6-prefix-length;
                      description "IP prefix length";
                    }
                    uses FIB-SH-TBL-FIB;
                  }
                }

                container summary {
                  description "Operational data for FIB Tablee";
                  uses FIB-SH-SUM;
                }

                container interface-infos {
                  description "Table of InterfaceInfo";

                  list interface-info {
                    key "link-type";
                    description "Specify link type";

                    container interfaces {
                      description "Table of interfaces";

                      list interface {
                        key "interface-name";
                        description "Specify Interface name";
                        leaf interface-name {
                          type xr:Interface-name;
                          description "Interface Name";
                        }
                        uses FIB-SH-INT;
                      }
                    }
                    leaf link-type {
                      type Fib-link;
                      description "Link type";
                    }
                  }
                }

                container ip-prefix-briefs {
                  description "IP FIB prefix brief table";

                  list ip-prefix-brief {
                    description "IP FIB prefix brief table entry";
                    leaf prefix {
                      type inet:ip-address-no-zone;
                      description "Destination IP address";
                    }
                    leaf prefix-length {
                      type xr:Ipv6-prefix-length;
                      description "IP prefix length";
                    }
                    uses FIB-SH-TBL-FIB;
                  }
                }

                container nh-info {
                  description "FIB NHInfo table";

                  container nh-info-detail-hardware-egress {
                    description
                      "NHInfoTable is accessed by two keys;
                      {NHInterface,NHAddress}";

                    container "nh-info-special-detail-hardware"+
                      "-egress" {
                      description
                        "Detail hardware engress info for Special
                        nhinfo";

                      container "nh-info-special-null-detail"+
                        "-hardware-egress" {
                        description
                          "Detail hardware engress info for
                          special-null NHInfo entry";
                        uses FIB-SH-NHINFO;
                      }

                      container "nh-info-special-punt-detail"+
                        "-hardware-egress" {
                        description
                          "Detail hardware engress info for
                          special-punt NHInfo entry";
                        uses FIB-SH-NHINFO;
                      }

                      container "nh-info-special-discard-detail"+
                        "-hardware-egress" {
                        description
                          "Detail hardware engress info for
                          special-discard NHInfo entry";
                        uses FIB-SH-NHINFO;
                      }

                      container "nh-info-special-drop-detail"+
                        "-hardware-egress" {
                        description
                          "Detail hardware engress info for
                          special-drop NHInfo entry";
                        uses FIB-SH-NHINFO;
                      }
                    }

                    container "nh-info-local-detail-hardware"+
                      "-egresses" {
                      description "Local (non-remote) nhinfo";

                      list nh-info-local-detail-hardware-egress {
                        description "Detail NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-remote-detail-hardware"+
                      "-egresses" {
                      description
                        "Detail hardware egress info for remote
                        NHInfo table";

                      list nh-info-remote-detail-hardware-egress {
                        description "Detail NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }

                  container nh-info-detail {
                    description
                      "NHInfoTable is accessed by two keys;
                      {NHInterface,NHAddress}";

                    container nh-info-local-details {
                      description "Local (non-remote) nhinfo";

                      list nh-info-local-detail {
                        description "Detail NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-special-detail {
                      description "Special nhinfo";

                      container nh-info-special-punt-detail {
                        description
                          "Detail special-punt NHInfo entry";
                        uses FIB-SH-NHINFO;
                      }

                      container nh-info-special-drop-detail {
                        description
                          "Detail special-drop NHInfo entry";
                        uses FIB-SH-NHINFO;
                      }

                      container nh-info-special-null-detail {
                        description
                          "Detail special-null NHInfo entry";
                        uses FIB-SH-NHINFO;
                      }

                      container nh-info-special-discard-detail {
                        description
                          "Detail special-discard NHInfo entry";
                        uses FIB-SH-NHINFO;
                      }
                    }

                    container nh-info-remote-details {
                      description "Detailed Remote NHInfo table";

                      list nh-info-remote-detail {
                        description "Detail NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }

                  container nh-info-detail-hardware-ingress {
                    description
                      "NHInfoTable is accessed by two keys;
                      {NHInterface,NHAddress}";

                    container "nh-info-remote-detail-hardware"+
                      "-ingresses" {
                      description
                        "Detailed hardware ingress info for
                        remote NHInfo table";

                      list nh-info-remote-detail-hardware-ingress {
                        description "Detail NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-local-detail-hardware"+
                      "-ingresses" {
                      description "Local (non-remote) nhinfo";

                      list nh-info-local-detail-hardware-ingress {
                        description "Detail NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container "nh-info-special-detail-hardware"+
                      "-ingress" {
                      description "Special nhinfo";

                      container "nh-info-special-punt-detail"+
                        "-hardware-ingress" {
                        description
                          "Detail hardware ingress info for
                          special-punt NHInfo entry";
                        uses FIB-SH-NHINFO;
                      }

                      container "nh-info-special-null-detail"+
                        "-hardware-ingress" {
                        description
                          "Detail hardware ingress info for
                          special-null NHInfo entry";
                        uses FIB-SH-NHINFO;
                      }

                      container "nh-info-special-drop-detail"+
                        "-hardware-ingress" {
                        description
                          "Detail hardware ingress info for
                          special-drop NHInfo entry";
                        uses FIB-SH-NHINFO;
                      }

                      container "nh-info-special-discard-detail"+
                        "-hardware-ingress" {
                        description
                          "Detail hardware ingress info for
                          special-discard NHInfo entry";
                        uses FIB-SH-NHINFO;
                      }
                    }
                  }

                  container nh-info-brief {
                    description
                      "NHInfoTable is accessed by two keys;
                      {NHInterface,NHAddress}";

                    container nh-info-special-brief {
                      description "Special nhinfo";

                      container nh-info-special-discard-brief {
                        description
                          "Brief special-discard NHInfo entry";
                        uses FIB-SH-NHINFO;
                      }

                      container nh-info-special-null-brief {
                        description
                          "Brief special-null NHInfo entry";
                        uses FIB-SH-NHINFO;
                      }

                      container nh-info-special-punt-brief {
                        description
                          "Brief special-punt NHInfo entry";
                        uses FIB-SH-NHINFO;
                      }

                      container nh-info-special-drop-brief {
                        description
                          "Brief special-drop NHInfo entry";
                        uses FIB-SH-NHINFO;
                      }
                    }

                    container nh-info-remote-briefs {
                      description "remote nhinfo";

                      list nh-info-remote-brief {
                        description "Detail NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }

                    container nh-info-local-briefs {
                      description "Local (non-remote) nhinfo";

                      list nh-info-local-brief {
                        description "Brief NHinfo entry";
                        leaf nh-interface-name {
                          type xr:Interface-name;
                          description "Interface Name";
                        }
                        leaf nh-proto {
                          type Fib-protocol;
                          description "Next-hop proto";
                        }
                        leaf nh-pfx-length {
                          type uint32;
                          description "Next-hop prefix length";
                        }
                        leaf nh-address {
                          type xr:Cisco-ios-xr-string;
                          description
                            "Next-hop address in string format";
                        }
                        uses FIB-SH-NHINFO;
                      }
                    }
                  }
                }
                leaf vrf-name {
                  type xr:Cisco-ios-xr-string;
                  description "VRF Name";
                }
              }
            }

            container exact-routes {
              description "Exact Route Table";

              list exact-route {
                description
                  "Exact route for the given source and
                  destination addresses";
                leaf protocol-name {
                  type Fib-protocol;
                  description "Protocol Name";
                }
                leaf vrf-name {
                  type xr:Cisco-ios-xr-string;
                  description "VRF Name";
                }
                leaf source {
                  type xr:Cisco-ios-xr-string;
                  description "Source address";
                }
                leaf destination {
                  type xr:Cisco-ios-xr-string;
                  description "Destination address";
                }
                leaf ipv6-flow-label {
                  type Fibipv6-flow-label;
                  description
                    "IPv6 flow label (applies only to and used
                    only for IPv6)";
                }
                uses FIB-SH-TBL-FIB;
              }
            }

            container protocol-global {
              description "FIB ipv6 global information";

              container segment-routing {
                description
                  "FIB ipv6 global segment routing information";

                container srv6 {
                  description
                    "FIB ipv6 global segment routing srv6
                    information";
                  uses FIB-SRV6-GBL-UPD;
                }
              }
            }

            container nh-ids {
              description
                "NHIdTable is accessed by two keys; {NHId}
                and/or {NHInterface,NHAddress";

              list nh-id {
                description "NextHopId table entry";
                leaf nh-id {
                  type uint32;
                  description "NexthopId Value";
                }
                leaf nh-interface-name {
                  type xr:Interface-name;
                  description "Interface Name";
                }
                leaf nh-address {
                  type xr:Cisco-ios-xr-string;
                  description
                    "Next-hop address in string format (e.g., 1
                    .2.3.4)";
                }
                uses FIB-SH-NHID-ENTRY;
              }
            }

            container frr-nhinfo-pendings {
              description "FIB FRR NHINFO pending information";

              list frr-nhinfo-pending {
                description "FIB FRR Nhinfo pending information";
                leaf queue-index {
                  type uint32;
                  description "Queue Index";
                }
                leaf frr-type {
                  type Fibfrr;
                  description "FRR Type";
                }
                leaf link-type {
                  type Fib-link;
                  description "Link Type";
                }
                leaf prefix-length {
                  type uint32;
                  description "Prefix Length";
                }
                leaf interface-name {
                  type xr:Interface-name;
                  description "Interface Name";
                }
                leaf main-interface-name {
                  type xr:Interface-name;
                  description "Main Interface Name";
                }
                leaf next-hop-prefix {
                  type inet:ip-address-no-zone;
                  description "NextHop Address";
                }
                leaf replicated-nh-type {
                  type Fibnh-info-repl;
                  description "Replicated NextHop Type";
                }
                uses FIB-SH-FRR-NHINFO;
              }
            }

            container external-client-summaries {
              description "External Client Summary Table";

              list external-client-summary {
                description "Summary of the external clients";
                leaf ecd-ver {
                  type uint32;
                  description "Ecd Version";
                }
                leaf id {
                  type uint32;
                  description
                    "ID of the client: ECDv1 is component id,
                    ECDv2 is client id";
                }
                uses FIB-SH-TBL-EXT-CLIENT-SUM;
              }
            }

            container misc {
              description "CEF misc hidden data";
              uses FIB-SH-MISC;
            }

            container local-label {
              description "Local label";

              container conflicts {
                description "FIB Local-label conflicts database";

                list conflict {
                  description "CEF Local-label conflicts entry";
                  leaf label {
                    type Fib-label;
                    description "Local label";
                  }
                  leaf source {
                    type Fib-route-source;
                    description "Route source";
                  }
                  leaf ll-ctype {
                    type Fibllc-entry;
                    description "Type of entry";
                  }
                  leaf pfx-tbl-id {
                    type uint32;
                    description "Table ID of IP prefix";
                  }
                  leaf prefix {
                    type xr:Cisco-ios-xr-string;
                    description "IP Prefix";
                  }
                  leaf prefix-len {
                    type uint32;
                    description "Length of IP Prefix";
                  }
                  uses FIB-MPLS-LLC;
                }
              }
            }
            leaf protocol-name {
              type Fib-protocol;
              description "Protocol Name ";
            }
          }
        }
        leaf node-name {
          type xr:Node-id;
          description "Node name";
        }
      }
    }
  }

  container oc-aft-l3 {
    config false;
    description "oc aft l3";

    container vrfs {
      description "Table VRFs - openconfig network-instances";

      list vrf {
        key "vrf-name";
        description "VRF/network-instace table";

        container abstract-forwarding-tables {
          description "Abstract forwarding table per FIB protocol";

          container mpls {
            description "MPLS abstract forwarding table";

            container labels {
              description "Table of MPLS labels";

              list label {
                key "label";
                description "Label data";
                leaf label {
                  type string;
                  description "Label";
                }
                uses NEXT-HOP-TABLE;
                uses STATE;
              }
            }
          }

          container ipv6-unicast {
            description "IPv6 abstract forwarding table";
            uses PREFIX-TABLE;
          }

          container ipv4-unicast {
            description "IPv4 abstract forwarding table";
            uses PREFIX-TABLE;
          }
        }
        leaf vrf-name {
          type xr:Cisco-ios-xr-string;
          description "Network Instance Name";
        }
      }
    }
  }

  container mpls-forwarding {
    config false;
    description "mpls forwarding";

    container nodes {
      description "Table of Nodes";

      list node {
        key "node-name";
        description "Operational data for a specific Node";

        container forwarding-summary {
          description "MPLS forwarding summary";
          uses MPLS-FWDING-SUMMARY;
        }

        container frr-logs {
          description "FRR Log Table";

          list frr-log {
            key "event-id";
            description "FRR Log information";
            leaf event-id {
              type uint32;
              description "Event ID";
            }
            uses FIB-MPLS-FRR-EVENT;
          }
        }

        container label-fib {
          description "Labels For FIB";

          container vrfs {
            description "Table of VRFs";

            list vrf {
              key "vrf-name";
              description "VRF table";
              leaf vrf-name {
                type xr:Cisco-ios-xr-string;
                description "VRF Name";
              }
              uses INFORMATION;
            }
          }

          container forwarding-details {
            description "MPLS Forwarding Detail table";

            list forwarding-detail {
              description "MPLS forwarding details";
              leaf label-value {
                type Mpls-label;
                description "Local label value";
              }
              leaf eos {
                type Mplseos;
                description "End of stack flag";
              }
              uses MPLS-SH-LEAF;
            }
          }

          container forwarding {
            description "Forwarding filtering details";
            uses INFORMATION;
          }

          container label-security {
            description "MPLS label security";

            container interfaces {
              description "MPLS label security interface table";

              list interface {
                key "interface-name";
                description "Specify interface Name";
                leaf interface-name {
                  type xr:Interface-name;
                  description "Interface Name";
                }
                uses MPLS-LABEL-SECURITY-INTF;
              }
            }

            container summary {
              description "MPLS label security summary";
              uses MPLS-LABEL-SECURITY-SUMMARY;
            }
          }
        }

        container tunnel {
          description "TE Tunnel information";

          container forwarding-tunnels {
            description "Forwarding details for TE tunnels";

            list forwarding-tunnel {
              key "interface-name";
              description
                "Forwarding information for the TE tunnel";
              leaf interface-name {
                type xr:Interface-name;
                description "Interface Name";
              }
              uses MPLS-SH-TEHEAD;
            }
          }
        }

        container frr-database {
          description "MPLS forwarding FRR Database";

          container frrdb-summary {
            description "MPLS forwarding FRR Database Summary";
            uses FIB-MPLS-FRR-DB-SUM;
          }

          container frrdb-protected-interface-table-summaries {
            description
              "MPLS forwarding FRR Database Protected
              Interface Summary Table";

            list frrdb-protected-interface-table-summary {
              key "interface-name";
              description
                "MPLS forwarding FRR Database Protected
                Interface Summary";
              leaf interface-name {
                type xr:Interface-name;
                description "Interface Name";
              }
              uses FIB-MPLS-FRR-DB-SUM;
            }
          }

          container frrdb-tunnel-midpoint-summary {
            description
              "MPLS forwarding FRR Database Tunnel Midpoint
              Summary";
            uses FIB-MPLS-FRR-DB-SUM;
          }

          container frrdb-tunnel-midpoints {
            description
              "MPLS forwarding FRR Database Tunnel Midpoint
              Table";

            list frrdb-tunnel-midpoint {
              key "local-label";
              description
                "MPLS forwarding FRR Database Tunnel Midpoint
                Entry";
              leaf local-label {
                type Mpls-label;
                description "Local label value";
              }
              uses MPLS-FRR-DB-ENTRY;
            }
          }

          container frrdb-tunnel-heads {
            description
              "MPLS forwarding FRR Database Tunnel Head
              Table";

            list frrdb-tunnel-head {
              key "interface-name";
              description
                "MPLS forwarding FRR Database Tunnel Head
                Entry";
              leaf interface-name {
                type xr:Interface-name;
                description "Interface Name";
              }
              uses MPLS-FRR-DB-ENTRY;
            }
          }

          container frrdb-tunnel-head-summary {
            description
              "MPLS forwarding FRR Database Tunnel Head
              Summary";
            uses FIB-MPLS-FRR-DB-SUM;
          }

          container frrdb-backup-interface-summaries {
            description
              "MPLS forwarding FRR Database Backup Interface
              Summary Table";

            list frrdb-backup-interface-summary {
              key "interface-name";
              description
                "MPLS forwarding FRR Database Backup
                Interface Summary";
              leaf interface-name {
                type xr:Interface-name;
                description "Interface Name";
              }
              uses FIB-MPLS-FRR-DB-SUM;
            }
          }
        }
        leaf node-name {
          type xr:Node-id;
          description "Node ID";
        }
      }
    }
  }
}
