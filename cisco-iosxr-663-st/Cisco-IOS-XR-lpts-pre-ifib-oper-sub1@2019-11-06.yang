submodule Cisco-IOS-XR-lpts-pre-ifib-oper-sub1 {

  belongs-to Cisco-IOS-XR-lpts-pre-ifib-oper {
    prefix Cisco-IOS-XR-lpts-pre-ifib-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lpts-pre-ifib package operational data.

     Copyright (c) 2013-2018 by Cisco Systems, Inc.
     All rights reserved.";

  revision "2019-11-06" {
    description
      "LPTS Punt Policer Support.";
  }

  revision "2019-10-23" {
    description
      "LPTS Punt Policer Support.";
  }

  revision "2018-11-26" {
    description
      "LPTS Domains Support.";
  }

  revision "2017-05-01" {
    description
      "Fixing backward compatibility error in module.";
  }

  revision "2016-11-22" {
    description
      "Initial revision for pre-ifib oper yang.";
  }

  revision "2015-11-09" {
    description
      "IOS XR 6.0 revision.";
  }


  grouping PUNT-POLICER-DOMAIN-LIST {
    description "LPTS Punt Policer Domain Information";
    leaf domain-index {
      type uint8;
      description "Domain Index";
    }
    leaf domain-name {
      type string;
      description "Domain Name";
    }
    leaf valid {
      type boolean;
      description "Domain is Valid";
    }
    leaf number-of-punt-types {
      type uint32;
      description "Number of Punt types";
    }

    list punt-type {
      description "Punt type List";
      uses PUNT-POLICER-TYPE-ENTRY;
    }

    list applied-config {
      description "Applied Policer Data";
      uses PUNT-POLICER-CONF-ENTRY;
    }
  }

  grouping PUNT-POLICER-CONF-ENTRY {
    description "LPTS applied punt policer data";
    leaf interface-handle {
      type xr:Interface-name;
      description "Interface Handle";
    }
    leaf virtual-interface {
      type boolean;
      description "Interface is Virtual";
    }
    leaf punt-name {
      type string;
      description "Punt Name";
    }
    leaf enabled {
      type boolean;
      description "Is Enabled";
    }
    leaf configured-rate {
      type uint32;
      description "Configured Policer Rate";
    }
    leaf domain-index {
      type uint8;
      description "Domain Index";
    }
    leaf punt-police-program-time {
      type string;
      description "Creation or Update Time";
    }
  }

  grouping PUNT-POLICER-TYPE-ENTRY {
    description "LPTS Punt type data";
    leaf punt-name {
      type string;
      description "Punt Name";
    }
    leaf configured {
      type boolean;
      description "Is Configured";
    }
    leaf active-cfg-state {
      type string;
      description "Active Cfg State";
    }
    leaf enabled {
      type boolean;
      description "Is Enabled";
    }
    leaf pending {
      type boolean;
      description "Is Pending";
    }
    leaf configured-rate {
      type uint32;
      description "Configured Policer Rate";
    }
    leaf operational-rate {
      type uint32;
      description "Operational Policer Rate";
    }
    leaf domain-name {
      type string;
      description "Domain Name";
    }
    leaf domain-index {
      type uint8;
      description "Domain Index";
    }
    leaf accepted {
      type uint64;
      description "Packets matched to accept";
    }
    leaf dropped {
      type uint64;
      description "Packets matched for drop";
    }
  }

  grouping PUNT-POLICER-INTERFACE-LIST {
    description "LPTS Punt Policer IFH Information";
    leaf interface-handle {
      type xr:Interface-name;
      description "Interface Handle";
    }
    leaf interface-name {
      type string;
      description "Interface Name";
    }
    leaf virtual-interface {
      type boolean;
      description "Interface is Virtual";
    }
    leaf number-of-punt-types {
      type uint32;
      description "Number of Punt types";
    }

    list punt-type {
      description "Punt type List";
      uses PUNT-POLICER-TYPE-ENTRY;
    }

    list applied-config {
      description "Applied Policer Data";
      uses PUNT-POLICER-CONF-ENTRY;
    }
  }

  grouping PUNT-POLICER-CFG-DATA {
    description "LPTS Punt Policer active Data";
    leaf has-config {
      type boolean;
      description "config presence";
    }
    leaf number-of-interfaces {
      type uint32;
      description "Number of Interfaces";
    }
    leaf number-of-domains {
      type uint32;
      description "Number of Domains";
    }

    list interface {
      description "Interface List";
      uses PUNT-POLICER-INTERFACE-LIST;
    }

    list domain {
      description "Domain List";
      uses PUNT-POLICER-DOMAIN-LIST;
    }
  }

  grouping PIFIB-PUNT-POLICER-DATA {
    description "LPTS Punt Policer Information";

    container config-data {
      description "Punt Policer Config Data";
      uses PUNT-POLICER-CFG-DATA;
    }
    leaf punt-policer-supported {
      type boolean;
      description "Punt Policer Supported";
    }
  }

  grouping DYNFLOWS-FLOW-ENTRY {
    description "LPTS Pre-IFIB Dynamic Flows Entry Data";
    leaf flow-name {
      type string;
      description "Flow Name";
    }
    leaf configurable {
      type boolean;
      description "Is Configurable";
    }
    leaf configured {
      type boolean;
      description "Is Configured";
    }
    leaf default-max {
      type uint32;
      description "Default Max";
    }
    leaf configured-max {
      type string;
      description "Configured Max";
    }
    leaf active-max {
      type uint32;
      description "Active Max";
    }
    leaf hardware-count {
      type uint32;
      description "Hardware Count";
    }
    leaf software-count {
      type uint32;
      description "Software Count";
    }
    leaf pending-software-entries {
      type boolean;
      description "Pending Software Entries";
    }
  }

  grouping PIFIB-DYNFLOWS-DATA {
    description "LPTS Pre-IFIB Dynamic Flows Data";
    leaf dynamic-flows-enabled {
      type boolean;
      description "Dynamic Flows Enabled";
    }
    leaf platform-supported-max {
      type uint32;
      description "Platform Max";
    }
    leaf platform-configured-max {
      type uint32;
      description "Platform Config Limit";
    }
    leaf platform-total-configured {
      type uint32;
      description "Platform Total Configured";
    }
    leaf total-hw-entries {
      type uint32;
      description "Total HW Entries";
    }
    leaf total-sw-entries {
      type uint32;
      description "Total SW Entries";
    }

    list flow {
      description "Flow Datalist";
      uses DYNFLOWS-FLOW-ENTRY;
    }
  }

  grouping DOMAIN-INTERFACE-LIST {
    description "LPTS Domain IFH Information";
    leaf interface-handle {
      type xr:Interface-name;
      description "Interface Handle";
    }
    leaf interface-name {
      type string;
      description "Interface Name";
    }
    leaf virtual-interface {
      type boolean;
      description "Interface is Virtual";
    }
  }

  grouping DOMAIN-INFO {
    description "LPTS Domain Information";
    leaf domain-name {
      type string;
      description "Domain Name";
    }
    leaf domain-index {
      type uint8;
      description "Domain Index";
    }
    leaf number-of-interfaces {
      type uint32;
      description "Number of Interfaces";
    }

    list interface {
      description "Interface List";
      uses DOMAIN-INTERFACE-LIST;
    }
  }

  grouping DOMAINS-CONFIG-DATA {
    description "LPTS Domains Data";
    leaf number-of-active-domains {
      type uint8;
      description "Number of Active Domains";
    }

    list domains-info {
      description "Domains Info";
      uses DOMAIN-INFO;
    }
  }

  grouping PIFIB-DOMAINS-DATA {
    description "LPTS interface Entry Information";

    container config-data {
      description "Domain Config Data";
      uses DOMAINS-CONFIG-DATA;
    }
    leaf domains-enabled {
      type boolean;
      description "Domains Enabled";
    }
    leaf number-of-supported-domains {
      type uint32;
      description "Number of Supported Domains";
    }
  }

  grouping PIFIB-SHOW-ENTRY {
    description "LPTS Pre-IFIB Entry Information";
    leaf vrf-name {
      type string;
      description "VRF Name";
    }
    leaf vid {
      type uint32;
      description "VRF ID";
    }
    leaf l3protocol {
      type uint32;
      description "Layer 3 Protocol";
    }
    leaf l4protocol {
      type uint32;
      description "Layer 4 Protocol";
    }
    leaf intf-name {
      type string;
      description "Interface Name";
    }
    leaf intf-handle {
      type uint32;
      description "Interface Handle";
    }
    leaf destination-addr {
      type string;
      description "Destination IP Address";
    }
    leaf source-addr {
      type string;
      description "Source IP Address";
    }
    leaf destination-type {
      type string;
      description "Destination Key Type";
    }
    leaf destination-value {
      type string;
      description "Destination Port/ICMP Type/IGMP Type";
    }
    leaf source-port {
      type string;
      description "Source port";
    }
    leaf is-frag {
      type uint8;
      description "Is Fragment";
    }
    leaf is-syn {
      type uint8;
      description "Is SYN";
    }
    leaf opcode {
      type string;
      description "Opcode";
    }
    leaf flow-type {
      type string;
      description "Flow type";
    }
    leaf listener-tag {
      type string;
      description "Listener Tag";
    }
    leaf local-flag {
      type uint8;
      description "Local Flag";
    }
    leaf is-fgid {
      type uint8;
      description "Is FGID or not";
    }
    leaf deliver-list-short {
      type string;
      description "Deliver List Short Format";
    }
    leaf deliver-list-long {
      type string;
      description "Deliver List Long Format";
    }
    leaf min-ttl {
      type uint8;
      description "Minimum TTL";
    }
    leaf accepts {
      type uint64;
      description "Packets matched to accept";
    }
    leaf drops {
      type uint64;
      description "Packets matched for drop";
    }
    leaf stale {
      type uint8;
      description "Is Stale";
    }
    leaf pifib-type {
      type uint8;
      description "sub Pre-IFIB type";
    }
    leaf pifib-program-time {
      type string;
      description "Creation or Update Time";
    }
    leaf domain-idx {
      type uint8;
      description "Domain Index";
    }
    leaf domain-name {
      type string;
      description "Domain Name";
    }
  }
}
