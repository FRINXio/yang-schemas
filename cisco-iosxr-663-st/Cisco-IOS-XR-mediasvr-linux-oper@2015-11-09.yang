module Cisco-IOS-XR-mediasvr-linux-oper {

  /*** NAMESPACE / PREFIX DEFINITION ***/

  namespace "http://cisco.com/ns/yang"+
    "/Cisco-IOS-XR-mediasvr-linux-oper";


  prefix "mediasvr-linux-oper";

  /*** LINKAGE (IMPORTS / INCLUDES) ***/

  import Cisco-IOS-XR-types { prefix "xr"; }

  include Cisco-IOS-XR-mediasvr-linux-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mediasvr-linux package operational data.

     This module contains definitions
     for the following management objects:
       media-svr: Media server CLI operations

     Copyright (c) 2013-2018 by Cisco Systems, Inc.
     All rights reserved.";

  revision "2015-11-09" {
    description
      "IOS XR 6.0 revision.";
  }


  container media-svr {
    config false;
    description "Media server CLI operations";

    container all {
      description "Show Media bag";
      uses SHOW-MEDIA-EDM-STRING;
    }

    container location-descriptions {
      description "Show Media";

      list location-description {
        key "node";
        description "Location specified in location";
        leaf node {
          type xr:Node-id;
          description "Node location";
        }
        uses SHOW-MEDIA-EDM-STRING;
      }
    }
  }
}
