submodule Cisco-IOS-XR-crypto-ssh-oper-sub1 {

  belongs-to Cisco-IOS-XR-crypto-ssh-oper {
    prefix Cisco-IOS-XR-crypto-ssh-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR crypto-ssh package operational data.

     Copyright (c) 2013-2018 by Cisco Systems, Inc.
     All rights reserved.";

  revision "2017-08-25" {
    description
      "Introducing show ssh history CLI.";
  }

  revision "2017-05-01" {
    description
      "Fixing backward compatibility error in module.";
  }

  revision "2015-06-02" {
    description
      "IOS XR 5.3.2 revision.";
  }

  revision "2015-01-07" {
    description
      "IOS XR 5.3.1 revision.";
  }


  grouping SSH-SERVER-PARAMS {
    description "Information about ssh server running parameters";
    leaf version {
      type string {
        length "0..10";
      }
      description "Version";
    }
    leaf port {
      type uint32;
      description "SSH Port";
    }
    leaf vrf {
      type string {
        length "0..500";
      }
      description "Vrfs and acls";
    }
    leaf netconfport {
      type uint32;
      description "Netconf Port";
    }
    leaf netconfvrf {
      type string {
        length "0..500";
      }
      description "Netconf vrfs and acls";
    }
    leaf netconfver {
      type string {
        length "0..10";
      }
      description "Netconf Version";
    }
    leaf hostkeyalgo {
      type string {
        length "0..200";
      }
      description "Hostkey algorithms";
    }
    leaf kexalgo {
      type string {
        length "0..200";
      }
      description "Key exchange algorithms";
    }
    leaf cipheralgo {
      type string {
        length "0..200";
      }
      description "Encryption algorithms";
    }
    leaf macalgo {
      type string {
        length "0..200";
      }
      description "Mac algorithms";
    }
    leaf backupserver {
      type string {
        length "0..100";
      }
      description "Backup SSH server";
    }
    leaf dscp {
      type uint32;
      description "Dscp";
    }
    leaf ratelimit {
      type uint32;
      description "ratelimit";
    }
    leaf sessionlimit {
      type uint32;
      description "session limit";
    }
    leaf rekeytime {
      type uint32;
      description "Rekey Time";
    }
    leaf rekeyvolume {
      type uint32;
      description "Rekey Volume";
    }
    leaf windowscalefactor {
      type uint32;
      description "Window scale factor";
    }
    leaf passwordauthen {
      type boolean;
      description "Password Authentication support";
    }
    leaf keyboardinteractiveauthen {
      type boolean;
      description "Pubkey Authentication support";
    }
    leaf pubkeyauthen {
      type boolean;
      description "Pubkey Authentication support";
    }
    leaf certificateauthen {
      type boolean;
      description "Certificate based Authentication support";
    }
  }
}
