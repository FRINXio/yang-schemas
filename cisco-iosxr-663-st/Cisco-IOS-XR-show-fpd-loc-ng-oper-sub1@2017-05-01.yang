submodule Cisco-IOS-XR-show-fpd-loc-ng-oper-sub1 {

  belongs-to Cisco-IOS-XR-show-fpd-loc-ng-oper {
    prefix Cisco-IOS-XR-show-fpd-loc-ng-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR show-fpd-loc-ng package operational data.

     Copyright (c) 2013-2018 by Cisco Systems, Inc.
     All rights reserved.";

  revision "2017-05-01" {
    description
      "Fixing backward compatibility error in module.";
  }

  revision "2015-11-09" {
    description
      "IOS XR 6.0 revision.";
  }


  grouping FPD-LOCATION-NAME {
    description "card location name string";
    leaf location-name {
      type string;
      description "card location";
    }
  }

  grouping FPD-SHOW-LOCATION-NAME-LIST {
    description "card location name string list";

    list location-name {
      description "card location list";
      uses FPD-LOCATION-NAME;
    }
  }

  grouping FPD-PKG-INFO {
    description "fpd pkg info";
    leaf card-type {
      type string;
      description "card type";
    }
    leaf fpd-desc {
      type string;
      description "fpd desc";
    }
    leaf upgrade-method {
      type string;
      description "reload or not";
    }
    leaf fpd-ver {
      type string;
      description "fpd version";
    }
    leaf min-sw-ver {
      type string;
      description "minimum sw version";
    }
    leaf min-hw-ver {
      type string;
      description "minimum hw version";
    }
  }

  grouping FPD-PKG-INFO-LIST {
    description "fpd pkg info list ";

    list fpd-pkg-data {
      description " fpd pkg list ";
      uses FPD-PKG-INFO;
    }
  }

  grouping FPD-LOC-INFO {
    description "fpd loc info";
    leaf location {
      type string;
      description "fpd location";
    }
    leaf fpd-name {
      type string;
      description "fpd name";
    }
  }

  grouping FPD-LOC-INFO-LIST {
    description "card location name string list";

    list fpd-name {
      description "Fpd name list";
      uses FPD-LOC-INFO;
    }
  }

  grouping FPD-INFO {
    description "fpd info";
    leaf location {
      type string;
      description "fpd location";
    }
    leaf card-name {
      type string;
      description "Name of card on which fpd is located";
    }
    leaf fpd-name {
      type string;
      description "fpd name";
    }
    leaf hw-version {
      type string;
      description "hadware version";
    }
    leaf secure-boot-attr {
      type string;
      description "secure boot attribur";
    }
    leaf status {
      type string;
      description "status of the fpd";
    }
    leaf running-version {
      type string;
      description "image running version ";
    }
    leaf programd-version {
      type string;
      description "image programd version";
    }
  }

  grouping FPD-INFO-LIST {
    description "fpd info list";
    leaf upgrade-status {
      type string;
      description "Either Upgrading or free used by CTC ";
    }

    list fpd-info-detaile {
      description " fpd list with all detailes";
      uses FPD-INFO;
    }
  }
}
