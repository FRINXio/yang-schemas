module Cisco-IOS-XR-ethernet-cfm-datatypes {

  /*** NAMESPACE / PREFIX DEFINITION ***/

  namespace "http://cisco.com/ns/yang"+
    "/Cisco-IOS-XR-ethernet-cfm-datatypes";


  prefix "ethernet-cfm-datatypes";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2018 by Cisco Systems, Inc.
     All rights reserved.";

  revision "2015-11-09" {
    description
      "IOS XR 6.0 revision.";
  }

  typedef Cfm-bnm-wtr {
    type uint32 {
      range "0..600";
    }
    description "Cfm bnm wtr";
  }
  typedef Cfm-ccm-interval {
    type enumeration {
      enum 3.3ms {
        value 1;
        description "3.3ms";
      }
      enum 10ms {
        value 2;
        description "10ms";
      }
      enum 100ms {
        value 3;
        description "100ms";
      }
      enum 1s {
        value 4;
        description "1s";
      }
      enum 10s {
        value 5;
        description "10s";
      }
      enum 1m {
        value 6;
        description "1m";
      }
      enum 10m {
        value 7;
        description "10m";
      }
    }
    description "Cfm ccm interval";
  }
  typedef Cfm-mep-id {
    type uint32 {
      range "1..8191";
    }
    description "Cfm mep id";
  }
  typedef Cfm-bnm-hold-off {
    type uint32 {
      range "0..600";
    }
    description "Cfm bnm hold off";
  }
  typedef Cfm-level {
    type uint32 {
      range "0..7";
    }
    description "Cfm level";
  }
  typedef Bandwidth-notification-state {
    type enumeration {
      enum ok {
        value 1;
        description "Link is not degraded";
      }
      enum degraded {
        value 2;
        description "Link is in degraded state";
      }
    }
    description "Bandwidth notification state";
  }
  typedef Cfm-cos-bits {
    type uint32 {
      range "0..7";
    }
    description "Cfm cos bits";
  }
  typedef Cfm-bnm-loss-threshold {
    type uint32 {
      range "2..255";
    }
    description "Cfm bnm loss threshold";
  }
  typedef Cfm-ais-interval {
    type enumeration {
      enum 1s {
        value 4;
        description "1s";
      }
      enum 1m {
        value 6;
        description "1m";
      }
    }
    description "Cfm ais interval";
  }
  typedef Cfm-mep-dir {
    type enumeration {
      enum up {
        value 0;
        description "Up MEP";
      }
      enum down {
        value 1;
        description "Down MEP";
      }
    }
    description "Cfm mep dir";
  }
}
