module Cisco-IOS-XR-ocni-oper {

  /*** NAMESPACE / PREFIX DEFINITION ***/

  namespace "http://cisco.com/ns/yang/Cisco-IOS-XR-ocni-oper";


  prefix "ocni-oper";

  /*** LINKAGE (IMPORTS / INCLUDES) ***/

  include Cisco-IOS-XR-ocni-oper-sub1 {
    revision-date 2017-11-23;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ocni package operational data.

     This module contains definitions
     for the following management objects:
       ocni-ni-base: An OpenConfig description of a network-instance.
         This may be a Layer 3 forwarding construct such as a virtual
         routing and forwarding (VRF) instance, or a Layer 2 instance
         such as a virtual switch instance (VSI). Mixed Layer 2 and
         Layer 3 instances are also supaported. Copyright (c) 2017 by
         Cisco Systems, Inc.  All rights reserved.

     Copyright (c) 2013-2018 by Cisco Systems, Inc.
     All rights reserved.";

  revision "2017-11-23" {
    description
      "Support for telemetry backend code.";
  }

  revision "2015-11-09" {
    description
      "IOS XR 6.0 revision.";
  }


  container ocni-ni-base {
    config false;
    description
      "An OpenConfig description of a network-instance.
      This may be a Layer 3 forwarding construct such
      as a virtual routing and forwarding (VRF)
      instance, or a Layer 2 instance such as a virtual
      switch instance (VSI). Mixed Layer 2 and Layer 3
      instances are also supaported. Copyright (c) 2017
      by Cisco Systems, Inc.  All rights reserved.";

    container network-instances {
      description
        "Network instances configured on the local system";

      list network-instance {
        key "name";
        description
          "Network instances configured on the local
          system";
        leaf name {
          type string;
          description
            "A unique name identifying the network instance";
        }
        uses OVERLAY-OCNI-NI-BASE-NETWORK-INSTANCE;
      }
    }
  }
}
