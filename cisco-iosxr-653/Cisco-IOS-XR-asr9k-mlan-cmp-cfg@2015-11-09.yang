module Cisco-IOS-XR-asr9k-mlan-cmp-cfg {

  /*** NAMESPACE / PREFIX DEFINITION ***/

  namespace "http://cisco.com/ns"+
    "/yang/Cisco-IOS-XR-asr9k-mlan-cmp-cfg";


  prefix "asr9k-mlan-cmp-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-mlan-cmp package configuration.

     This module contains definitions
     for the following management objects:
       mlan-disable-cmp: Disable/Enable CMP

     Copyright (c) 2013-2018 by Cisco Systems, Inc.
     All rights reserved.";

  revision "2015-11-09" {
    description
      "IOS XR 6.0 revision.";
  }


  container mlan-disable-cmp {
    description "Disable/Enable CMP";

    container nodes {
      description
        "Fully qualified RSP4/RSP4s/RP2 card
        specification";

      list node {
        key "node-name";
        description "A node";
        leaf disable {
          type empty;
          description "Disable CMP";
        }
        leaf node-name {
          type xr:Node-id;
          description "NodeName";
        }
      }
    }
  }
}
