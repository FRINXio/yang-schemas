submodule Cisco-IOS-XR-asr9k-fsi-oper-sub1 {

  belongs-to Cisco-IOS-XR-asr9k-fsi-oper {
    prefix Cisco-IOS-XR-asr9k-fsi-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-fsi package operational data.

     Copyright (c) 2013-2018 by Cisco Systems, Inc.
     All rights reserved.";

  revision "2015-11-09" {
    description
      "IOS XR 6.0 revision.";
  }


  grouping FSI-GENERIC-SHOW-COUNTER {
    description "Structure containing counter info";
    leaf count {
      type uint64;
      description "Counter";
    }
    leaf counter-name {
      type string;
      description "Counter Name";
    }
  }

  grouping FSI-GENERIC-STATS {
    description "Structure containing all stats of one type";

    list fsi-stat {
      max-elements "60";
      description "Stats Table";
      uses FSI-GENERIC-SHOW-COUNTER;
    }
  }

  grouping FSI-SHOW-GENERIC-STATS {
    description "Bag containing fsi stats";
    leaf last-clear-time {
      type uint64;
      description "Last Clear Time";
    }
    leaf stat-table-name {
      type string;
      description "Stat Table Name";
    }

    list stats-table {
      description "Array of counters ";
      uses FSI-GENERIC-STATS;
    }
  }
}
