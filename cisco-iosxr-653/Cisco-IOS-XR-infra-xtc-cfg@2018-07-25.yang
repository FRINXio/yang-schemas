module Cisco-IOS-XR-infra-xtc-cfg {

  /*** NAMESPACE / PREFIX DEFINITION ***/

  namespace "http://cisco.com/ns/yang/Cisco-IOS-XR-infra-xtc-cfg";


  prefix "infra-xtc-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-xtc package configuration.

     This module contains definitions
     for the following management objects:
       pce: PCE configuration data

     Copyright (c) 2013-2018 by Cisco Systems, Inc.
     All rights reserved.";

  revision "2018-07-25" {
    description
      "Removed incorrect mandatory specifications.";
  }

  revision "2018-07-02" {
    description
      "Removed mandatory specification from Netconf SSH username/password";
  }

  revision "2017-09-30" {
    description
      "Ensure propagation of MDA mandatory state to YANG model.";
  }

  revision "2017-09-07" {
    description
      "Fixed type translation error.";
  }

  revision "2016-05-31" {
    description
      "Revision description string.";
  }

  revision "2015-11-09" {
    description
      "IOS XR 6.0 revision.";
  }

  typedef Pce-segment {
    type enumeration {
      enum ipv4-address {
        value 1;
        description "IPv4 Address";
      }
      enum mpls-label {
        value 3;
        description "MPLS Label";
      }
    }
    description "Pce segment";
  }
  typedef Pce-path-hop {
    type enumeration {
      enum mpls {
        value 1;
        description "Segment-routing MPLS";
      }
      enum srv6 {
        value 2;
        description "Segment-routing v6";
      }
    }
    description "Pce path hop";
  }
  typedef Pce-path {
    type enumeration {
      enum explicit {
        value 1;
        description "Explicit";
      }
      enum dynamic {
        value 2;
        description "Dynamic";
      }
    }
    description "Pce path";
  }
  typedef Pce-disjoint-path {
    type enumeration {
      enum link {
        value 1;
        description "Link";
      }
      enum node {
        value 2;
        description "Node";
      }
      enum srlg {
        value 3;
        description "SRLG";
      }
      enum srlg-node {
        value 4;
        description "SRLG Node";
      }
    }
    description "Pce disjoint path";
  }
  typedef Pce-end-point {
    type enumeration {
      enum end-point-type-ipv4 {
        value 1;
        description "IPv4 endpoint address";
      }
      enum end-point-type-ipv6 {
        value 2;
        description "IPv6 endpoint address";
      }
    }
    description "Pce end point";
  }
  typedef Pce-binding-sid {
    type enumeration {
      enum mpls-label-specified {
        value 1;
        description "Use specified BSID MPLS label";
      }
      enum mpls-label-any {
        value 2;
        description "Allocate BSID MPLS label";
      }
    }
    description "Pce binding sid";
  }
  typedef Pce-metric {
    type enumeration {
      enum igp {
        value 1;
        description "IGP metric type";
      }
      enum te {
        value 2;
        description "TE metric type";
      }
      enum hopcount {
        value 3;
        description "Hopcount metric type";
      }
      enum latency {
        value 12;
        description "Latency metric type";
      }
    }
    description "Pce metric";
  }
  typedef Pcerest-authentication {
    type enumeration {
      enum basic {
        value 1;
        description "Basic HTTP auth";
      }
      enum digest {
        value 2;
        description "MD5-Digest HTTP auth";
      }
    }
    description "Pcerest authentication";
  }
  typedef Pce-explicit-path-hop {
    type enumeration {
      enum address {
        value 1;
        description "Address";
      }
      enum sid-node {
        value 2;
        description "SID Node";
      }
      enum sid-adjancency {
        value 3;
        description "SID Adjacency";
      }
      enum binding-sid {
        value 4;
        description "Binding SID";
      }
    }
    description "Pce explicit path hop";
  }

  grouping ENABLE {
    description
      "Common node of pce, lsp-name, disjoint-path,
      group, rsvp-te, explicit-path, pcc-address, rest,
      rest-user, netconf";
    leaf enable {
      type empty;
      description "True only";
    }
  }

  container pce {
    description "PCE configuration data";

    container ipv6-state-syncs {
      description "Standby IPv6 PCE configuration";

      list ipv6-state-sync {
        key "address";
        description "Standby PCE ipv6 address";
        leaf address {
          type inet:ipv6-address-no-zone;
          description "IPv6 address";
        }
      }
    }

    container pcc-addresses {
      description "Path computation client configuration";

      list pcc-address {
        key "address";
        description "Path computation client address";

        container lsp-names {
          description "MPLS label switched path";

          list lsp-name {
            key "name";
            description "MPLS label switched path";

            container rsvp-te {
              presence "Indicates a rsvp-te node is configured.";
              description "RSVP-TE configuration";

              container affinity {
                description "LSP Affinity";
                leaf include-any {
                  type xr:Hex-integer;
                  description "Include-any affinity value";
                }
                leaf include-all {
                  type xr:Hex-integer;
                  description "Include-all affinity value";
                }
                leaf exclude-any {
                  type xr:Hex-integer;
                  description "Exclude-any affinity value";
                }
              }

              container priority {
                presence "Indicates a priority node is configured.";
                description "Tunnel Setup and Hold Priorities";
                leaf setup-priority {
                  type uint32 {
                    range "0..7";
                  }
                  mandatory true;
                  description "Setup Priority";
                }
                leaf hold-priority {
                  type uint32 {
                    range "0..7";
                  }
                  mandatory true;
                  description "Hold Priority";
                }
              }
              leaf fast-protect {
                type empty;
                description "Enable fast protection";
              }
              leaf bandwidth {
                type uint32;
                units "kbit/s";
                mandatory true;
                description "Bandwidth configuration";
              }
              uses ENABLE;
            }
            leaf undelegate {
              type empty;
              description "Undelegate LSP";
            }
            leaf explicit-path-name {
              type string;
              mandatory true;
              description "Explicit-path name";
            }
            leaf name {
              type xr:Cisco-ios-xr-string;
              description "LSP name";
            }
            uses ENABLE;
          }
        }
        leaf address {
          type inet:ipv4-address-no-zone;
          description "IPv4 address";
        }
        uses ENABLE;
      }
    }

    container logging {
      description "PCE logging configuration";
      leaf no-path {
        type empty;
        description "Logging NO-PATH configuration";
      }
      leaf pcerr {
        type empty;
        description "Logging of received PCErr messages";
      }
      leaf fallback {
        type empty;
        description "Logging fallback configuration";
      }
    }

    container backoff {
      presence "Indicates a backoff node is configured.";
      description "PCE backoff configuration";
      leaf ratio {
        type uint32 {
          range "0..255";
        }
        default "2";
        description "Backoff common ratio configuration";
      }
      leaf threshold {
        type uint32 {
          range "0..3600";
        }
        default "0";
        description "Backoff threshold configuration";
      }
      leaf difference {
        type uint32 {
          range "0..255";
        }
        default "2";
        description "Backoff common difference configuration";
      }
    }

    container rest {
      description "REST configuration";

      container rest-users {
        description "REST authorized users configuration";

        list rest-user {
          key "name";
          description "REST authorized user";
          leaf rest-user-password {
            type xr:Proprietary-password;
            description "REST user password configuration";
          }
          leaf name {
            type xr:Cisco-ios-xr-string;
            description "User name";
          }
          uses ENABLE;
        }
      }
      leaf rest-authentication {
        type Pcerest-authentication;
        description "REST authentication type";
      }
      uses ENABLE;
    }

    container state-syncs {
      description "Standby IPv4 PCE configuration";

      list state-sync {
        key "address";
        description "Standby PCE ipv4 address";
        leaf address {
          type inet:ipv4-address-no-zone;
          description "IPv4 address";
        }
      }
    }

    container segment-routing {
      description "PCE segment-routing configuration";

      container traffic-engineering {
        description "Traffic Engineering configuration data";

        container affinity-bits {
          description "Affinity Bit-map";

          list affinity-bit {
            key "color-name";
            description "Affinity Bit";
            leaf color-name {
              type xr:Cisco-ios-xr-string {
                length "1..32";
              }
              description "Color Name";
            }
            leaf bit {
              type uint32 {
                range "0..31";
              }
              mandatory true;
              description "The bit";
            }
          }
        }

        container peers {
          description "Peer configuration";

          list peer {
            key "peer-addr";
            description "Peer configuration";

            container policies {
              description "Policy configuration";

              list policy {
                key "policy-name";
                description "Policy configuration";

                container binding-sid {
                  description "Binding Segment ID";
                  leaf binding-sid-type {
                    type Pce-binding-sid;
                    description "Binding SID type";
                  }
                  leaf mpls-label {
                    when "../binding-sid-type ="+
                      " 'mpls-label-specified'" {
                        description
                          "../BindingSIDType = MPLSLabelSpecified";
                    }
                    type uint32 {
                      range "16..1048575";
                    }
                    description "MPLS Label";
                  }
                }

                container color-endpoint {
                  description "Color and Endpoint";
                  leaf color {
                    type uint32 {
                      range "1..4294967295";
                    }
                    description "Color";
                  }
                  leaf end-point-type {
                    type Pce-end-point;
                    description "End point type";
                  }
                  leaf end-point-address {
                    type inet:ip-address-no-zone;
                    description "End point address";
                  }
                }

                container candidate-paths {
                  description
                    "Policy candidate-paths configuration";

                  container affinity-rules {
                    description "Affinity rule table";

                    list affinity-rule {
                      key "rule aff-value";
                      description "Affinity rule";
                      leaf rule {
                        type uint32 {
                          range "0..2";
                        }
                        description "affinity rule";
                      }
                      leaf aff-value {
                        type xr:Cisco-ios-xr-string {
                          length "1..32";
                        }
                        description "affinity value";
                      }
                    }
                  }

                  container preferences {
                    description
                      "Policy path-option preference table";

                    list preference {
                      key "path-index";
                      description
                        "Policy path-option preference entry";

                      container path-infos {
                        description
                          "Policy path-option preference
                          configuration";

                        list path-info {
                          key "type hop-type segment-list-name";
                          description "Policy configuration";

                          container metric {
                            presence "Indicates a metric node is"+
                              " configured.";
                            description
                              "Metric configuration, valid only for
                              dynamic path-options";
                            leaf metric-type {
                              type Pce-metric;
                              mandatory true;
                              description "Metric type";
                            }
                          }
                          leaf enable {
                            type empty;
                            description "True only";
                          }
                          leaf type {
                            type Pce-path;
                            description "Path-option type";
                          }
                          leaf hop-type {
                            type Pce-path-hop;
                            description
                              "Type of dynamic path to be computed";
                          }
                          leaf segment-list-name {
                            type xr:Cisco-ios-xr-string {
                              length "1..128";
                            }
                            description "Segment-list name";
                          }
                        }
                      }
                      leaf enable {
                        type empty;
                        description "True only";
                      }
                      leaf path-index {
                        type uint32 {
                          range "1..65535";
                        }
                        description "Path-option preference";
                      }
                    }
                  }
                  leaf enable {
                    type empty;
                    description "True only";
                  }
                }
                leaf enable {
                  type empty;
                  description "True only";
                }
                leaf shutdown {
                  type empty;
                  description "Administratively shutdown policy";
                }
                leaf policy-name {
                  type xr:Cisco-ios-xr-string {
                    length "1..128";
                  }
                  description "Policy name";
                }
              }
            }
            leaf enable {
              type empty;
              description "True only";
            }
            leaf peer-addr {
              type inet:ip-address-no-zone;
              description "Peer address";
            }
          }
        }

        container segments {
          description "Segment-lists configuration";

          list segment {
            key "path-name";
            description "Segment-list configuration";

            container segments {
              description
                "Segments/hops configuration for given
                Segment-list";

              list segment {
                key "segment-index";
                description "Configure Segment/hop at the index";
                leaf segment-index {
                  type uint32 {
                    range "1..65535";
                  }
                  description "Segment index";
                }
                leaf segment-type {
                  type Pce-segment;
                  description "Segment/hop type";
                }
                leaf address {
                  when "../segment-type = 'ipv4-address'" {
                    description "../SegmentType = IPv4Address";
                  }
                  type inet:ipv4-address-no-zone;
                  description "IPv4 Address";
                }
                leaf mpls-label {
                  when "../segment-type = 'mpls-label'" {
                    description "../SegmentType = MPLSLabel";
                  }
                  type uint32 {
                    range "0..1048575";
                  }
                  description "MPLS Label";
                }
              }
            }
            leaf path-name {
              type xr:Cisco-ios-xr-string {
                length "1..128";
              }
              description "Segment-list name";
            }
          }
        }
        leaf enable {
          type empty;
          description "True only";
        }
      }
      leaf te-latency {
        type empty;
        description "Use te-latency algorithm configuration";
      }
      leaf strict-sid-only {
        type empty;
        description "Use strict-sid-only configuration";
      }
    }

    container timers {
      presence "Indicates a timers node is configured.";
      description "PCE Timers configuration";
      leaf reoptimization-timer {
        type uint32 {
          range "600..86400";
        }
        units "second";
        default "1800";
        description "Topology reoptimization timer configuration";
      }
      leaf keepalive {
        type uint32 {
          range "0..255";
        }
        units "second";
        default "30";
        description
          "Keepalive interval in seconds, zero to disable";
      }
      leaf minimum-peer-keepalive {
        type uint32 {
          range "0..255";
        }
        units "second";
        default "20";
        description
          "Minimum acceptable peer proposed keepalive
          interval";
      }
    }

    container netconf {
      description "NETCONF configuration";

      container netconf-ssh {
        description "NETCONF SSH configuration";
        leaf netconf-ssh-password {
          type xr:Proprietary-password;
          description "Password to use for NETCONF SSH connections";
        }
        leaf netconf-ssh-user {
          type string;
          description
            "User name to use for NETCONF SSH connections";
        }
      }
      uses ENABLE;
    }

    container disjoint-path {
      description "Disjoint path configuration";

      container groups {
        description "Association configuration";

        list group {
          key "group-id dp-type sub-id";
          description "Association Group Configuration";

          container group-lsp-records {
            description "lsp pcc records container with in group";

            list group-lsp-record {
              key "lsp-id";
              description
                "LSP first/second PCC record tuple
                containingIpAddr, LspName, DisjPath";
              leaf lsp-id {
                type uint32 {
                  range "1..2";
                }
                description "Lsp id";
              }
              leaf ip-addr {
                type inet:ipv4-address-no-zone;
                description "IP address of PCC";
              }
              leaf lsp-name {
                type string;
                description "Identifying name for LSP";
              }
              leaf disj-path {
                type uint32 {
                  range "0..1";
                }
                description "Set to 1 to follow shortest-path";
              }
            }
          }
          leaf strict {
            type empty;
            description "Disable Fallback";
          }
          leaf group-id {
            type uint32 {
              range "1..65535";
            }
            description "Group ID";
          }
          leaf dp-type {
            type Pce-disjoint-path;
            description "Disjointness type";
          }
          leaf sub-id {
            type uint32 {
              range "0..65535";
            }
            description "Sub group ID, 0 to unset";
          }
          uses ENABLE;
        }
      }
      uses ENABLE;
    }

    container explicit-paths {
      description "Explicit paths";

      list explicit-path {
        key "name";
        description "Explicit-path configuration";

        container path-hops {
          description "Path Hops";

          list path-hop {
            key "index";
            description "Explicit path hop configuration";
            leaf index {
              type uint32 {
                range "1..65535";
              }
              description "Hop Index";
            }
            leaf hop-type {
              type Pce-explicit-path-hop;
              description "Path hop type";
            }
            leaf address {
              when "../hop-type = 'address' or ../hop-type ="+
                " 'sid-node' or ../hop-type = 'sid-adjancency'" {
                  description
                    "../HopType = Address or ../HopType =
                    SIDNode or ../HopType = SIDAdjancency";
              }
              type inet:ipv4-address-no-zone;
              default "0.0.0.0";
              description "IPv4 Address";
            }
            leaf remote-address {
              when "../hop-type = 'sid-adjancency'" {
                description "../HopType = SIDAdjancency";
              }
              type inet:ipv4-address-no-zone;
              default "0.0.0.0";
              description "Remote IPv4 address";
            }
            leaf mpls-label {
              when "../hop-type = 'sid-node' or ../hop-type ="+
                " 'sid-adjancency' or ../hop-type = 'binding-sid'" {
                  description
                    "../HopType = SIDNode or ../HopType =
                    SIDAdjancency or ../HopType = BindingSID";
              }
              type uint32 {
                range "0..1048575";
              }
              default "0";
              description "MPLS Label";
            }
          }
        }
        leaf name {
          type xr:Cisco-ios-xr-string;
          description "Explicit-path name";
        }
        uses ENABLE;
      }
    }
    leaf server-address {
      type inet:ipv4-address-no-zone;
      description "IPv4 address of PCE server";
    }
    leaf ipv6-server-address {
      type inet:ipv6-address-no-zone;
      description "IPv6 address of PCE server";
    }
    leaf password {
      type xr:Proprietary-password;
      description "MD5 password";
    }
    uses ENABLE;
  }
}
