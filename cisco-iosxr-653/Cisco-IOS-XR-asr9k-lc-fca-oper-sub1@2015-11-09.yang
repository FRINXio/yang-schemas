submodule Cisco-IOS-XR-asr9k-lc-fca-oper-sub1 {

  belongs-to Cisco-IOS-XR-asr9k-lc-fca-oper {
    prefix Cisco-IOS-XR-asr9k-lc-fca-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-lc-fca package operational data.

     Copyright (c) 2013-2018 by Cisco Systems, Inc.
     All rights reserved.";

  revision "2015-11-09" {
    description
      "IOS XR 6.0 revision.";
  }

  typedef Spa-failure-reason {
    type enumeration {
      enum spa-failure-reason-unknown {
        value 1;
        description "spa failure reason unknown";
      }
      enum spa-failure-reason-spi-failure {
        value 2;
        description "spa failure reason spi failure";
      }
      enum spa-failure-reason-boot {
        value 3;
        description "spa failure reason boot";
      }
      enum spa-failure-reason-hw-failed {
        value 4;
        description "spa failure reason hw failed";
      }
      enum spa-failure-reason-sw-failed {
        value 5;
        description "spa failure reason sw failed";
      }
      enum spa-failure-reason-sw-restart {
        value 6;
        description "spa failure reason sw restart";
      }
      enum spa-failure-reason-check-fpd {
        value 7;
        description "spa failure reason check fpd";
      }
      enum spa-failure-reason-read-type {
        value 8;
        description "spa failure reason read type";
      }
    }
    description "SPA failure reasons";
  }
  typedef Spa-reset-reason {
    type enumeration {
      enum spa-reset-reason-unknown {
        value 1;
        description "spa reset reason unknown";
      }
      enum spa-reset-reason-manual {
        value 2;
        description "spa reset reason manual";
      }
      enum spa-reset-reason-fpd-upgrade {
        value 3;
        description "spa reset reason fpd upgrade";
      }
      enum spa-reset-reason-audit-fail {
        value 4;
        description "spa reset reason audit fail";
      }
      enum spa-reset-reason-failure {
        value 5;
        description "spa reset reason failure";
      }
    }
    description "SPA reset reasons";
  }
  typedef Spa-oper-state {
    type enumeration {
      enum spa-state-reset {
        value 1;
        description "spa state reset";
      }
      enum spa-state-failed {
        value 2;
        description "spa state failed";
      }
      enum spa-state-booting {
        value 3;
        description "spa state booting";
      }
      enum spa-state-ready {
        value 4;
        description "spa state ready";
      }
    }
    description "SPA operational states";
  }

  grouping SPA-BAY-STATUS-INFO {
    description "SPA bay status info";
    leaf bay-number {
      type uint16;
      description "BAY number";
    }
    leaf is-spa-inserted {
      type boolean;
      description "If SPA inserted";
    }
    leaf spa-type {
      type uint16;
      description "SPA type";
    }
    leaf is-spa-admin-up {
      type boolean;
      description "If SPA admin state is Up";
    }
    leaf spa-oper-state {
      type Spa-oper-state;
      description "SPA operational state";
    }
    leaf is-spa-power-admin-up {
      type boolean;
      description "If SPA power admin state is Up";
    }
    leaf is-spa-powered {
      type boolean;
      description "If SPA powered";
    }
    leaf is-spa-in-reset {
      type boolean;
      description "If SPA in reset";
    }
    leaf last-reset-reason {
      type Spa-reset-reason;
      description "Last reset reason";
    }
    leaf last-failure-reason {
      type Spa-failure-reason;
      description "Last Failure Reason";
    }
    leaf insertion-time {
      type uint32;
      units "second";
      description
        "Time when SPA last insertedin calendar format:
        seconds since00:00:00 UTC, January 1, 1970";
    }
    leaf last-ready-time {
      type uint32;
      units "second";
      description
        "Time when SPA last reached Ready statein
        calendar format: seconds since00:00:00 UTC,
        January 1, 1970";
    }
    leaf up-time {
      type uint32;
      units "second";
      description "Uptime in seconds";
    }
  }
}
