module Cisco-IOS-XR-ip-mobileip-cfg {

  /*** NAMESPACE / PREFIX DEFINITION ***/

  namespace "http://cisco.com/ns/yang/Cisco-IOS-XR-ip-mobileip-cfg";


  prefix "ip-mobileip-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-mobileip package configuration.

     This module contains definitions
     for the following management objects:
       mobile-ip: MobileIP configuration

     Copyright (c) 2013-2018 by Cisco Systems, Inc.
     All rights reserved.";

  revision "2015-11-09" {
    description
      "IOS XR 6.0 revision.";
  }

  revision "2015-09-02" {
    description
      "Initial version";
  }

  typedef Gre-key-type {
    type enumeration {
      enum symmetric {
        value 1;
        description
          "Symmetric GRE Key (same Uplink and Downlink
          key)";
      }
    }
    description "Gre key type";
  }
  typedef Service-type {
    type enumeration {
      enum ipv4 {
        value 1;
        description "ipv4 service type";
      }
      enum ipv6 {
        value 2;
        description "ipv6 service type";
      }
      enum dual {
        value 3;
        description "dual service type";
      }
    }
    description "Service type";
  }
  typedef Lma-service {
    type enumeration {
      enum service-mll {
        value 1;
        description "Wireless Private Routing service";
      }
    }
    description "Lma service";
  }
  typedef Redist-type {
    type enumeration {
      enum home-address {
        value 1;
        description "Redistribute HoA/HNP routes";
      }
    }
    description "Redist type";
  }
  typedef Redist-sub-type {
    type enumeration {
      enum host-prefix {
        value 1;
        description "Redistribute HoA/HNP host prefix routes";
      }
      enum disable {
        value 2;
        description
          "Disable redistribution of HoA/HNP host and pool
          refix routes";
      }
    }
    description "Redist sub type";
  }
  typedef Lma-role {
    type enumeration {
      enum 3gma {
        value 0;
        description "3GMA mode";
      }
    }
    description "Lma role";
  }
  typedef Lma-rat {
    type enumeration {
      enum virtual {
        value 0;
        description "VIRTUAL rat";
      }
      enum ppp {
        value 1;
        description "PPP rat";
      }
      enum ethernet {
        value 2;
        description "ETHERNET rat";
      }
      enum wlan {
        value 3;
        description "WLAN rat";
      }
      enum wi-max {
        value 4;
        description "WIMAX rat";
      }
      enum 3gppgeran {
        value 5;
        description "3GPP_GERAN rat";
      }
      enum 3gpputran {
        value 6;
        description "3GPP_UTRAN rat";
      }
      enum 3gppeutran {
        value 7;
        description "3GPP_E_UTRAN rat";
      }
      enum 3gpp2ehrpd {
        value 8;
        description "3GPP2_EHRPD rat";
      }
      enum 3gpp2hrpd {
        value 9;
        description "3GPP2_HRPD rat";
      }
      enum 3gpp21rtt {
        value 10;
        description "3GPP2_1RTT rat";
      }
      enum 3gpp2umb {
        value 11;
        description "3GPP2_UMB rat";
      }
    }
    description "Lma rat";
  }
  typedef Encap-opt {
    type enumeration {
      enum greipv4 {
        value 4;
        description "GRE IPv4 tunnel encap";
      }
      enum greipv6 {
        value 5;
        description "GRE IPv6 tunnel encap";
      }
      enum mgreipv4 {
        value 7;
        description "mGRE IPv4 tunnel encap";
      }
      enum mgreipv6 {
        value 8;
        description "mGRE IPv6 tunnel encap";
      }
    }
    description "Encap opt";
  }

  container mobile-ip {
    description "MobileIP configuration";

    container domains {
      description "Table of Domain";

      list domain {
        key "domain-name";
        description "PMIPv6 domain configuration";

        container mags {
          description "Table of MAG";

          list mag {
            key "mag-name";
            description "MAG within domain";
            leaf mag-name {
              type xr:Cisco-ios-xr-string {
                length "1..125";
              }
              description "MAG Identifier";
            }
          }
        }

        container nais {
          description "Table of NAI";

          list nai {
            key "nai-name";
            description "Network access identifier or Realm";
            leaf lma {
              type string {
                length "1..125";
              }
              description "LMA for this MN";
            }
            leaf apn {
              type string {
                length "1..125";
              }
              description "Access point network for this MN";
            }
            leaf customer {
              type xr:Cisco-ios-xr-string {
                length "1..125";
              }
              description "Customer name for this MN";
            }
            leaf service {
              type Service-type;
              description "Service type for this MN";
            }
            leaf network {
              type string {
                length "1..125";
              }
              description "Network name (Address pool) for this MN";
            }
            leaf nai-name {
              type string {
                length "1..125";
              }
              description "MN Identifier";
            }
          }
        }

        container authenticate-option {
          description
            "Authentication option between PMIPV6 entities";
          leaf spi {
            type xr:Hex-integer;
            description "SPI in hex value";
          }
          leaf key {
            type string {
              length "1..125";
            }
            description "ASCII string";
          }
        }

        container lmas {
          description "Table of LMA";

          list lma {
            key "lma-name";
            description "LMA within domain";
            leaf lma-name {
              type xr:Cisco-ios-xr-string {
                length "1..125";
              }
              description "LMA Identifier";
            }
          }
        }
        leaf enable {
          type empty;
          description
            "Enable PMIPv6 domain configuration. Deletion
            of this object also causes deletion of all
            associated objects under Domain.";
        }
        leaf domain-name {
          type xr:Cisco-ios-xr-string {
            length "1..125";
          }
          description "Domain Name";
        }
      }
    }

    container lmas {
      description "Table of LMA";

      list lma {
        key "lma-name domain-name";
        description "PMIPv6 LMA configuration";

        container binding-revocation-attributes {
          description "LMA Binding Revocation Attributes";

          container delay {
            description
              "Time to wait before Retransmitting BRI
              Message";
            leaf br-min {
              type uint32 {
                range "500..65535";
              }
              description "Specify in millisec";
            }
            leaf br-max {
              type uint32 {
                range "500..65535";
              }
              description "Specify in millisec";
            }
          }
          leaf retry {
            type uint32 {
              range "1..10";
            }
            description
              "Number of Retransmissons Allowed for BRI
              Message";
          }
        }

        container rat-attributes {
          description
            "Radio access technology type config  this LMA";
          leaf lma-rat {
            type Lma-rat;
            description "LMA rat type";
          }
          leaf priority-value {
            type uint32 {
              range "1..255";
            }
            description "Specify the priority value";
          }
        }

        container heart-beat-attributes {
          description "heartbeat config for this LMA";
          leaf interval {
            type uint32 {
              range "10..3600";
            }
            description "Specify the interval value in second";
          }
          leaf retries {
            type uint32 {
              range "1..10";
            }
            description "Specify the retry value";
          }
          leaf timeout {
            type uint32 {
              range "1..3600";
            }
            description "Specify the timeout value";
          }
        }

        container lmaipv6-addresses {
          description "Table of LMAIPv6Address";

          list lmaipv6-address {
            key "address";
            description "Configure IPv6 address for this LMA";
            leaf address {
              type inet:ipv6-address-no-zone;
              description "LMA IPv6 address";
            }
          }
        }

        container hnp {
          description "LMA HNP options";
          leaf maximum {
            type uint32 {
              range "1..3";
            }
            description "maximum HNPs allowed per MN interface";
          }
        }

        container redistribute {
          description "Redistribute routes";
          leaf redist-type {
            type Redist-type;
            description "Redistribute type";
          }
          leaf redist-sub-type {
            type Redist-sub-type;
            description "Redistribute sub-type";
          }
        }

        container aaa {
          description "AAA configuration for this LMA";

          container accounting {
            description "AAA accounting for this LMA";
            leaf enable {
              type empty;
              description "Set constant integer";
            }
            leaf interim-interval {
              type uint32 {
                range "1..86400";
              }
              units "minute";
              description "Interim acounting interval (in minutes)";
            }
          }
        }

        container dscp {
          description "DSCP for packets originating from this LMA";
          leaf value {
            type uint32 {
              range "1..63";
            }
            description "Specify the DSCP value";
          }
          leaf force {
            type empty;
            description "Set constant integer";
          }
        }

        container lmaipv4-addresses {
          description "Table of LMAIPv4Address";

          list lmaipv4-address {
            key "address";
            description "Configure IPv4 address for this LMA";
            leaf address {
              type inet:ipv4-address-no-zone;
              description "LMA IPv4 address";
            }
          }
        }

        container roles {
          description "Table of Role";

          list role {
            key "lma-role";
            description "Role of this LMA";
            leaf lma-role {
              type Lma-role;
              description "LMA role mode";
            }
          }
        }

        container binding-attributes {
          description "LMA binding attributes";
          leaf refresh-time {
            type uint32 {
              range "4..65000";
            }
            units "second";
            description "Specify in seconds, (multiples of 4)";
          }
          leaf delete-wait-interval {
            type uint32 {
              range "100..65535";
            }
            description "bce delete wait time interval";
          }
          leaf create-wait-interval {
            type uint32 {
              range "100..65535";
            }
            description "bce create wait time interval";
          }
          leaf max-life-time {
            type uint32 {
              range "10..65535";
            }
            units "second";
            description "Maximum bce lifetime permitted";
          }
          leaf maximum {
            type uint32 {
              range "1..128000";
            }
            description "Specify max. number of bindings";
          }
        }

        container mags {
          description "Table of MAG";

          list mag {
            key "mag-name domain-name";
            description "MAG within LMA";

            container authenticate-option {
              description
                "Authentication option between PMIPV6
                entities";
              leaf spi {
                type xr:Hex-integer;
                description "SPI in hex value";
              }
              leaf key {
                type string {
                  length "1..125";
                }
                description "ASCII string";
              }
            }

            container dscp {
              description
                "DSCP for packets originating from this MAG";
              leaf value {
                type uint32 {
                  range "1..63";
                }
                description "Specify the DSCP value";
              }
              leaf force {
                type empty;
                description "Set constant integer";
              }
            }
            leaf encap-option {
              type Encap-opt;
              description
                "Encapsulation option between PMIPV6 entities";
            }
            leaf ipv4-address {
              type inet:ipv4-address-no-zone;
              description "Configure IPv4 address for this MAG";
            }
            leaf ipv6-address {
              type inet:ipv6-address-no-zone;
              description "Configure IPv6 address for this MAG";
            }
            leaf tunnel {
              type xr:Interface-name;
              description "static tunnel for this peer MAG";
            }
            leaf mag-name {
              type string {
                length "1..125";
              }
              description "MAG identifier";
            }
            leaf domain-name {
              type string {
                length "1..125";
              }
              description "Domain name";
            }
          }
        }

        container tunnel-attributes {
          description "tunnel attributes";
          leaf mtu {
            type uint32 {
              range "68..17916";
            }
            description "maximum transmission unit for tunnel";
          }
          leaf acl {
            type string {
              length "1..125";
            }
            description "access list to apply for tunnel";
          }
        }

        container services {
          description "Table of Service";

          list service {
            key "lma-service";
            description "Service of this LMA";

            container customers {
              description "Table of Customer";

              list customer {
                key "customer-name vrf-name";
                description
                  "customer configuration on this mobile local
                  loop service";

                container authenticate-option {
                  description
                    "Authentication option between PMIPV6
                    entities";
                  leaf spi {
                    type xr:Hex-integer;
                    description "SPI in hex value";
                  }
                  leaf key {
                    type string {
                      length "1..125";
                    }
                    description "ASCII string";
                  }
                }

                container heart-beat-attributes {
                  description "heartbeat config for this Customer";
                  leaf interval {
                    type uint32 {
                      range "10..3600";
                    }
                    description
                      "Specify the interval value in second";
                  }
                  leaf retries {
                    type uint32 {
                      range "1..10";
                    }
                    description "Specify the retry value";
                  }
                  leaf timeout {
                    type uint32 {
                      range "1..3600";
                    }
                    description "Specify the timeout value";
                  }
                }

                container transports {
                  description "Table of Transport";

                  list transport {
                    key "vrf-name";
                    description "Customer transport attributes";
                    leaf ipv4-address {
                      type inet:ipv4-address-no-zone;
                      description
                        "Configure IPv4 address for this LMA";
                    }
                    leaf ipv6-address {
                      type inet:ipv6-address-no-zone;
                      description
                        "Configure IPv6 address for this LMA";
                    }
                    leaf vrf-name {
                      type string {
                        length "1..125";
                      }
                      description "VRF Name";
                    }
                  }
                }

                container network-attributes {
                  description "network parameters for the customer";

                  container authorizes {
                    description "Table of Authorize";

                    list authorize {
                      key "name";
                      description
                        "not authorize the network prefixes";

                      container pool-attributes {
                        description "Pool configs for this network";

                        container mobile-node {
                          description
                            "pool configs for the mobile nodes";

                          container ipv4-pool {
                            description "None";
                            leaf start-address {
                              type inet:ipv4-address-no-zone;
                              description "Pool IPv4 start address";
                            }
                            leaf pool-prefix {
                              type uint32 {
                                range "8..30";
                              }
                              description "IPv4 Pool Prefix value";
                            }
                          }

                          container ipv6-pool {
                            description "None";
                            leaf start-address {
                              type inet:ipv6-address-no-zone;
                              description "Pool IPv6 start address";
                            }
                            leaf pool-prefix {
                              type uint32 {
                                range "8..62";
                              }
                              description "IPv6 Pool Prefix value";
                            }
                          }
                        }

                        container mobile-network {
                          description
                            "pool configs for the mobile network";

                          container mripv6-pools {
                            description "Table of MRIPV6Pool";

                            list mripv6-pool {
                              key "start-address";
                              description "ipv6 pool";
                              leaf start-address {
                                type inet:ipv6-address-no-zone;
                                description
                                  "Pool IPv6 start address";
                              }
                              leaf pool-prefix {
                                type uint32 {
                                  range "8..64";
                                }
                                description
                                  "IPv6 Pool Prefix value";
                              }
                              leaf network-prefix {
                                type uint32 {
                                  range "8..64";
                                }
                                description
                                  "IPv4 Network Prefix value";
                              }
                            }
                          }

                          container mripv4-pools {
                            description "Table of MRIPV4Pool";

                            list mripv4-pool {
                              key "start-address";
                              description "ipv4 pool";
                              leaf start-address {
                                type inet:ipv4-address-no-zone;
                                description
                                  "Pool IPv4 start address";
                              }
                              leaf pool-prefix {
                                type uint32 {
                                  range "8..30";
                                }
                                description
                                  "IPv4 Pool Prefix value";
                              }
                              leaf network-prefix {
                                type uint32 {
                                  range "8..32";
                                }
                                description
                                  "IPv4 Network Prefix value";
                              }
                            }
                          }
                        }
                      }
                      leaf name {
                        type string {
                          length "1..125";
                        }
                        description "ASCII string";
                      }
                    }
                  }
                  leaf unauthorize {
                    type empty;
                    description
                      "not authorize the network prefixes";
                  }
                }

                container gre-key {
                  description "Customer specific GRE key";
                  leaf gre-key-type {
                    type Gre-key-type;
                    description "GRE key type";
                  }
                  leaf gre-key-value {
                    type uint32 {
                      range "1..4294967295";
                    }
                    description "GRE key value";
                  }
                }

                container binding-attributes {
                  description
                    "Customer specific binding attributes";
                  leaf max-life-time {
                    type uint32 {
                      range "10..65535";
                    }
                    units "second";
                    description "Maximum bce lifetime permitted";
                  }
                }
                leaf mnp-customer {
                  type uint32 {
                    range "1..4000000";
                  }
                  description "mnp limit config for customer";
                }
                leaf mnp-ipv4-lmn {
                  type uint32 {
                    range "1..32";
                  }
                  description
                    "mnp limit config for customer specific
                    logical mn";
                }
                leaf mnp-ipv6-lmn {
                  type uint32 {
                    range "1..32";
                  }
                  description
                    "mnp limit config for customer specific
                    logical mn";
                }
                leaf mnp-lmn {
                  type uint32 {
                    range "1..32";
                  }
                  description
                    "mnp limit config for customer specific
                    logical mn";
                }
                leaf mnp-ipv4-customer {
                  type uint32 {
                    range "1..4000000";
                  }
                  description "mnp limit config for customer";
                }
                leaf mnp-ipv6-customer {
                  type uint32 {
                    range "1..4000000";
                  }
                  description "mnp limit config for customer";
                }
                leaf mobile-route-ad {
                  type uint32 {
                    range "1..254";
                  }
                  description "Specify the Admin Distance value";
                }
                leaf bandwidth-aggregate {
                  type uint32 {
                    range "1..4294967295";
                  }
                  units "kbit/s";
                  description
                    "Aggregate bandwidth across all logical MNs";
                }
                leaf customer-name {
                  type string {
                    length "1..32";
                  }
                  description "Customer name";
                }
                leaf vrf-name {
                  type string {
                    length "1..32";
                  }
                  description "VRF name";
                }
              }
            }
            leaf mnp-customer {
              type uint32 {
                range "1..4000000";
              }
              description "mnp limit config for all customer's";
            }
            leaf mnp-ipv4-lmn {
              type uint32 {
                range "1..32";
              }
              description "mnp limit config for all logical mn's";
            }
            leaf mnp-ipv6-lmn {
              type uint32 {
                range "1..32";
              }
              description "mnp limit config for all logical mn's";
            }
            leaf mnp-lmn {
              type uint32 {
                range "1..32";
              }
              description "mnp limit config for all logical mn's";
            }
            leaf ignore-home-address {
              type empty;
              description "Ignore HoA/HNP option";
            }
            leaf mnp-ipv4-customer {
              type uint32 {
                range "1..4000000";
              }
              description "mnp limit config for all customer's";
            }
            leaf mnp-ipv6-customer {
              type uint32 {
                range "1..4000000";
              }
              description "mnp limit config for all customer's";
            }
            leaf lma-service {
              type Lma-service;
              description "LMA service mode";
            }
          }
        }

        container networks {
          description "Table of Network";

          list network {
            key "lma-network";
            description "network for this LMA";

            container pool-attributes {
              description "Pool configs for this network";

              container mobile-node {
                description "pool configs for the mobile nodes";

                container ipv4-pool {
                  description "None";
                  leaf start-address {
                    type inet:ipv4-address-no-zone;
                    description "Pool IPv4 start address";
                  }
                  leaf pool-prefix {
                    type uint32 {
                      range "8..30";
                    }
                    description "IPv4 Pool Prefix value";
                  }
                }

                container ipv6-pool {
                  description "None";
                  leaf start-address {
                    type inet:ipv6-address-no-zone;
                    description "Pool IPv6 start address";
                  }
                  leaf pool-prefix {
                    type uint32 {
                      range "8..62";
                    }
                    description "IPv6 Pool Prefix value";
                  }
                }
              }

              container mobile-network {
                description "pool configs for the mobile network";

                container mripv6-pools {
                  description "Table of MRIPV6Pool";

                  list mripv6-pool {
                    key "start-address";
                    description "ipv6 pool";
                    leaf start-address {
                      type inet:ipv6-address-no-zone;
                      description "Pool IPv6 start address";
                    }
                    leaf pool-prefix {
                      type uint32 {
                        range "8..64";
                      }
                      description "IPv6 Pool Prefix value";
                    }
                    leaf network-prefix {
                      type uint32 {
                        range "8..64";
                      }
                      description "IPv4 Network Prefix value";
                    }
                  }
                }

                container mripv4-pools {
                  description "Table of MRIPV4Pool";

                  list mripv4-pool {
                    key "start-address";
                    description "ipv4 pool";
                    leaf start-address {
                      type inet:ipv4-address-no-zone;
                      description "Pool IPv4 start address";
                    }
                    leaf pool-prefix {
                      type uint32 {
                        range "8..30";
                      }
                      description "IPv4 Pool Prefix value";
                    }
                    leaf network-prefix {
                      type uint32 {
                        range "8..32";
                      }
                      description "IPv4 Network Prefix value";
                    }
                  }
                }
              }
            }
            leaf lma-network {
              type string {
                length "1..125";
              }
              description "Network name";
            }
          }
        }

        container replay-protection {
          description "Replay Protection Method";
          leaf timestamp-window {
            type uint32 {
              range "1..255";
            }
            units "second";
            description "Specify timestamp window value in seconds";
          }
        }
        leaf generate {
          type empty;
          description "generate gre key for LMA bindings";
        }
        leaf mobile-route-ad {
          type uint32 {
            range "1..254";
          }
          description "Specify the Admin Distance value";
        }
        leaf ani {
          type empty;
          description "enable ani option processing in LMA";
        }
        leaf multipath {
          type empty;
          description "enable multipath support for LMA";
        }
        leaf dynamic {
          type empty;
          description "enable dynamic mag learning for LMA";
        }
        leaf enforce {
          type empty;
          description "enforce heartbeat values to MAG";
        }
        leaf default-profile {
          type string {
            length "1..125";
          }
          description "Default MN profile for LMA";
        }
        leaf interface {
          type xr:Interface-name;
          description "CN facing interface name";
        }
        leaf mobile-map {
          type string {
            length "1..125";
          }
          description "Mobile Map for this LMA";
        }
        leaf pgw-subs-cont {
          type empty;
          description "Feature related to interface with PGW";
        }
        leaf lma-name {
          type string {
            length "1..125";
          }
          description "LMA name";
        }
        leaf domain-name {
          type string {
            length "1..125";
          }
          description "Domain name";
        }
      }
    }
  }
}
