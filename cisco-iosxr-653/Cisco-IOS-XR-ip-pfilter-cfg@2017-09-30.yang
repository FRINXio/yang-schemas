module Cisco-IOS-XR-ip-pfilter-cfg {

  /*** NAMESPACE / PREFIX DEFINITION ***/

  namespace "http://cisco.com/ns/yang/Cisco-IOS-XR-ip-pfilter-cfg";


  prefix "ip-pfilter-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-pfilter package configuration.

     This YANG module augments the
       Cisco-IOS-XR-ifmgr-cfg
     module with configuration data.

     Copyright (c) 2013-2018 by Cisco Systems, Inc.
     All rights reserved.";

  revision "2017-09-30" {
    description
      "Ensure propagation of MDA mandatory state to YANG model.";
  }

  revision "2017-05-01" {
    description
      "Fixing backward compatibility error in module.";
  }

  revision "2015-11-09" {
    description
      "IOS XR 6.0 revision.";
  }


  augment "/a1:interface-configurations/a1:interface-configuration" {

    container ipv6-packet-filter {
      description
        "IPv6 Packet Filtering configuration for the
        interface";

      container inbound {
        description
          "IPv6 Packet filter to be applied to inbound
          packets";
        leaf common-acl-name {
          type xr:Cisco-ios-xr-string {
            length "1..64";
          }
          description
            "Reserved for backward compatibility. IPv6
            Packet Filter Name to be applied to Inbound
            packets, ACL providing HW optimization when
            applied on multiple interfaces. NOTE: This
            parameter is mandatory if 'Name' is not
            specified.";
        }
        leaf name {
          type xr:Cisco-ios-xr-string {
            length "1..64";
          }
          description
            "Reserved for backward compatibility. IPv6
            Packet Filter Name to be applied to Inbound 
            NOTE: This parameter is mandatory if
            'CommonACLName' is not specified.";
        }
        leaf interface-statistics {
          type empty;
          description
            "True if packets hitting the ACL should be
            counted in hardware per interface.The default
            is not to count them. NOTE:
            InterfaceStatistics is allowed only if Name is
            specified.";
        }
        leaf compression-level {
          type uint32 {
            range "0..3";
          }
          description
            "The level of compression applied to the ACL on
            this interface. The range is 0 to 3 with
            default being no compression (0).";
        }
        leaf-list acl-name-array {
          type xr:Cisco-ios-xr-string {
            length "1..64";
          }
          max-elements "5";
          description
            "Array of IPv6 Packet Filter Names to be
            applied to Inbound packets";
        }
        leaf-list is-common-array {
          type boolean;
          max-elements "5";
          description
            "Array of CommonACL flags for each ACL. TRUE
            indicates HW optimization on multiple
            interfaces is provided";
        }
      }

      container outbound {
        description
          "IPv6 Packet filter to be applied to outbound
          packets";
        leaf do-not-use {
          type string {
            length "1..64";
          }
          description "Reserved.  Error if specified.";
        }
        leaf name {
          type xr:Cisco-ios-xr-string {
            length "1..64";
          }
          description
            "Reserved for backward compatibility. IPv6
            Packet Filter Name to be applied to Outbound 
            packets.";
        }
        leaf interface-statistics {
          type empty;
          description
            "True if packets hitting the ACL should be
            counted in hardware per interface.The default
            is not to count them.";
        }
        leaf compression-level {
          type uint32 {
            range "0..3";
          }
          description
            "The level of compression applied to the ACL on
            this interface. The range is 0 to 3 with
            default being no compression (0).";
        }
        leaf-list acl-name-array {
          type xr:Cisco-ios-xr-string {
            length "1..64";
          }
          max-elements "5";
          description
            "Array of IPv6 Packet Filter Names to be
            applied to Inbound packets";
        }
        leaf-list is-common-array {
          type boolean;
          max-elements "5";
          description
            "Array of CommonACL flags for each ACL. TRUE
            indicates HW optimization on multiple
            interfaces is provided";
        }
      }
    }
    description
      "This augment extends the configuration data of
      'Cisco-IOS-XR-ifmgr-cfg'";
  }

  augment "/a1:interface-configurations/a1:interface-configuration" {

    container es-packet-filter {
      description
        "ES Packet Filtering configuration for the
        interface";
      leaf outbound {
        type xr:Cisco-ios-xr-string {
          length "1..64";
        }
        description
          "Name of filter to be applied to outbound
          packets";
      }
      leaf inbound {
        type xr:Cisco-ios-xr-string {
          length "1..64";
        }
        description
          "Name of filter to be applied to inbound packets";
      }
    }
    description
      "This augment extends the configuration data of
      'Cisco-IOS-XR-ifmgr-cfg'";
  }

  augment "/a1:interface-configurations/a1:interface-configuration" {

    container ipv4-packet-filter {
      description
        "IPv4 Packet Filtering configuration for the
        interface";

      container outbound {
        description
          "IPv4 Packet filter to be applied to outbound
          packets";
        leaf do-not-use {
          type string {
            length "1..64";
          }
          description "Reserved.  Error if specified.";
        }
        leaf name {
          type xr:Cisco-ios-xr-string {
            length "1..64";
          }
          description
            "Reserved for backward compatibility. IPv4
            Packet Filter Name to be applied to Outbound
            packets NOTE: This parameter is mandatory if
            'CommonACLName' is not specified.";
        }
        leaf hardware-count {
          type empty;
          description
            "True if packets hitting the ACL should be
            counted in the hardware.  The default is not
            to count them.";
        }
        leaf interface-statistics {
          type empty;
          description
            "True if packets hitting the ACL should be
            counted in hardware per interface.The default
            is not to count them.";
        }
        leaf compression-level {
          type uint32 {
            range "0..3";
          }
          description
            "The level of compression applied to the ACL on
            this interface. The range is 0 to 3 with
            default being no compression (0).";
        }
        leaf-list acl-name-array {
          type xr:Cisco-ios-xr-string {
            length "1..64";
          }
          max-elements "5";
          description
            "Array of IPv4 Packet Filter Names to be
            applied to Outbound packets";
        }
        leaf-list is-common-array {
          type boolean;
          max-elements "5";
          description
            "Array of CommonACL flags for each ACL. TRUE
            indicates HW optimization on multiple
            interfaces is provided";
        }
      }

      container inbound {
        description
          "IPv4 Packet filter to be applied to inbound
          packets";
        leaf common-acl-name {
          type xr:Cisco-ios-xr-string {
            length "1..64";
          }
          description
            "Reserved for backward compatibility. IPv4
            Packet Filter Name to be applied to Inbound
            packets, ACL providing HW optimization when
            applied on multiple interfaces. NOTE: This
            parameter is mandatory if 'Name' is not
            specified.";
        }
        leaf name {
          type xr:Cisco-ios-xr-string {
            length "1..64";
          }
          description
            "Reserved for backward compatibility. IPv4
            Packet Filter Name to be applied to Inbound
            packets NOTE: This parameter is mandatory if
            'CommonACLName' is not specified.";
        }
        leaf hardware-count {
          type empty;
          description
            "True if packets hitting the ACL should be
            counted in the hardware.  The default is not
            to count them. NOTE: HardwareCount is allowed
            only if Name is specified.";
        }
        leaf interface-statistics {
          type empty;
          description
            "True if packets hitting the ACL should be
            counted in hardware per interface.The default
            is not to count them. NOTE:
            InterfaceStatistics is allowed only if Name is
            specified.";
        }
        leaf compression-level {
          type uint32 {
            range "0..3";
          }
          description
            "The level of compression applied to the ACL on
            this interface. The range is 0 to 3 with
            default being no compression (0).";
        }
        leaf-list acl-name-array {
          type xr:Cisco-ios-xr-string {
            length "1..64";
          }
          max-elements "5";
          description
            "Array of IPv4 Packet Filter Names to be
            applied to Inbound packets";
        }
        leaf-list is-common-array {
          type boolean;
          max-elements "5";
          description
            "Array of CommonACL flags for each ACL. TRUE
            indicates HW optimization on multiple
            interfaces is provided";
        }
      }
    }
    description
      "This augment extends the configuration data of
      'Cisco-IOS-XR-ifmgr-cfg'";
  }
}
