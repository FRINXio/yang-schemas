module nokia-types-security {

    yang-version "1.1";

    namespace "urn:nokia.com:sros:ns:yang:sr:types-security";

    prefix "types-security";

    import nokia-sros-yang-extensions     { prefix "sros-ext"; }
    import nokia-types-sros               { prefix "types-sros"; }


    sros-ext:sros-major-release "rel20";

    organization "Nokia";

    contact
        "Nokia SR OS Support
         Web: <http://www.nokia.com>";

    description
        "Common security data types used in the SR OS management system.

         Copyright 2016 Nokia. All rights reserved. Reproduction of this document
         is authorized on the condition that the foregoing copyright notice is included.

         This nokia-types-security YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-04-05";

    typedef cpm-packet-rate-limit {
        type union {
            type int32 {
                range "1..65535";
            }
            type enumeration {
                enum "max"                          { value -1; }
            }
        }
        description
            "A packet rate limit expressed in packets per second.
             It can be applied to packet streams towards the CPM CPU.";
    }

    typedef cpm-policy-packet-rate-limit {
        type union {
            type int32 {
                range "1..65534";
            }
            type enumeration {
                enum "max"                          { value -1; }
            }
        }
        description
            "A packet rate limit expressed in packets per second.
             It can be applied to packet streams towards the CPM CPU.";
    }

    typedef key-fingerprint {
        type union {
            type enumeration {
                enum "disabled"                     { value -1; }
            }
            type string {
                length "47";
            }
        }
        default "disabled";
    }

    typedef burst-size {
        type int32 {
            range "0..131072";
        }
    }

    typedef pki-file-name {
        type types-sros:display-string {
            length "1..95";
            pattern ".*\\S.*" {
                error-message "File name must not be all spaces";
            }
            pattern "[^\\\\:/]*" {
                error-message "File name must not contain a path";
            }
        }
        description "Name of file in the system-pki directory.";
    }

    typedef password-authentication-order {
        type enumeration {
            enum "local"                        { value 1; }
            enum "radius"                       { value 2; }
            enum "tacplus"                      { value 3; }
            enum "ldap"                         { value 4; }
        }
        description
            "password-authentication-order is an integer value that specifies the
             user authentication method.";
    }

    typedef keychain-algo {
        type enumeration {
            enum "aes-128-cmac-96"              { value 1; }
            enum "hmac-sha-1-96"                { value 2; }
            enum "password"                     { value 3; }
            enum "message-digest"               { value 4; }
            enum "hmac-md5"                     { value 5; }
            enum "hmac-sha-1"                   { value 6; }
            enum "hmac-sha-256"                 { value 7; }
        }
        description "The encryption algorithm used by a keychain key.";
    }

    typedef crl-update-status {
        type enumeration {
            enum "not-updating"                 { value 0; }
            enum "auto-scheduled"               { value 1; }
            enum "auto-downloading"             { value 2; }
            enum "manual-downloading"           { value 3; }
            enum "stopped"                      { value 4; }
            enum "auto-verifying"               { value 5; }
            enum "manual-verifying"             { value 6; }
        }
        description
            "Indicates the CRL update status.

             Values:
                 notUpdating       (0)
                     The system is not updating the CRL file. This happens when
                     the following conditions are met:
                         1) The system is not manually updating a CRL file, and
                         2) tmnxPkiCAProfAtCrlUpdAdminState is 'outOfService (3)'.

                 autoScheduled     (1)
                     The system is waiting for the next scheduled CRL update time
                     (tmnxPkiCAProfAtCrlUpdNxCrlUpdTm) in an automated
                     CRL update operation. This happens when the following
                     conditions are met:
                         1) tmnxPkiCAProfAtCrlUpdAdminState is 'inService (2)',
                            and
                         2) The next scheduled CRL update time is not reached.

                 autoDownloading   (2)
                     The system is downloading the CRL file in an automated CRL
                     update operation. This happens when the following conditions
                     are met:
                         1) tmnxPkiCAProfAtCrlUpdAdminState is 'inService (2)',
                            and
                         2) The current CRL is invalid, or next scheduled CRL update
                            time is reached.

                 manualDownloading (3)
                     The system is downloading the CRL file in a manual CRL update
                     operation (tmnxPkiCAProfManCrlUpdTable).

                 stopped           (4)
                     The system stopped updating the CRL. This happens when one
                     of the following conditions are met:
                         1) In the automated CRL update case, the system did not find
                            a CRL that qualifies from any of the configured URLs.
                            Meanwhile, tmnxPkiCAProfAtCrlUpdScheduleT is
                            'nextUpdateBased (1)' and the value of
                            tmnxPkiCAProfAtCrlUpdRetryIntv is zero; or
                         2) In the automated CRL update case, the system finds a CRL
                            that qualifies from one of the configured URLs, but
                            the 'nextUpdate' field is missing.
                            Meanwhile, tmnxPkiCAProfAtCrlUpdScheduleT is
                            'nextUpdateBased (1)'; or
                         3) In the manual CRL update case, the system did not find
                            a CRL that qualifies from any of the configured URLs.
                         4) The manual CRL update was aborted by configuring
                            tmnxPkiCAProfManCrlUpdAbort to 'doAction (1)'.

                     tmnxPkiCAProfCrlCurUpdStatus will never be 'stopped (4)' when
                     tmnxPkiCAProfAtCrlUpdScheduleT is 'periodic (2)'. In this
                     case, after attempting all URLs, the system will try to
                     update the CRL file again in
                     tmnxPkiCAProfAtCrlUpdPrdcUpdIntv seconds.

                 autoVerifying     (5)
                     The system is verifying the downloaded CRL file in an
                     automated CRL update operation.

                 manualVerifying   (6)
                     The system is verifying the downloaded CRL file in a
                     manual CRL update operation.";
    }

}
