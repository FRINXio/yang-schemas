module nokia-types-bfd {

    yang-version "1.1";

    namespace "urn:nokia.com:sros:ns:yang:sr:types-bfd";

    prefix "types-bfd";

    import nokia-sros-yang-extensions     { prefix "sros-ext"; }


    sros-ext:sros-major-release "rel20";

    organization "Nokia";

    contact
        "Nokia SR OS Support
         Web: <http://www.nokia.com>";

    description
        "Common bfd data types used in the SR OS management system.

         Copyright 2016 Nokia. All rights reserved. Reproduction of this document
         is authorized on the condition that the foregoing copyright notice is included.

         This nokia-types-bfd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-12-11";

    typedef protocols {
        type bits {
            bit ospfv2                         { position 0; }
            bit pim                            { position 1; }
            bit isis                           { position 2; }
            bit static-route                   { position 3; }
            bit mc-ring                        { position 4; }
            bit rsvp                           { position 5; }
            bit bgp                            { position 6; }
            bit vrrp                           { position 7; }
            bit srrp                           { position 8; }
            bit mcep                           { position 9; }
            bit ldp                            { position 10; }
            bit ipsec-tunnel                   { position 11; }
            bit ospfv3                         { position 12; }
            bit mc-ipsec                       { position 13; }
            bit mc-mobile                      { position 14; }
            bit mpls-tp                        { position 15; }
            bit lag                            { position 16; }
            bit opergrp                        { position 17; }
            bit vccv                           { position 18; }
            bit rsvp-lsp                       { position 19; }
            bit ldp-lsp                        { position 20; }
            bit bgp-lsp                        { position 21; }
            bit rip                            { position 22; }
            bit ripng                          { position 23; }
            bit mpls-np                        { position 24; }
        }
        description "The protocols that are using a BFD session.";
    }

    typedef cfg-endpoint-type {
        type enumeration {
            enum "cpm-np"                       { value 1; }
            enum "auto"                         { value 2; }
        }
        description "The configured session endpoint type.";
    }

    typedef act-endpoint-type {
        type enumeration {
            enum "iom"                          { value 1; }
            enum "cpm"                          { value 2; }
            enum "cpm-np"                       { value 3; }
        }
        description "The actual session endpoint type.";
    }

    typedef session-state {
        type enumeration {
            enum "admin-down"                   { value 0; }
            enum "down"                         { value 1; }
            enum "init"                         { value 2; }
            enum "up"                           { value 3; }
        }
        description "The state of the BFD protocol.";
    }

    typedef fec-type {
        type enumeration {
            enum "rsvp"                         { value 1; }
            enum "ldp"                          { value 2; }
            enum "bgp"                          { value 3; }
            enum "sr-te"                        { value 4; }
        }
        description "The fec type";
    }

}
