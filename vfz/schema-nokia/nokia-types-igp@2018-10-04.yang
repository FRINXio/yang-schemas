module nokia-types-igp {

    yang-version "1.1";

    namespace "urn:nokia.com:sros:ns:yang:sr:types-igp";

    prefix "types-igp";

    import nokia-sros-yang-extensions     { prefix "sros-ext"; }
    import nokia-types-sros               { prefix "types-sros"; }


    sros-ext:sros-major-release "rel20";

    organization "Nokia";

    contact
        "Nokia SR OS Support
         Web: <http://www.nokia.com>";

    description
        "Common IGP data types used in the SR OS management system.

         Copyright 2016 Nokia. All rights reserved. Reproduction of this document
         is authorized on the condition that the foregoing copyright notice is included.

         This nokia-types-igp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2018-10-04";

    typedef router-id {
        type types-sros:ipv4-address;
        description "Specifies the routerId.";
    }

    typedef system-id {
        type string {
            length "14";
            pattern "[0-9A-Fa-f]{4}(\\.[0-9A-Fa-f]{4}){2}";
        }
        default "0000.0000.0000";
        description "This type defines ISIS system id using pattern, system id looks like : 0143.0438.AeF0.";
    }

    typedef sid-type {
        type enumeration {
            enum "none"                         { value 0; }
            enum "index"                        { value 1; }
            enum "label"                        { value 2; }
        }
        description "Specifies how the value of SID shall be interpreted.";
    }

    typedef scope-type {
        type enumeration {
            enum "local"                        { value 1; }
        }
        description "Specifies if the value is locally significant or is allocated from a global database. ";
    }

    typedef tunn-next-hop-family-type {
        type enumeration {
            enum "ipv4"                         { value 0; }
            enum "ipv6"                         { value 1; }
            enum "srv4"                         { value 2; }
            enum "srv6"                         { value 3; }
        }
        description "Specifies type of tunnel next hop family";
    }

    typedef tunn-next-hop-family-type-v4-only {
        type enumeration {
            enum "ipv4"                         { value 0; }
            enum "srv4"                         { value 2; }
        }
        description "Specifies type of tunnel next hop family";
    }

    typedef adj-sid-hold-type {
        type union {
            type uint32 {
                range "1..300";
            }
            type enumeration {
                enum "none"                         { value 0; }
            }
        }
        description "Configure adjacency SID hold time.";
    }

    typedef export-tunnel-table-type {
        type enumeration {
            enum "ldp"                          { value 1; }
        }
        description "Configure tunnel table export";
    }

    typedef overload-timeout {
        type union {
            type uint32 {
                range "1..1800";
            }
            type enumeration {
                enum "forever"                      { value 0; }
            }
        }
        units "seconds";
        description "Time to stay in overload.";
    }

}
