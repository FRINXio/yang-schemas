/*
 * Copyright (c) 2021 Juniper Networks, Inc.
 * All rights reserved.
 */


// FRINX change show-l2circuit to submodule 
 submodule show-l2circuit {
  belongs-to show-route {
    prefix "jrpc";
  }

  import junos-extension {
    prefix junos;
  }

  organization
    "Juniper Networks, Inc.";

  description
    "Junos YANG module for RPC";


   rpc get-l2ckt-connection-information {
     description "Show the Layer 2 circuit connections";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf neighbor {
         description "IP address of neighbor";
         default "all";
         type string;
       }
       leaf interface {
         description "Name of interface";
         default "all";
         type string;
       }
       leaf state {
         default "up-down";
         type enumeration {
           enum "down" {
             description "Display nonoperational connections";
           }
           enum "up" {
             description "Display operational connections";
           }
           enum "up-down" {
             description "Display both operational and nonoperational connections (default)";
           }
         }
       }
       leaf level {
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and interface status (default)";
           }
           enum "summary" {
             description "Display summary output";
           }
         }
       }
     }
     // FRINX add output
     output{
     anyxml l2circuit-connection-information;

     }
   }
 }
