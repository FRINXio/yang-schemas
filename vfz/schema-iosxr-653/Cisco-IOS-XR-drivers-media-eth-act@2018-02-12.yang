module Cisco-IOS-XR-drivers-media-eth-act {

  namespace "http://cisco.com/ns/yang/Cisco-IOS-XR-drivers-media-eth-act";

  prefix "eth-drvr-act";

  import Cisco-IOS-XR-types { prefix "csc"; }

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR action package configuration.

     Copyright (c) 2018 by Cisco Systems, Inc.
     All rights reserved.";

  revision "2018-02-12" {
    description
      "IOS XR 6.5.1 revision.";
  }

  rpc clear-controller-counters {
    csc:xr-task "interface";
    csc:cli-command "clear controller <controller-name> stats";
    description
      "Clear Ethernet MAC ASIC statistics.";
    input {
      leaf controller-name {
        mandatory true;
        type csc:Interface-name;
        description "Controller name";
      }
    }
  }

}
