module Cisco-IOS-XR-ppp-ea-oper {

  /*** NAMESPACE / PREFIX DEFINITION ***/

  namespace "http://cisco.com/ns/yang/Cisco-IOS-XR-ppp-ea-oper";


  prefix "ppp-ea-oper";

  /*** LINKAGE (IMPORTS / INCLUDES) ***/

  import Cisco-IOS-XR-types { prefix "xr"; }

  include Cisco-IOS-XR-ppp-ea-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ppp-ea package operational data.

     This module contains definitions
     for the following management objects:
       pppea: PPPEA operational data

     Copyright (c) 2013-2018 by Cisco Systems, Inc.
     All rights reserved.";

  revision "2015-11-09" {
    description
      "IOS XR 6.0 revision.";
  }


  container pppea {
    config false;
    description "PPPEA operational data";

    container nodes {
      description "Per node PPPEA operational data";

      list node {
        key "node-name";
        description
          "The PPPEA operational data for a particular
          node";

        container ea-interface-names {
          description
            "Show interface related information from the
            PPP EA";

          list ea-interface-name {
            key "interface-name";
            description "Interface name";
            leaf interface-name {
              type xr:Interface-name;
              description "Interface running PPPEA";
            }
            uses PPP-EA-INTERFACE-INFO;
          }
        }
        leaf node-name {
          type xr:Node-id;
          description "The identifier for the node";
        }
      }
    }
  }
}
