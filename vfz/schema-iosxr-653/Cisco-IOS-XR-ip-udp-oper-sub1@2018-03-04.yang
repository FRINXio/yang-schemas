submodule Cisco-IOS-XR-ip-udp-oper-sub1 {

  belongs-to Cisco-IOS-XR-ip-udp-oper {
    prefix Cisco-IOS-XR-ip-udp-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-udp package operational data.

     Copyright (c) 2013-2018 by Cisco Systems, Inc.
     All rights reserved.";

  revision "2018-03-04" {
    description
      "PCB_ID argument is passed in string format.";
  }

  revision "2017-09-07" {
    description
      "Fixed type translation error.";
  }

  revision "2016-02-26" {
    description
      "Descriptions updated.";
  }

  revision "2015-11-09" {
    description
      "IOS XR 6.0 revision.";
  }

  typedef Udp-in6-addr {
    type inet:ipv6-address;
    description "Udp in6 addr";
  }
  typedef Udp-address-family {
    type enumeration {
      enum ipv4 {
        value 2;
        description "IPv4";
      }
      enum ipv6 {
        value 26;
        description "IPv6";
      }
    }
    description "Address Family Type";
  }

  grouping UDP-SH-BRIEF-BAG {
    description "UDP connection brief information";

    container local-address {
      description "Local address";
      uses UDP-ADDRESS-TYPE;
    }

    container foreign-address {
      description "Foreign address";
      uses UDP-ADDRESS-TYPE;
    }
    leaf af-name {
      type Udp-address-family;
      description "Address family";
    }
    leaf local-port {
      type uint16;
      description "Local port";
    }
    leaf foreign-port {
      type uint16;
      description "Foreign port";
    }
    leaf receive-queue {
      type uint32;
      description "Receive queue count";
    }
    leaf send-queue {
      type uint32;
      description "Send queue count";
    }
    leaf vrf-id {
      type uint32;
      description "VRF ID";
    }
  }

  grouping UDP-ADDRESS-TYPE {
    description "UDP ADDRESS TYPE";
    leaf af-name {
      type Udp-address-family;
      description "AFName";
    }
    leaf ipv4-address {
      when "../af-name = 'ipv4'" {
        description "../AFName = 'IPv4'";
      }
      type inet:ipv4-address;
      description "IPv4 Address";
    }
    leaf ipv6-address {
      when "../af-name != 'ipv4'" {
        description "../AFName != 'IPv4'";
      }
      type Udp-in6-addr;
      description "IPv6 Address";
    }
  }

  grouping UDP-SH-TABLE-BAG {
    description "UDP detail pcb information";

    container local-address {
      description "Local address";
      uses UDP-ADDRESS-TYPE;
    }

    container foreign-address {
      description "Foreign address";
      uses UDP-ADDRESS-TYPE;
    }
    leaf af-name {
      type Udp-address-family;
      description "Address family";
    }
    leaf local-process-id {
      type uint32;
      description "ID of local process";
    }
    leaf local-port {
      type uint16;
      description "Local port";
    }
    leaf foreign-port {
      type uint16;
      description "Foreign port";
    }
    leaf receive-queue {
      type uint32;
      description "Receive queue count";
    }
    leaf send-queue {
      type uint32;
      description "Send queue count";
    }
    leaf vrf-id {
      type uint32;
      description "VRF ID";
    }
  }

  grouping UDP-PCB-RECEIVE-STATS-TYPE {
    description "UDP receive statistics";
    leaf received-network-packets {
      type uint64;
      description "Packets received from network";
    }
    leaf failed-queued-application-packets {
      type uint32;
      description "Packets failed queued to application";
    }
    leaf queued-application-packets {
      type uint64;
      description "Packets queued to application";
    }
    leaf failed-queued-application-socket-packets {
      type uint32;
      description
        "Packet that couldn't be queued to application.on
        socket";
    }
    leaf queued-application-socket-packets {
      type uint64;
      description "Packets queued to application on socket";
    }
  }

  grouping UDP-PCB-SEND-STATS-TYPE {
    description "UDP send statistics";
    leaf received-application-bytes {
      type uint64;
      units "byte";
      description "Bytes received from application";
    }
    leaf received-xipc-pulses {
      type uint64;
      description "XIPC pulses received from application";
    }
    leaf sent-network-packets {
      type uint64;
      description "Packets sent to network (v4/v6 IO)";
    }
    leaf sent-net-io-packets {
      type uint64;
      description "Packets sent to network (NetIO)";
    }
    leaf failed-queued-network-packets {
      type uint32;
      description
        "Packets failed getting queued to network (v4/v6
        IO)";
    }
    leaf failed-queued-net-io-packets {
      type uint32;
      description
        "Packets failed getting queued to network (NetIO)";
    }
  }

  grouping UDP-SH-PCB-STATS-BAG {
    description "UDP statistics";

    container send {
      description "UDP send statistics";
      uses UDP-PCB-SEND-STATS-TYPE;
    }

    container receive {
      description "UDP receive statistics";
      uses UDP-PCB-RECEIVE-STATS-TYPE;
    }
    leaf vrf-id {
      type uint32;
      description "VRF ID";
    }
    leaf is-paw-socket {
      type boolean;
      description "True if paw socket";
    }
  }

  grouping UDP-SH-STATS-BAG {
    description "UDP statistics summary";
    leaf received-total-packets {
      type uint32;
      description "Total packets received";
    }
    leaf received-no-port-packets {
      type uint32;
      description "Packets received when no wild listener";
    }
    leaf received-bad-checksum-packets {
      type uint32;
      description "Packets received has bad checksum";
    }
    leaf received-too-short-packets {
      type uint32;
      description "Packets received is too short";
    }
    leaf received-drop-packets {
      type uint32;
      description "Packets dropped for other reasons";
    }
    leaf sent-total-packets {
      type uint32;
      description "Total packets sent";
    }
    leaf sent-error-packets {
      type uint32;
      description "Total send erorr packets";
    }
    leaf forward-broadcast-packets {
      type uint32;
      description "Total forwarding broadcast packets";
    }
    leaf cloned-packets {
      type uint32;
      description "Total cloned packets";
    }
    leaf failed-clone-packets {
      type uint32;
      description "Total failed cloned packets";
    }
  }
}
