submodule Cisco-IOS-XR-lpts-pre-ifib-oper-sub1 {

  belongs-to Cisco-IOS-XR-lpts-pre-ifib-oper {
    prefix Cisco-IOS-XR-lpts-pre-ifib-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lpts-pre-ifib package operational data.

     Copyright (c) 2013-2018 by Cisco Systems, Inc.
     All rights reserved.";

  revision "2017-05-01" {
    description
      "Fixing backward compatibility error in module.";
  }

  revision "2016-02-22" {
    description
      "Initial revision for pre-ifib oper yang.";
  }

  revision "2015-11-09" {
    description
      "IOS XR 6.0 revision.";
  }


  grouping DYNFLOWS-FLOW-ENTRY {
    description "LPTS Pre-IFIB Dynamic Flows Entry Data";
    leaf flow-name {
      type string;
      description "Flow Name";
    }
    leaf configurable {
      type boolean;
      description "Is Configurable";
    }
    leaf configured {
      type boolean;
      description "Is Configured";
    }
    leaf default-max {
      type uint32;
      description "Default Max";
    }
    leaf configured-max {
      type string;
      description "Configured Max";
    }
    leaf active-max {
      type uint32;
      description "Active Max";
    }
    leaf hardware-count {
      type uint32;
      description "Hardware Count";
    }
    leaf software-count {
      type uint32;
      description "Software Count";
    }
    leaf pending-software-entries {
      type boolean;
      description "Pending Software Entries";
    }
  }

  grouping PIFIB-DYNFLOWS-DATA {
    description "LPTS Pre-IFIB Dynamic Flows Data";
    leaf dynamic-flows-enabled {
      type boolean;
      description "Dynamic Flows Enabled";
    }
    leaf platform-supported-max {
      type uint32;
      description "Platform Max";
    }
    leaf platform-configured-max {
      type uint32;
      description "Platform Config Limit";
    }
    leaf platform-total-configured {
      type uint32;
      description "Platform Total Configured";
    }
    leaf total-hw-entries {
      type uint32;
      description "Total HW Entries";
    }
    leaf total-sw-entries {
      type uint32;
      description "Total SW Entries";
    }

    list flow {
      description "Flow Datalist";
      uses DYNFLOWS-FLOW-ENTRY;
    }
  }

  grouping PIFIB-SHOW-ENTRY {
    description "LPTS Pre-IFIB Entry Information";
    leaf vrf-name {
      type string;
      description "VRF Name";
    }
    leaf vid {
      type uint32;
      description "VRF ID";
    }
    leaf l3protocol {
      type uint32;
      description "Layer 3 Protocol";
    }
    leaf l4protocol {
      type uint32;
      description "Layer 4 Protocol";
    }
    leaf intf-name {
      type string;
      description "Interface Name";
    }
    leaf intf-handle {
      type uint32;
      description "Interface Handle";
    }
    leaf destination-addr {
      type string;
      description "Destination IP Address";
    }
    leaf source-addr {
      type string;
      description "Source IP Address";
    }
    leaf destination-type {
      type string;
      description "Destination Key Type";
    }
    leaf destination-value {
      type string;
      description "Destination Port/ICMP Type/IGMP Type";
    }
    leaf source-port {
      type string;
      description "Source port";
    }
    leaf is-frag {
      type uint8;
      description "Is Fragment";
    }
    leaf is-syn {
      type uint8;
      description "Is SYN";
    }
    leaf opcode {
      type string;
      description "Opcode";
    }
    leaf flow-type {
      type string;
      description "Flow type";
    }
    leaf listener-tag {
      type string;
      description "Listener Tag";
    }
    leaf local-flag {
      type uint8;
      description "Local Flag";
    }
    leaf is-fgid {
      type uint8;
      description "Is FGID or not";
    }
    leaf deliver-list-short {
      type string;
      description "Deliver List Short Format";
    }
    leaf deliver-list-long {
      type string;
      description "Deliver List Long Format";
    }
    leaf min-ttl {
      type uint8;
      description "Minimum TTL";
    }
    leaf accepts {
      type uint64;
      description "Packets matched to accept";
    }
    leaf drops {
      type uint64;
      description "Packets matched for drop";
    }
    leaf stale {
      type uint8;
      description "Is Stale";
    }
    leaf pifib-type {
      type uint8;
      description "sub Pre-IFIB type";
    }
    leaf pifib-program-time {
      type string;
      description "Creation or Update Time";
    }
  }
}
