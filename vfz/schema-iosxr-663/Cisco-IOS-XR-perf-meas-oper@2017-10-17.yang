module Cisco-IOS-XR-perf-meas-oper {

  /*** NAMESPACE / PREFIX DEFINITION ***/

  namespace "http://cisco.com/ns/yang/Cisco-IOS-XR-perf-meas-oper";


  prefix "perf-meas-oper";

  /*** LINKAGE (IMPORTS / INCLUDES) ***/

  import Cisco-IOS-XR-types { prefix "xr"; }

  include Cisco-IOS-XR-perf-meas-oper-sub2 {
    revision-date 2017-10-17;
  }

  include Cisco-IOS-XR-perf-meas-oper-sub1 {
    revision-date 2017-10-17;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR perf-meas package operational data.

     This module contains definitions
     for the following management objects:
       performance-measurement: Performance Measurement operational
         data
       performance-measurement-responder: performance measurement
         responder

     Copyright (c) 2013-2018 by Cisco Systems, Inc.
     All rights reserved.";

  revision "2017-10-17" {
    description
      "Revision Zero.";
  }

  revision "2015-11-09" {
    description
      "IOS XR 6.0 revision.";
  }


  container performance-measurement {
    config false;
    description "Performance Measurement operational data";

    container nodes {
      description "Node table for node-specific operational data";

      list node {
        key "node";
        description "Node-specific data for a particular node";

        container summary {
          description "Summary";
          uses PM-SUMMARY-BAG;
        }

        container interfaces {
          description "Interfaces";

          container interface-details {
            description "Interface detailed table";

            list interface-detail {
              key "interface-name";
              description "Detailed interface information";
              leaf interface-name {
                type xr:Interface-name;
                description "Interface name";
              }
              uses PM-INTF-BAG;
            }
          }

          container interface-delay {
            description "Delay-measurement intformation";

            container interface-last-aggregations {
              description "Table of last probe aggregation";

              list interface-last-aggregation {
                key "interface-name";
                description "Last probe aggregation information";
                leaf interface-name {
                  type xr:Interface-name;
                  description "Interface name";
                }
                uses PM-INTF-LAST-AGGR-BAG;
              }
            }

            container interface-probe-histories {
              description "Table of probe histories";

              list interface-probe-history {
                key "interface-name";
                description "Probe history information";
                leaf interface-name {
                  type xr:Interface-name;
                  description "Interface name";
                }
                uses PM-INTF-PROBE-HISTORY-BAG;
              }
            }

            container interface-aggregated-histories {
              description "Table of aggregated probe histories";

              list interface-aggregated-history {
                key "interface-name";
                description "Aggregated probe history information";
                leaf interface-name {
                  type xr:Interface-name;
                  description "Interface name";
                }
                uses PM-INTF-AGGR-HISTORY-BAG;
              }
            }

            container interface-last-probes {
              description "Table of last probes";

              list interface-last-probe {
                key "interface-name";
                description "Last measurement information";
                leaf interface-name {
                  type xr:Interface-name;
                  description "Interface name";
                }
                uses PM-INTF-LAST-PROBE-BAG;
              }
            }

            container interface-last-advertisements {
              description "Table of last advertisements";

              list interface-last-advertisement {
                key "interface-name";
                description "Last advertisement information";
                leaf interface-name {
                  type xr:Interface-name;
                  description "Interface name";
                }
                uses PM-INTF-LAST-ADVERT-BAG;
              }
            }
          }
        }
        leaf node {
          type xr:Node-id;
          description "Node";
        }
      }
    }
  }

  container performance-measurement-responder {
    config false;
    description "performance measurement responder";

    container nodes {
      description "Node table for node-specific operational data";

      list node {
        key "node";
        description "Node-specific data for a particular node";

        container summary {
          description "Summary";
          uses PM-RESP-SUMMARY-BAG;
        }

        container interfaces {
          description "Table of interfaces";

          list interface {
            key "interface-name";
            description "Interface information";
            leaf interface-name {
              type xr:Cisco-ios-xr-string;
              description "Interface name";
            }
            uses PM-RESP-INTF-BAG;
          }
        }
        leaf node {
          type xr:Node-id;
          description "Node";
        }
      }
    }
  }
}
