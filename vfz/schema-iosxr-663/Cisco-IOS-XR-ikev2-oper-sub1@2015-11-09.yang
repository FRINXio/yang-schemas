submodule Cisco-IOS-XR-ikev2-oper-sub1 {

  belongs-to Cisco-IOS-XR-ikev2-oper {
    prefix Cisco-IOS-XR-ikev2-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ikev2 package operational data.

     Copyright (c) 2013-2018 by Cisco Systems, Inc.
     All rights reserved.";

  revision "2015-11-09" {
    description
      "IOS XR 6.0 revision.";
  }

  typedef String1 {
    type string;
    description "String1";
  }

  grouping IKEV2-EDM-PEER {
    description "IKEV2 EDM PEER";
    leaf peer-name {
      type string;
      description "Name of the peer";
    }
    leaf ip-address {
      type string;
      description "IP Address of the peer";
    }
    leaf subnet {
      type string;
      description "Subnet mask of the peer";
    }
    leaf local-psk {
      type string;
      description "Local PSK";
    }
    leaf remote-psk {
      type string;
      description "Remote PSK";
    }
  }

  grouping IKEV2-EDM-KEYRING {
    description "IKEV2 EDM KEYRING";
    leaf keyring-name {
      type string;
      description "Name of the Keyring";
    }

    list peer {
      description "List of peers";
      uses IKEV2-EDM-PEER;
    }
  }

  grouping IKEV2-EDM-PROFILE {
    description "IKEV2 EDM PROFILE";
    leaf profile-name {
      type string;
      description "Name of the Profile";
    }
    leaf keyring-name {
      type string;
      description "Name of the keyring";
    }
    leaf match-any {
      type boolean;
      description "Match Any Criteria";
    }
    leaf lifetime {
      type uint32;
      description "Lifetime";
    }
    leaf dpd-interval {
      type uint32;
      description "DPD Interval";
    }
    leaf dpd-retry {
      type uint32;
      description "DPD Retry";
    }
    leaf-list addr {
      type inet:ipv4-address;
      description "Match address of peer";
    }
    leaf-list mask {
      type inet:ipv4-address;
      description "Mask of peer";
    }
  }

  grouping IKEV2-EDM-PROPOSAL {
    description "IKEV2 EDM PROPOSAL";
    leaf proposal-name {
      type string;
      description "Name of the proposal";
    }
    leaf-list encryption-alg {
      type String1;
      description "Encryption Algorithm";
    }
    leaf-list hash-alg {
      type String1;
      description "Integrity Algorithm";
    }
    leaf-list prf-alg {
      type String1;
      description "PRF Algorithm";
    }
    leaf-list group-alg {
      type String1;
      description "Group Algorithm";
    }
  }

  grouping IKEV2-EDM-POLICY {
    description "IKEV2 EDM POLICY";
    leaf policy-name {
      type string;
      description "Name of the policy";
    }
    leaf-list addr {
      type inet:ipv4-address;
      description "Match address of peer";
    }
    leaf-list proposal {
      type String1;
      description "List of proposals";
    }
  }

  grouping IKEV2-EDM-SA-DB {
    description "IKEV2 EDM SA DB";

    list sa {
      description "SA list";
      uses IKEV2-EDM-SA;
    }
  }

  grouping IKEV2-EDM-CHILD-SA {
    description "IKEV2 EDM CHILD SA";
    leaf local-selector {
      type string;
      description "Local Selector";
    }
    leaf remote-selector {
      type string;
      description "Remote Selector";
    }
    leaf esp-spi-in-out {
      type string;
      description "ESP SPI In Out";
    }
    leaf encr {
      type string;
      description "Encryption";
    }
    leaf keysize {
      type uint32;
      description "Keysize";
    }
    leaf hmac {
      type string;
      description "ESP HMAC";
    }
  }

  grouping IKEV2-EDM-SA {
    description "IKEV2 EDM SA";
    leaf tunnel-id {
      type uint32;
      description "Tunnel ID";
    }
    leaf local-addr-port {
      type string;
      description "Local Addr Port";
    }
    leaf remote-addr-port {
      type string;
      description "Remote Addr Port";
    }
    leaf state {
      type string;
      description "State";
    }
    leaf encr {
      type string;
      description "Encryption";
    }
    leaf keysize {
      type uint32;
      description "Keysize";
    }
    leaf prf {
      type string;
      description "PRF";
    }
    leaf hash {
      type string;
      description "Hash";
    }
    leaf dh-group {
      type uint32;
      description "DH Group";
    }
    leaf auth-sign {
      type string;
      description "Auth Sign";
    }
    leaf auth-verify {
      type string;
      description "Auth Verify";
    }
    leaf life-active {
      type string;
      description "Life-Active Time";
    }
    leaf session-id {
      type uint32;
      description "Session ID";
    }
    leaf status-desc {
      type string;
      description "Status Description";
    }
    leaf local-spi {
      type string;
      description "Local SPI";
    }
    leaf remote-spi {
      type string;
      description "Remote SPI";
    }
    leaf local-id {
      type string;
      description "Local ID";
    }
    leaf remote-id {
      type string;
      description "Remote ID";
    }
    leaf sa-initiator {
      type boolean;
      description "Sa Initiator";
    }
  }

  grouping IKEV2-EDM-SESSION {
    description "IKEV2 EDM SESSION";
    leaf session-id {
      type uint32;
      description "Session ID";
    }
    leaf session-status {
      type string;
      description "Session Status";
    }
    leaf ike-cnt {
      type uint32;
      description "IKE Count";
    }
    leaf child-cnt {
      type uint32;
      description "Child Count";
    }

    list sa {
      description "SA List";
      uses IKEV2-EDM-SA;
    }

    list child-sa {
      description "Child SA List";
      uses IKEV2-EDM-CHILD-SA;
    }
  }

  grouping IKEV2-EDM-SESSION-DB {
    description "IKEV2 EDM SESSION DB";

    list session {
      description "Session List";
      uses IKEV2-EDM-SESSION;
    }
  }
}
