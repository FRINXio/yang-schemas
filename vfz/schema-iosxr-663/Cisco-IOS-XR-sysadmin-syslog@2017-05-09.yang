module Cisco-IOS-XR-sysadmin-syslog {
  namespace "http://www.cisco.com/ns/yang/Cisco-IOS-XR-sysadmin-syslog";
  prefix syslog;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

This module defines configuration for
sysadmin syslog infrastructure.

Copyright(c) 2010-2016 by Cisco Systems, Inc.
All rights reserved.

    Copyright (c) 2012-2018 by Cisco Systems, Inc.
     All rights reserved.";
  revision 2017-05-09 {
    description
      "Namespace change to comply with Cisco guidelines";
  }


  grouping syslog-grp {
    container console {
      description
        "Syslog Infrastructure";
      choice disable_or_severity {
        mandatory false;
        case choice_emergency {
          leaf emergency {
            type empty;
          }
        }
        case choice_alert {
          leaf alert {
            type empty;
          }
        }
        case choice_critical {
          leaf critical {
            type empty;
          }
        }
        case choice_error {
          leaf error {
            type empty;
          }
        }
        case choice_warning {
          leaf warning {
            type empty;
          }
        }
        case choice_notice {
          leaf notice {
            type empty;
          }
        }
        case choice_informational {
          leaf informational {
            type empty;
          }
        }
        case choice_debug {
          leaf debug {
            type empty;
          }
        }
        case choice_disable {
          leaf disable {
            type empty;
          }
        }
      }
    }
  }

  typedef num-lines-type {
    type uint32;
  }

  typedef dir-or-file-path-type {
    type string;
  }
}
