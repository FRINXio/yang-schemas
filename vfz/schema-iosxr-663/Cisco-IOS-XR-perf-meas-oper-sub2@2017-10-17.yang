submodule Cisco-IOS-XR-perf-meas-oper-sub2 {

  belongs-to Cisco-IOS-XR-perf-meas-oper {
    prefix Cisco-IOS-XR-perf-meas-oper;
  }

  /*** LINKAGE (IMPORTS / INCLUDES) ***/

  import ietf-inet-types { prefix "inet"; }

  import ietf-yang-types { prefix "yang"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR perf-meas package operational data.

     Copyright (c) 2013-2018 by Cisco Systems, Inc.
     All rights reserved.";

  revision "2017-10-17" {
    description
      "Revision Zero.";
  }

  revision "2015-11-09" {
    description
      "IOS XR 6.0 revision.";
  }

  typedef Pm-advert-reason {
    type enumeration {
      enum periodic-timer-expired-no-advertisements {
        description
          "Periodic timer expired. No advertisements have
          occured";
      }
      enum periodic-advertisement-threshold-average {
        description
          "Periodic timer expired. Average value threshold
          crossed";
      }
      enum periodic-advertisement-threshold-minimum {
        description
          "Periodic timer expired. Minimum value threshold
          crossed";
      }
      enum periodic-advertisement-threshold-maximum {
        description
          "Periodic timer expired. Maximum value threshold
          crossed";
      }
      enum periodic-advertisement-threshold-variance {
        description
          "Periodic timer expired. Variance value
          threshold crossed";
      }
      enum accelerated-advertisement-threshold-minimum {
        description "Accelerated minimum value threshold crossed";
      }
      enum accelerated-advertisement-upper-bound-minimum {
        description "Accelerated minimum value upper bound crossed";
      }
      enum advertisement-enabled {
        description "Advertisement enabled";
      }
      enum advertisement-disabled {
        description "Advertisement disabled";
      }
      enum session-unconfigured {
        description "Session unconfigured";
      }
      enum clear-cli-command {
        description "Session cleared via CLI";
      }
      enum advertise-delay-config {
        description "Advertise delay config";
      }
      enum advertise-delay-unconfig {
        description "Advertise delay unconfig";
      }
      enum received-control-code-error {
        description
          "Recevied control code error, as per RFC 6374,
          from the responder";
      }
      enum link-is-down {
        description "Link is in down state";
      }
    }
    description "PM advertisement reason";
  }
  typedef Pm-probe-not-running-reason {
    type enumeration {
      enum probe-is-running {
        description "Probe is running";
      }
      enum platform-not-supported {
        description "Measurement is not supported on this plaftorm";
      }
      enum nonv1-active-node {
        description "Node is not V1 active";
      }
      enum control-code-error {
        description "An uncleared control code error was received";
      }
      enum interface-admin-down {
        description "Interface admin down";
      }
      enum interface-down {
        description "Interface down";
      }
      enum mpls-capability-not-present {
        description "MPLS is not enabled on interface";
      }
      enum interface-not-present {
        description "Interface not present or preconfigured";
      }
      enum ip-address-not-configured {
        description "IP address is not present on interface";
      }
    }
    description "PM probe not running reason";
  }
  typedef Pm-measurement {
    type enumeration {
      enum delay-measurement-type {
        description "Delay Measurement Type";
      }
    }
    description "PM Measurement Type";
  }
  typedef Pm-transport {
    type enumeration {
      enum interface-transport-type {
        description "Interface transport type";
      }
      enum rsvpte-transport-type {
        description "RSVP-TE tunnel transport type";
      }
      enum sr-policy-transport-type {
        description "SR Policy transport type";
      }
    }
    description "PM Transport Type";
  }
  typedef Pm-delay-mode {
    type enumeration {
      enum delay-mode-one-way {
        description "One-way delay-measurement mode";
      }
      enum delay-mode-two-way {
        description "Two-way delay-measurement mode";
      }
    }
    description "PM Delay Mode Type";
  }

  grouping PM-INTF-LAST-ADVERT-BAG {
    description "PM interface delay last advertisement bag";

    container last-advertisement {
      description "Last advertisement";
      uses PM-SCB-LAST-ADVERT-BAG;
    }
  }

  grouping PM-INTF-LAST-PROBE-BAG {
    description "PM interface delay last probe bag";

    container last-probe {
      description "Last probe";
      uses PM-PROBE-SAMPLE-BAG;
    }
  }

  grouping PM-INTF-AGGR-HISTORY-BAG {
    description "PM interface delay aggregated probe history bag";
    leaf interface-name-xr {
      type string;
      description "Interface name";
    }
    leaf interface-handle {
      type uint32;
      description "Interface handle";
    }

    list history {
      description "History of previous probe aggregations";
      uses PM-AGGR-SAMPLE-BAG;
    }
  }

  grouping PM-PROBE-SAMPLE-BAG {
    description "PM delay probe history bag";

    container probe-values {
      description "Probe values";
      uses PM-VALUES-BAG;
    }
    leaf probe-start-timestamp {
      type uint64;
      units "millisecond";
      description
        "Time last probe started (milliseconds since Jan.
        1, 1970)";
    }
    leaf packets-sent {
      type uint32;
      description "Packets sent";
    }
    leaf packets-received {
      type uint32;
      description "Packets received";
    }
  }

  grouping PM-INTF-PROBE-HISTORY-BAG {
    description "PM interface delay probe history bag";
    leaf interface-name-xr {
      type string;
      description "Interface name";
    }
    leaf interface-handle {
      type uint32;
      description "Interface handle";
    }

    list history {
      description "History of previous probes";
      uses PM-PROBE-SAMPLE-BAG;
    }
  }

  grouping PM-AGGR-SAMPLE-BAG {
    description "PM aggregated delay probe history bag";

    container aggregated-probe-values {
      description "Aggregated probe values";
      uses PM-VALUES-BAG;
    }
    leaf aggregation-timestamp {
      type uint64;
      units "millisecond";
      description
        "Time probe aggregation was done (milliseconds
        since Jan. 1, 1970)";
    }
    leaf aggregation-action {
      type Pm-advert-reason;
      description "Action performed with the aggregated values";
    }
  }

  grouping PM-INTF-LAST-AGGR-BAG {
    description "PM interface delay last aggregation bag";

    container last-aggregation {
      description "Last probe aggregation";
      uses PM-AGGR-SAMPLE-BAG;
    }
  }

  grouping PM-SCB-CONTROL-CODE {
    description "Last received control code";
    leaf control-code {
      type uint8;
      description "MPLS PM RFC 6374 control code";
    }
    leaf timestamp {
      type uint64;
      units "millisecond";
      description
        "Received timestamp of the control code
        (milliseconds since Jan. 1, 1970)";
    }
  }

  grouping PM-SCB-NEXT-ADVERT-BAG {
    description "PM delay next advertisement bag";

    container advertisement-interval-values {
      description "Advertisement interval values";
      uses PM-VALUES-BAG;
    }
    leaf advertisement-interval-probes-remaining {
      type uint32;
      description
        "Probes remaining until next periodic
        advertisement check";
    }
    leaf rolling-average {
      type uint32;
      description "Rolling average value (uSec)";
    }
  }

  grouping PM-SCB-LAST-ADVERT-BAG {
    description "PM delay last advertisement bag";

    container advertised-values {
      description "Advertised values";
      uses PM-VALUES-BAG;
    }
    leaf time-of-advertisement {
      type uint64;
      units "millisecond";
      description
        "Time of the advertisement (milliseconds since
        Jan. 1, 1970)";
    }
    leaf advertisement-reason {
      type Pm-advert-reason;
      description "Reason for advertisement";
    }
  }

  grouping PM-SCB-SAMPLE-BAG {
    description "PM delay probe sample bag";
    leaf measurement-value {
      type uint64;
      description "Measurement value (nsec)";
    }
    leaf query-timestamp {
      type uint64;
      units "millisecond";
      description
        "Timestamp when the measurement was taken
        (milliseconds since Jan. 1, 1970)";
    }
  }

  grouping PM-VALUES-BAG {
    description "PM delay summarized delay values";
    leaf average {
      type uint32;
      description "Average value (uSec)";
    }
    leaf minimum {
      type uint32;
      description "Minimum value (uSec)";
    }
    leaf maximum {
      type uint32;
      description "Maximum value (uSec)";
    }
    leaf variance {
      type uint32;
      description "Variance value (uSec)";
    }
  }

  grouping PM-SCB-PROBE-BAG {
    description "PM delay probe bag";

    container probe-results {
      description "Summarized  results of the current probe";
      uses PM-VALUES-BAG;
    }
    leaf probe-start-time-stamp {
      type uint64;
      units "millisecond";
      description
        "Timestamp in milliseconds of the current probe
        start (milliseconds since Jan. 1, 1970)";
    }
    leaf next-probe-start-time-remaining-in-millisec {
      type uint32;
      units "millisecond";
      description
        "Time in milliseconds until the next probe starts";
    }
    leaf next-packet-sent-time-remaining-in-millisec {
      type uint32;
      units "millisecond";
      description
        "Time in milliseconds until the next packet is
        sent";
    }
    leaf number-of-packets-sent {
      type uint32;
      description "Number of packets sent in the current probe";
    }
    leaf number-of-packets-received {
      type uint32;
      description "Number of packets received in the current probe";
    }
    leaf probe-not-running-reason {
      type Pm-probe-not-running-reason;
      description "Reason why probe is not running";
    }
  }

  grouping PM-SCB-BAG {
    description "PM interface delay session bag";

    container current-probe {
      description "Information for the current probe";
      uses PM-SCB-PROBE-BAG;
    }

    container session-counters {
      description "Session counters";
      uses PM-DELAY-COUNTERS-INFO-BAG;
    }

    container last-advertisement-information {
      description "Last advertisement information";
      uses PM-SCB-LAST-ADVERT-BAG;
    }

    container next-advertisement-information {
      description "Next advertisement information";
      uses PM-SCB-NEXT-ADVERT-BAG;
    }

    container last-notification-control-code {
      description "Last notifcation control code received";
      uses PM-SCB-CONTROL-CODE;
    }

    container last-error-control-code {
      description "Last error control code received";
      uses PM-SCB-CONTROL-CODE;
    }
    leaf session-id {
      type uint32;
      description "Session ID";
    }
    leaf transport-type {
      type Pm-transport;
      description "Transport Type";
    }
    leaf measurement-type {
      type Pm-measurement;
      description "Measurement Type";
    }
    leaf periodic-advertisement-interval-in-sec {
      type uint32;
      units "second";
      description "Periodic advertisement interval in seconds";
    }

    list probe-history {
      description "Current probe history";
      uses PM-SCB-SAMPLE-BAG;
    }
  }

  grouping PM-INTF-BAG {
    description "PM interface bag";
    leaf interface-name-xr {
      type string;
      description "Interface name";
    }
    leaf interface-handle {
      type uint32;
      description "Interface handle";
    }
    leaf interface-state {
      type boolean;
      description "Interface state";
    }
    leaf source-address {
      type inet:ipv4-address;
      description "Source Address";
    }
    leaf source-v6-address {
      type inet:ipv6-address;
      description "Source IPv6 Address";
    }
    leaf source-mac-address {
      type yang:mac-address;
      description "Source Mac address";
    }
    leaf primary-vlan-tag {
      type uint16;
      description "Primary VLAN Tag";
    }
    leaf secondary-vlan-tag {
      type uint16;
      description "Secondary VLAN Tag";
    }

    list delay-measurement-session {
      description "Delay-measurement sessions";
      uses PM-SCB-BAG;
    }
  }

  grouping PM-DELAY-GLOBAL-COUNTERS-BAG {
    description "PM global counters";
    leaf query-packets-sent {
      type uint64;
      description "Query packets sent";
    }
    leaf query-packets-received {
      type uint64;
      description "Query packets received";
    }
    leaf received-packet-error-invalid-session-id {
      type uint64;
      description "Received packet error, invalid session ID";
    }
    leaf received-packet-error-no-session {
      type uint64;
      description "Received packet error, no session";
    }
  }

  grouping PM-INTF-EXCLUSIVE-DELAY-COUNTERS-INFO-BAG {
    description "PM INTF EXCLUSIVE DELAY COUNTERS INFO BAG";
    leaf query-packet-sent-error-interface-down {
      type uint64;
      description "Query packet sent error, interface down";
    }
    leaf query-packet-sent-error-no-mpls-caps {
      type uint64;
      description "Query packet sent error, no MPLS caps";
    }
  }

  grouping PM-EXCLUSIVE-DELAY-COUNTERS-INFO-UNION {
    description "PM EXCLUSIVE DELAY COUNTERS INFO UNION";

    container interface-exclusive-counters {
      when "../type = 'interface-transport-type'" {
        description "../type = 'InterfaceTransportType'";
      }
      description "Counters Exclusive for interface";
      uses PM-INTF-EXCLUSIVE-DELAY-COUNTERS-INFO-BAG;
    }
    leaf type {
      type Pm-transport;
      description "type";
    }
  }

  grouping PM-QUERIER-DELAY-COUNTERS-BAG {
    description "PM delay querier counters";
    leaf query-packets-sent {
      type uint64;
      description "Query packets sent";
    }
    leaf query-packet-sent-errors {
      type uint64;
      description "Query packets sent error";
    }
    leaf query-packet-sent-error-no-ip-address {
      type uint64;
      description "Query packet sent error, no IP address";
    }
    leaf query-packets-received {
      type uint64;
      description "Query packets received";
    }
    leaf received-packet-error-negative-delay {
      type uint64;
      description "Received packet error, negative delay";
    }
    leaf received-packet-error-delay-exceeds-threshold {
      type uint64;
      description "Received packet error, delay exceeds threshold";
    }
    leaf received-packet-error-missing-tx-timestamp {
      type uint64;
      description "Received packet error, missing Tx timestamp";
    }
    leaf received-packet-error-missing-rx-timestamp {
      type uint64;
      description "Received packet error, missing Rx timestamp";
    }
    leaf received-packet-error-probe-full {
      type uint64;
      description "Received packet error, probe full";
    }
    leaf received-packet-error-probe-not-started {
      type uint64;
      description "Received packet error, probe not started";
    }
    leaf received-packet-control-code-error {
      type uint64;
      description "Received packet with a control code error";
    }
    leaf received-packet-control-code-notification {
      type uint64;
      description
        "Received packet with a control code notification";
    }
    leaf probes-started {
      type uint64;
      description "Probes started";
    }
    leaf probes-complete {
      type uint64;
      description "Probes completed";
    }
    leaf probes-incomplete {
      type uint64;
      description "Probes incomplete";
    }
    leaf advertisement {
      type uint64;
      description "Advertisements";
    }
  }

  grouping PM-DELAY-COUNTERS-INFO-BAG {
    description "PM DELAY COUNTERS INFO BAG";

    container generic-counters {
      description "Generic counters for a PM interface instance";
      uses PM-QUERIER-DELAY-COUNTERS-BAG;
    }

    container exclusive-counters {
      description "Exclusive counters for a PM interface instance";
      uses PM-EXCLUSIVE-DELAY-COUNTERS-INFO-UNION;
    }
  }

  grouping PM-DELAY-PROFILE-BAG {
    description "PM profile bag";
    leaf probe-interval {
      type uint32;
      description "Probe Interval (sec)";
    }
    leaf burst-interval {
      type uint32;
      description "Burst Interval (msec)";
    }
    leaf burst-count {
      type uint32;
      description "Burst Count";
    }
    leaf delay-measurement-mode {
      type Pm-delay-mode;
      description "Delay Measurement Mode Type";
    }
    leaf periodic-advertisement-enabled {
      type boolean;
      description "Advertisement Periodic Enabled";
    }
    leaf periodic-advertisement-interval {
      type uint32;
      description "Advertisement Periodic Interval (sec)";
    }
    leaf effective-periodic-advertisement-interval {
      type uint32;
      description "Advertisement Periodic Effective (sec)";
    }
    leaf periodic-advertisement-threshold {
      type uint32;
      description "Advertisement Periodic Threshold (%)";
    }
    leaf periodic-advertisement-minimum-change {
      type uint32;
      description "Advertisement Periodic Minimum Change (uSec)";
    }
    leaf accelerated-advertisement-threshold {
      type uint32;
      description "Advertisement Accelerated Threshold (%)";
    }
    leaf accelerated-advertisement-minimum-change {
      type uint32;
      description "Advertisement Accelerated Minimum Change (uSec)";
    }
    leaf accelerated-advertisement-enabled {
      type boolean;
      description "Advertisement Accelerated Enabled";
    }
  }

  grouping PM-DELAY-TRANSPORT-SUMMARY-BAG {
    description "PM delay summary bag";

    container delay-profile {
      description "Delay profile";
      uses PM-DELAY-PROFILE-BAG;
    }

    container delay-transport-counters {
      description "PM delay counters for a transport types";
      uses PM-DELAY-COUNTERS-INFO-BAG;
    }
    leaf total-delay-sessions {
      type uint32;
      description "Number of delay measurement sessions enabled";
    }
  }

  grouping PM-DELAY-SUMMARY-BAG {
    description "PM Delay Summary bag";

    container interface-delay-summary {
      description "Interface delay summary";
      uses PM-DELAY-TRANSPORT-SUMMARY-BAG;
    }

    container delay-global-counters {
      description "PM delay global counters";
      uses PM-DELAY-GLOBAL-COUNTERS-BAG;
    }
  }

  grouping PM-SUMMARY-BAG {
    description "PM Summary bag";

    container delay-summary {
      description "Delay summary";
      uses PM-DELAY-SUMMARY-BAG;
    }
    leaf total-interfaces {
      type uint32;
      description "Number of delay measurement interfaces enabled";
    }
  }
}
