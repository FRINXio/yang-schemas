module nokia-oper-global {

    yang-version "1.1";

    namespace "urn:nokia.com:sros:ns:yang:sr:oper-global";

    prefix "oper-global";

    import nokia-sros-yang-extensions     { prefix "sros-ext"; }


    sros-ext:sros-major-release "rel20";

    organization "Nokia";

    contact
        "Nokia SR OS Support
         Web: <http://www.nokia.com>";


    revision "2020-10-15";

    container global-operations {
        config false;
        description "Enter the global-operations context";

        action md-cli-raw-command {
            description "Trigger MD-CLI command.";

            input {

                leaf md-cli-input-line {
                    type string;
                    mandatory true;
                    description "MD-CLI command to be executed.";
                }

            }
            output {

                container results {
                    description "Enter the results context";

                    leaf md-cli-output-block {
                        type string;
                        description "Output of executed MD-CLI command.";
                    }

                } // container results

            }
        }
    } // container global-operations

}
