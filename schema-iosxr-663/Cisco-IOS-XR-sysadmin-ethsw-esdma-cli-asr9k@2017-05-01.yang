module Cisco-IOS-XR-sysadmin-ethsw-esdma-cli-asr9k {
  namespace "http://www.cisco.com/ns/yang/Cisco-IOS-XR-sysadmin-ethsw-esdma-cli-asr9k";
  prefix esdma;
  import Cisco-IOS-XR-sysadmin-ethsw-esdma-admin-exec {
    prefix esdma_admin_exec;
  }
  import Cisco-IOS-XR-sysadmin-ethsw-esdma-bridge {
    prefix esdma_bridge;
  }
  import Cisco-IOS-XR-sysadmin-ethsw-esdma-clear {
    prefix esdma_clear;
  }
  import Cisco-IOS-XR-sysadmin-ethsw-esdma-fdb {
    prefix esdma_fdb;
  }
  import Cisco-IOS-XR-sysadmin-ethsw-esdma-mac {
    prefix esdma_mac;
  }
  import Cisco-IOS-XR-sysadmin-ethsw-esdma-mgmt-agent {
    prefix esdma_mgmt_agent;
  }
  import Cisco-IOS-XR-sysadmin-ethsw-esdma-reachable {
    prefix esdma_reachable;
  }
  import Cisco-IOS-XR-sysadmin-ethsw-esdma-statistics {
    prefix esdma_statistics;
  }
  import Cisco-IOS-XR-sysadmin-ethsw-esdma-summary {
    prefix esdma_summary;
  }
  import Cisco-IOS-XR-sysadmin-ethsw-esdma-trace {
    prefix esdma_trace;
  }
  import Cisco-IOS-XR-sysadmin-ethsw-esdma-trunk {
    prefix esdma_trunk;
  }
  import Cisco-IOS-XR-sysadmin-ethsw-esdma-vlan {
    prefix esdma_vlan;
  }
  import Cisco-IOS-XR-sysadmin-ethsw-esdma-debug {
    prefix esdma_debug;
  }
  import Cisco-IOS-XR-sysadmin-ethsw-esdma-sdr {
    prefix esdma_sdr;
  }
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

The 'switch' module provides support for configuring and
monitoring the control Ethernet switches and ports.
Support includes basic switch and port statistics.

Copyright(c) 2011-2017 by Cisco Systems, Inc.
All rights reserved.

    Copyright (c) 2012-2018 by Cisco Systems, Inc.
     All rights reserved.";
  revision 2017-05-01 {
    description
      "Namespace change to comply with Cisco guidelines on namespace";
  }


  grouping switch_clear {
    container oper {
      description
        "Control Ethernet switch operational data.";
      config false;
      uses esdma_clear:switch-clear-fdb;
      uses esdma_clear:switch-clear-statistics;
    }
  }

  grouping switch {
    container oper {
      description
        "Control Ethernet switch operational data.";
      config false;
      uses esdma_reachable:switch-reachable-data;
      uses esdma_summary:switch-summary-group;
      uses esdma_statistics:switch-statistics-group;
      uses esdma_mac:switch-mac-group;
      uses esdma_bridge:switch-bridge-group;
      uses esdma_fdb:switch-fdb-group;
      uses esdma_vlan:switch-vlan-group;
      uses esdma_trace:esd-ctrace;
      uses esdma_mgmt_agent:esdma-mgmt-group;
      uses esdma_sdr:switch-sdr-group;
      uses esdma_admin_exec:switch-exec-admin;
      uses esdma_trunk:switch-trunk-group;
      uses esdma_debug:switch-debug-group;
    }
  }
}
