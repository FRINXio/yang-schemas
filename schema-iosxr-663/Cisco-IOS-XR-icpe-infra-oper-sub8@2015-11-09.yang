submodule Cisco-IOS-XR-icpe-infra-oper-sub8 {

  belongs-to Cisco-IOS-XR-icpe-infra-oper {
    prefix Cisco-IOS-XR-icpe-infra-oper;
  }

  /*** LINKAGE (IMPORTS / INCLUDES) ***/

  include Cisco-IOS-XR-icpe-infra-oper-sub4 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2018 by Cisco Systems, Inc.
     All rights reserved.";

  revision "2015-11-09" {
    description
      "IOS XR 6.0 revision.";
  }


  grouping ICPE-OPER-SAT-VERSION-TYPE {
    description "ICPE OPER SAT VERSION TYPE";
    leaf version-check-state {
      type Icpe-oper-ver-check-state;
      description "Version check state";
    }
    leaf remote-version-present {
      type boolean;
      description "Remote version present";
    }
    leaf-list remote-version {
      type Xr-yang-string;
      description "Remote version";
    }
  }

  grouping ICPE-OPER-SAT-REMOTE-VERSION-TYPE {
    description "Satellite remote version information";

    container active-version {
      description "Satellite active version information";
      uses ICPE-OPER-SAT-VERSION-TYPE;
    }

    container transferred-version {
      description "Satellite transferred version information";
      uses ICPE-OPER-SAT-VERSION-TYPE;
    }

    container committed-version {
      description "Satellite committed version information";
      uses ICPE-OPER-SAT-VERSION-TYPE;
    }
    leaf satellite-id-xr {
      type uint16;
      description "Satellite ID";
    }
    leaf version-check-state {
      type Icpe-oper-ver-check-state;
      description "Version check state";
    }
    leaf remote-version-present {
      type boolean;
      description "Remote version present";
    }
    leaf-list remote-version {
      type Xr-yang-string;
      description "Remote version";
    }
  }
}
