module Cisco-IOS-XR-sysadmin-asr9k-envmon-types {
  namespace "http://www.cisco.com/ns/Cisco-IOS-XR-sysadmin-asr9k-envmon-types";
  prefix envmon-types;

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2017-11-27 {
    description
      "Add graceful shutdown disable CLI.";
  }


  typedef num_pm {
    type uint32 {
      range "0..12";
    }
  }

  grouping fan-speed-group {
    leaf raise-fan-speed {
      config false;
      type uint32 {
        range "0..100";
      }
    }
  }

  grouping fan-ctrl-optics-group {
    leaf fan-ctrl-optics {
      config false;
      type uint32 {
        range "0..1";
      }
    }
  }

  grouping vin-uv-shut-group {
    leaf graceful-shutdown {
      config false;
      type uint32 {
        range "0..1";
      }
    }
  }
}
