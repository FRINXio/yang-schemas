//*************  DO-NOT EDIT  **************
//*********** Auto-generated file ********** 

 module cisco-xr-openconfig-platform-linecard-deviations {

  prefix  "oc-linecarddevs";

  namespace "http://cisco.com/ns/yang/cisco-xr-openconfig-platform-linecard-deviations";

  import openconfig-platform-linecard { prefix oc-linecard; }
  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-platform-linecard.yang@2017-08-03 

     on Cisco IOS-XR devices.

     Copyright (c) 2017-2019 by Cisco Systems, Inc.
     All rights reserved.";

  revision "2018-12-10" {
    description
      "Initial revision applicable to IOS-XR 6.6.1";
  }


  deviation /oc-platform:components/oc-platform:component/oc-linecard:linecard/oc-linecard:config/oc-linecard:power-admin-state {
    deviate not-supported;
  }


}
//total deviations:1
