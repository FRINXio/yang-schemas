module Cisco-IOS-XR-infra-tc-oper {

  /*** NAMESPACE / PREFIX DEFINITION ***/

  namespace "http://cisco.com/ns/yang/Cisco-IOS-XR-infra-tc-oper";


  prefix "infra-tc-oper";

  /*** LINKAGE (IMPORTS / INCLUDES) ***/

  import Cisco-IOS-XR-types { prefix "xr"; }

  include Cisco-IOS-XR-infra-tc-oper-sub1 {
    revision-date 2019-06-17;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-tc package operational data.

     This module contains definitions
     for the following management objects:
       traffic-collector: Global Traffic Collector configuration
         commands

     Copyright (c) 2013-2018 by Cisco Systems, Inc.
     All rights reserved.";

  revision "2019-06-17" {
    description
      "Change type of tunnel interface name to string";
  }

  revision "2015-11-09" {
    description
      "IOS XR 6.0 revision.";
  }

  typedef Tc-oper-af-name {
    type enumeration {
      enum ipv4 {
        value 0;
        description "IPv4";
      }
      enum ipv6 {
        value 1;
        description "IPv6";
      }
    }
    description "Tc oper af name";
  }
  typedef Tc-oper-local-label {
    type uint32 {
      range "16..1048575";
    }
    description "Tc oper local label";
  }

  grouping AF-TABLE {
    description "Common node of default-vrf, traffic-collector";

    container afs {
      description "Address Family specific operational data";

      list af {
        key "af-name";
        description "Operational data for given Address Family";

        container counters {
          description "Show Counters";

          container prefixes {
            description "Prefix Database";

            list prefix {
              description "Show Prefix Counter";
              leaf ipaddr {
                type xr:Cisco-ios-xr-string;
                description "IP Address";
              }
              leaf mask {
                type xr:Cisco-ios-xr-string;
                description "Prefix Mask";
              }
              leaf label {
                type Tc-oper-local-label;
                description "Local Label";
              }
              uses TC-MGMT-PREFIX-DATA;
            }
          }

          container tunnels {
            description "Tunnels";

            list tunnel {
              key "interface-name";
              description "Tunnel information";
              leaf interface-name {
                type xr:Cisco-ios-xr-string;
                description "The Interface Name";
              }
              uses TC-MGMT-TUNNEL-DATA;
            }
          }
        }
        leaf af-name {
          type Tc-oper-af-name;
          description "Address Family name";
        }
      }
    }
  }

  container traffic-collector {
    config false;
    description "Global Traffic Collector configuration commands";

    container external-interfaces {
      description "External Interface";

      list external-interface {
        key "interface-name";
        description "External Interface ";
        leaf interface-name {
          type xr:Interface-name;
          description "The Interface Name";
        }
        uses TC-MGMT-EXT-IF-DATA;
      }
    }

    container summary {
      description "Traffic Collector summary";
      uses TC-MGMT-SUMMARY;
    }

    container vrf-table {
      description "VRF specific operational data";

      container default-vrf {
        description "DefaultVRF specific operational data";
        uses AF-TABLE;
      }
    }
    uses AF-TABLE;
  }
}
